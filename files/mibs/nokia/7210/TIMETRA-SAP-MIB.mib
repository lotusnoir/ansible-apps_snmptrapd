TIMETRA-SAP-MIB DEFINITIONS ::= BEGIN

IMPORTS
    MODULE-IDENTITY, OBJECT-TYPE,
    NOTIFICATION-TYPE, Gauge32,
    Integer32, Unsigned32, IpAddress,
    Counter64, Counter32                        FROM SNMPv2-SMI

    MODULE-COMPLIANCE, OBJECT-GROUP,
    NOTIFICATION-GROUP                          FROM SNMPv2-CONF

    TEXTUAL-CONVENTION,
    DisplayString,
    RowStatus, MacAddress, TimeStamp,
    TruthValue                                  FROM SNMPv2-TC

    InterfaceIndexOrZero                        FROM IF-MIB

    InetAddressPrefixLength,
    InetAddressType, InetAddress,
    InetAddressIPv6
                                                FROM INET-ADDRESS-MIB

    AtmTrafficDescrParamIndex,
    AtmVpIdentifier,
    AtmVcIdentifier
                                                FROM ATM-TC-MIB

    TIngPolicerId, TEgrPolicerId,
    TmnxIngPolicerStatMode, TmnxEgrPolicerStatMode,
    ServiceAdminStatus, 
    TmnxPortID, TmnxEncapVal, TmnxServId, TmnxCustId, TNamedItem,
    TIngressQueueId, TEgressQueueId, TNamedItemOrEmpty, TPortSchedulerPIR,
    TmnxActionType, TmnxOperState, TmnxIgmpVersion,
    TCpmProtPolicyID, TCIRRate, TPIRRate, TmnxEnabledDisabled, TItemDescription,
    TPolicyStatementNameOrEmpty, TSapIngressPolicyID, TSapEgressPolicyID,
    TIngressHsmdaQueueId, TEgressHsmdaQueueId,
    THsmdaPIRKRateOverride, THsmdaCIRKRateOverride,
    TIngHsmdaPerPacketOffsetOvr,
    TEgrHsmdaPerPacketOffsetOvr,
    TEgressPerPacketOffsetOvr,
    TIngressHsmdaCounterId, TEgressHsmdaCounterId,
    TmnxManagedRouteStatus, TmnxAdminState,
    TBurstSize, TBurstPercentOrDefault,
    TAdaptationRule, TmnxVRtrID, 
    TmnxDefSubIdSource, TmnxAncpStringOrZero,
    THPolCIRRateOverride, THPolPIRRateOverride,
    TBurstSizeBytes, TBurstSizeBytesOverride, TPlcrBurstSizeBytesOverride,
    TmnxDefInterDestIdSource, TPerPacketOffsetOvr,
    TmnxIngPolicerStatModeOverride, TWeight,
    TmnxEgrPolicerStatModeOverride, QTag,
    TCpmProtPolicyIDOrDefault, TDSCPNameOrEmpty,
    TmnxBsxTransitIpPolicyIdOrZero,
    TmnxBsxTransPrefPolicyIdOrZero,
    TTmplPolicyID, ServiceOperStatus,
    TPIRPercentOverride, TCIRPercentOverride,
    TSapEgrEncapGrpQosPolicyIdOrZero, TSapEgrEncapGroupType,
    TSapEgrEncapGroupActionType, SvcISID,
    THsmdaWrrWeightOverride, TPortSchedulerAggRateLimitPIR,
    THSMDABurstSizeBytesOverride,
    TmnxBsxAarpIdOrZero, TmnxBsxAarpServiceRefType,
    TQosQGrpInstanceIDorZero, THPolVirtualSchePIRRate,
    TQosIngressPolicyID, TBurstLimit,
    TmnxLagPerLinkHashClass, TmnxLagPerLinkHashWeight,
    THPolVirtualScheCIRRate, TmnxLinkMapProfileIdOrZero,
    TmnxDistCpuProtActionDuration, TmnxDistCpuProtState,
     TQosQueuePIRRate, TQosQueueCIRRate,
    TmnxRipListenerStatus,
    TmnxDistCpuProtProtocolId, TmnxISID, TmnxIsidMFibStatus,
    TmnxSubShcvAction,
    TmnxSubShcvInterval,
    TmnxSubShcvRetryTimeout,
    TmnxSubShcvRetryCount,
    TEgressPolicerId, TIngressPolicerId
                                               FROM TIMETRA-TC-MIB

    tmnxServObjs, tmnxServConformance, tmnxServNotifications,
    custId, svcId, svcVpnId, tlsMstiInstanceId, tstpTraps,
    tmnxOtherBridgeId, tmnxCustomerBridgeId, tmnxCustomerRootBridgeId,
    protectedMacForNotify, tlsDhcpLseStateNewCiAddr,
    tlsDhcpLseStateNewChAddr, tlsDHCPClientLease, tlsDhcpLseStateOldCiAddr,
    tlsDhcpLseStateOldChAddr, hostConnectivityCiAddrType,
    hostConnectivityCiAddr, hostConnectivityChAddr,
    staticHostDynamicMacIpAddress, staticHostDynamicMacConflict,
    svcTlsMacMoveMaxRate, svcDhcpProxyError,
    svcDhcpCoAError, svcDhcpSubAuthError,
    tlsDhcpPacketProblem, svcDhcpLseStateNewCiAddr,
    svcDhcpLseStateNewChAddr, svcDhcpClientLease,
    svcDhcpLseStateOldCiAddr, svcDhcpLseStateOldChAddr, svcDhcpPacketProblem,
    svcDhcpLseStatePopulateError,
    ServObjName, ServObjDesc, ServType, VpnId, TlsBpduTranslation,
    TlsLimitMacMoveLevel, TlsLimitMacMove, StpExceptionCondition,
    BridgeId, TSapIngQueueId, TSapEgrQueueId, TStpPortState, StpPortRole,
    StpProtocol, MvplsPruneState, TQosQueueAttribute, TVirtSchedAttribute,
    MstiInstanceIdOrZero, TdmOptionsCasTrunkFraming, CemSapReportAlarm,
    tlsFdbType,
    CemSapEcid, L2ptProtocols, ConfigStatus,
    ServShcvOperState
                                                FROM TIMETRA-SERV-MIB

    timetraSRMIBModules                         FROM TIMETRA-GLOBAL-MIB

    tmnxPortCemStatsReportAlarm                 FROM TIMETRA-PORT-MIB
    tmnxChassisIndex, tmnxCardSlotNum, tmnxFPNum,
    TmnxHwIndexOrZero                           FROM TIMETRA-CHASSIS-MIB

    tSapIngPolicerId, tSapEgrPolicerId,
    tVirtualSchedulerName, tSchedulerPolicyName,
    tQosPolicerLevel,
    TmnxMcFrClassIndex                          FROM TIMETRA-QOS-MIB

    TFilterID                                   FROM TIMETRA-FILTER-MIB;

timetraSvcSapMIBModule   MODULE-IDENTITY
        LAST-UPDATED "201402200000Z"
        ORGANIZATION "Nokia"
        CONTACT-INFO
            "Nokia SROS Support
             Web: http://www.nokia.com"
    DESCRIPTION
        "This document is the SNMP MIB module to manage and provision
        the various services of the Nokia SROS system.

        Copyright 2003-2015 Nokia. All rights reserved. 
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."

--
--  Revision History
--
    REVISION        "201402200000Z"
    DESCRIPTION     "Rev 13.0               20 Feb 2014 00:00
                     13.0 release of the TIMETRA-SAP-MIB."
                     
    REVISION        "201401010000Z"
    DESCRIPTION     "Rev 12.0                1 Jan 2014 00:00
                     12.0 release of the TIMETRA-SAP-MIB."

    REVISION        "201102010000Z"
    DESCRIPTION     "Rev 9.0                 1 Feb 2011 00:00
                     9.0 release of the TIMETRA-SAP-MIB."

    REVISION        "200902280000Z"
    DESCRIPTION     "Rev 7.0                28 Feb 2009 00:00
                     7.0 release of the TIMETRA-SAP-MIB."

    REVISION        "200807010000Z"
    DESCRIPTION     "Rev 6.1                01 Jul 2008 00:00
                     6.1 release of the TIMETRA-SAP-MIB."

    REVISION        "200710010000Z"
    DESCRIPTION     "Rev 1.0                01 OCT 2007 00:00
                     1.0 release of the TIMETRA-SAP-MIB from TIMETRA-SERV-MIB."

    ::= { timetraSRMIBModules 55 }

-- --------------------------------------------------------------------
--      TIMETRA-SAP-MIB organisation
-- --------------------------------------------------------------------
tmnxSapObjs             OBJECT IDENTIFIER ::= { tmnxServObjs 3 }
    tmnxSapNotifyObjs       OBJECT IDENTIFIER ::= { tmnxSapObjs 100 }

tmnxSapConformance      OBJECT IDENTIFIER ::= { tmnxServConformance 3 }

sapTrapsPrefix          OBJECT IDENTIFIER ::= { tmnxServNotifications 3 }
    sapTraps                OBJECT IDENTIFIER ::= { sapTrapsPrefix 0 }

-- ----------------------------------------------------------------------------
--  Textual Conventions
-- ----------------------------------------------------------------------------

TmnxSapAtmEncapsulation ::= TEXTUAL-CONVENTION
    STATUS  current
    DESCRIPTION
       "The TmnxSapAtmEncapsulation data type is an enumerated integer 
         that specifies the data encapsulation used over the AAL5 SSCS layer.  
         
         The definition references RFC 2684 Multiprotocol Encapsulation over 
         ATM AAL5 and the ATM Forum LAN Emulation specification."
     SYNTAX          INTEGER {
                          vcMultiplexRoutedProtocol      (1),
                          vcMultiplexBridgedProtocol8023 (2),
                          llcSnapRoutedProtocol          (7),
                          multiprotocolFrameRelaySscs    (8),
                          unknown                        (10),
                          llcSnapBridgedProtocol8023     (11),
                          vcMultiplexPpp                 (12),
                          llcNlpidPpp                    (13),
                          auto                           (14)
                      }

TmnxSapSubscriberLimit ::= TEXTUAL-CONVENTION
    STATUS  current
    DESCRIPTION
       "The TmnxSapSubscriberLimit data type is an enumerated integer 
         that specifies the maximum number of subscribers allowed on
         a SAP."
    SYNTAX Unsigned32 (0..131071)

TmnxVlanGroupId ::= TEXTUAL-CONVENTION
    STATUS  current
    DESCRIPTION
       "The TmnxVlanGroupId data type is an enumerated integer 
         that specifies the VLAN range group identifer."
    SYNTAX Unsigned32 (1..4094)

TmnxSapInstStatus ::= TEXTUAL-CONVENTION
    STATUS  current
    DESCRIPTION
       "The TmnxSapInstStatus data type is an enumerated integer 
        that indicates status of the SAP instantiating other SAPs
        controlled by this SAP."
    SYNTAX INTEGER {
             notApplicable (1),
             complete (2),
             inProgress (3),
             failed (4)
           }

-- --------------------------------------------------------------------
-- tmnxSapObjs group
-- --------------------------------------------------------------------
sapNumEntries OBJECT-TYPE
    SYNTAX          Integer32
    MAX-ACCESS      read-only
    STATUS          current
    DESCRIPTION     "The current number of SAPs configured in this
                     device."
    ::= { tmnxSapObjs 1 }

-- ----------------------------------
-- Base SAP Table
-- ----------------------------------
sapBaseInfoTable OBJECT-TYPE
    SYNTAX          SEQUENCE OF SapBaseInfoEntry
    MAX-ACCESS      not-accessible
    STATUS          current
    DESCRIPTION     "A table that contains basic SAP information."
    ::= { tmnxSapObjs 2 }

sapBaseInfoEntry OBJECT-TYPE
    SYNTAX          SapBaseInfoEntry
    MAX-ACCESS      not-accessible
    STATUS          current
    DESCRIPTION     "Information about a specific SAP."
    INDEX           { svcId, sapPortId, sapEncapValue }
    ::= { sapBaseInfoTable 1 }

SapBaseInfoEntry ::=
    SEQUENCE {
        sapPortId                       TmnxPortID,
        sapEncapValue                   TmnxEncapVal,
        sapRowStatus                    RowStatus,
        sapType                         ServType,
        sapDescription                  ServObjDesc,
        sapAdminStatus                  ServiceAdminStatus,
        sapOperStatus                   INTEGER,
        sapIngressQosPolicyId           TSapIngressPolicyID,
        sapIngressMacFilterId           TFilterID,
        sapIngressIpFilterId            TFilterID,
        sapEgressQosPolicyId            TSapEgressPolicyID,
        sapEgressMacFilterId            TFilterID,
        sapEgressIpFilterId             TFilterID,
        sapMirrorStatus                 INTEGER,
        sapIesIfIndex                   InterfaceIndexOrZero,
        sapLastMgmtChange               TimeStamp,
        sapCollectAcctStats             TruthValue,
        sapAccountingPolicyId           Unsigned32,
        sapVpnId                        VpnId,
        sapCustId                       TmnxCustId,
        sapCustMultSvcSite              ServObjName,
        sapIngressQosSchedulerPolicy    ServObjName,
        sapEgressQosSchedulerPolicy     ServObjName,
        sapSplitHorizonGrp              ServObjName,
        sapIngressSharedQueuePolicy     ServObjName,
        sapIngressMatchQinQDot1PBits    INTEGER,
        sapOperFlags                    BITS,
        sapLastStatusChange             TimeStamp,
        sapAntiSpoofing                 INTEGER,
        sapIngressIpv6FilterId          TFilterID,
        sapEgressIpv6FilterId           TFilterID,
        sapTodSuite                     TNamedItemOrEmpty,
        sapIngUseMultipointShared       TruthValue,
        sapEgressQinQMarkTopOnly        TruthValue,
        sapEgressAggRateLimit           TPortSchedulerAggRateLimitPIR,
        sapEndPoint                     ServObjName,
        sapIngressVlanTranslation       INTEGER,
        sapIngressVlanTranslationId     Integer32,
        sapSubType                      INTEGER,
        sapCpmProtPolicyId              TCpmProtPolicyID,
        sapCpmProtMonitorMac            TruthValue,
        sapEgressFrameBasedAccounting   TruthValue,
        sapIngressAggRateLimit          TPortSchedulerPIR,
        sapEgressHsmdaShaperOverride    TNamedItemOrEmpty,
        sapIngressHsmdaPacketOffOvr     TIngHsmdaPerPacketOffsetOvr,
        sapEgressHsmdaPacketOffOverride TEgrHsmdaPerPacketOffsetOvr,
        sapCallingStationId             DisplayString,
        sapIsaAaApplicationProfile      ServObjName,
        sapIngPolicerPolicy             TNamedItemOrEmpty,
        sapEgrPolicerPolicy             TNamedItemOrEmpty,
        sapTmplUsed                     TNamedItemOrEmpty,
        sapEthRingIndex                 Unsigned32,
        sapIngressFlowspec              TruthValue,
        sapCpmProtEthCfmMonitorFlags    BITS,
        sapTransitIpPolicyId            TmnxBsxTransitIpPolicyIdOrZero,
        sapOperGrp                      TNamedItemOrEmpty,
        sapMonitorOperGrp               TNamedItemOrEmpty,
        sapEgressHsmdaWrrPolicyOvr      TNamedItemOrEmpty,
        sapTransitPrefixPolicyId        TmnxBsxTransPrefPolicyIdOrZero,
        sapCpmProtMonitorIP             TruthValue,
        sapHostsAdminState              ServiceAdminStatus,
        sapHostLockoutPolicy            TNamedItemOrEmpty,
        sapAarpId                       TmnxBsxAarpIdOrZero,
        sapIngressFPQGrp                TNamedItemOrEmpty,
        sapIngressFPQGrpInstanceId      TQosQGrpInstanceIDorZero,
        sapAarpServRefType              TmnxBsxAarpServiceRefType,
        sapSiteName                     TNamedItemOrEmpty,
        sapIgnoreOperDown               TruthValue,
        sapLagLinkMapProfile            TmnxLinkMapProfileIdOrZero,
        sapIngressIPv6Flowspec          TruthValue,
        sapEgressPortQGrp               TNamedItemOrEmpty,
        sapEgressPortQGrpInstanceId     TQosQGrpInstanceIDorZero,
        sapEtreeRootLeafTag             TruthValue,
        sapEtreeLeafTag                 Integer32,
        sapEtreeLeafAc                  TruthValue,
        sapEgressAggRateLUB             TruthValue,
        sapEgressAggRateLmt             Unsigned32
    }

sapPortId OBJECT-TYPE
    SYNTAX          TmnxPortID
    MAX-ACCESS      read-only
    STATUS          current
    DESCRIPTION     "The ID of the access port where this SAP
                     is defined."
    ::= { sapBaseInfoEntry 1 }

sapEncapValue OBJECT-TYPE
    SYNTAX          TmnxEncapVal
    MAX-ACCESS      read-only
    STATUS          current
    DESCRIPTION     "The value of the label used to identify this
                     SAP on the access port specified by sapPortId."
    ::= { sapBaseInfoEntry 2 }

sapRowStatus OBJECT-TYPE
    SYNTAX          RowStatus
    MAX-ACCESS      read-create
    STATUS          current
    DESCRIPTION     "This object indicates the status of this row. The
                     only values supported during a set operation are
                     'createAndGo' and 'destroy'."
    ::= { sapBaseInfoEntry 3 }

sapType OBJECT-TYPE
    SYNTAX          ServType
    MAX-ACCESS      read-only
    STATUS          current
    DESCRIPTION     "This object indicates the type of service where
                     this SAP is defined."
    ::= { sapBaseInfoEntry 4 }

sapDescription OBJECT-TYPE
    SYNTAX          ServObjDesc
    MAX-ACCESS      read-create
    STATUS          current
    DESCRIPTION     "Generic information about this SAP."
    DEFVAL          { "" }
    ::= { sapBaseInfoEntry 5 }

sapAdminStatus OBJECT-TYPE
    SYNTAX          ServiceAdminStatus
    MAX-ACCESS      read-create
    STATUS          current
    DESCRIPTION     "The desired state of this SAP."
    DEFVAL          { up }
    ::= { sapBaseInfoEntry 6 }

sapOperStatus OBJECT-TYPE
    SYNTAX          INTEGER {
                        up                 (1),
                        down               (2),
                        ingressQosMismatch (3),
                        egressQosMismatch  (4),
                        portMtuTooSmall    (5),
                        svcAdminDown       (6),
                        iesIfAdminDown     (7)
                    }
    MAX-ACCESS      read-only
    STATUS          current
    DESCRIPTION     "The value of the object sapOperStatus indicates the
                     operating state of this SAP."
    ::= { sapBaseInfoEntry 7 }

sapIngressQosPolicyId OBJECT-TYPE
    SYNTAX          TSapIngressPolicyID
    MAX-ACCESS      read-create
    STATUS          current
    DESCRIPTION     "The value of the object sapIngressQosPolicyId specifies
                     the row index in the tSapIngressTable corresponding to this
                     ingress QoS policy, or one if no policy is specified.
                     The value 0 is needed for mirror SAPs that
                     cannot have a QoS policy assigned."
    DEFVAL          { 1 }
    ::= { sapBaseInfoEntry 8 }

sapIngressMacFilterId OBJECT-TYPE
    SYNTAX          TFilterID
    MAX-ACCESS      read-create
    STATUS          current
    DESCRIPTION     "The value of the object sapIngressMacFilterId specifies
                     the row index in the tMacFilterTable corresponding to this
                     ingress filter, or zero if no filter is specified."
    DEFVAL          { 0 }
    ::= { sapBaseInfoEntry 9 }

sapIngressIpFilterId OBJECT-TYPE
    SYNTAX          TFilterID
    MAX-ACCESS      read-create
    STATUS          current
    DESCRIPTION     "The value of the object sapIngressIpFilterId specifies the
                     row index in the tIPFilterTable corresponding to this
                     ingress filter, or zero if no filter is specified."
    DEFVAL          { 0 }
    ::= { sapBaseInfoEntry 10 }

sapEgressQosPolicyId OBJECT-TYPE
    SYNTAX          TSapEgressPolicyID
    MAX-ACCESS      read-create
    STATUS          current
    DESCRIPTION     "The row index in the tSapEgressTable
                     corresponding to this egress QoS policy,
                     or one if no policy is specified."
    DEFVAL          { 1 }
    ::= { sapBaseInfoEntry 11 }

sapEgressMacFilterId OBJECT-TYPE
    SYNTAX          TFilterID
    MAX-ACCESS      read-create
    STATUS          current
    DESCRIPTION     "The row index in the tMacFilterTable
                     corresponding to this egress filter,
                     or zero if no filter is specified."
    DEFVAL          { 0 }
    ::= { sapBaseInfoEntry 12 }

sapEgressIpFilterId OBJECT-TYPE
    SYNTAX          TFilterID
    MAX-ACCESS      read-create
    STATUS          current
    DESCRIPTION     "The row index in the tIPFilterTable
                     corresponding to this egress filter,
                     or zero if no filter is specified."
    DEFVAL          { 0 }
    ::= { sapBaseInfoEntry 13 }

sapMirrorStatus OBJECT-TYPE
    SYNTAX          INTEGER {
                        ingress          (1),
                        egress           (2),
                        ingressAndEgress (3),
                        disabled         (4)
                    }
    MAX-ACCESS      read-only
    STATUS          current
    DESCRIPTION     "This object specifies whether traffic
                     mirroring has been enabled on this SAP."
    ::= { sapBaseInfoEntry 14 }

sapIesIfIndex OBJECT-TYPE
    SYNTAX          InterfaceIndexOrZero
    MAX-ACCESS      read-create
    STATUS          current
    DESCRIPTION     "When the value of sapType is 'ies' this
                     object specifies the index of the IES interface
                     where this SAP is defined. The value of this object
                     can be set only when the row is created and cannot
                     be changed while the row status is 'active'. This
                     object is otherwise not significant and should have
                     the value zero."
    ::= { sapBaseInfoEntry 15 }

sapLastMgmtChange OBJECT-TYPE
    SYNTAX          TimeStamp
    MAX-ACCESS      read-only
    STATUS          current
    DESCRIPTION     "The value of sysUpTime at the time of the
                     most recent management-initiated change to
                     this SAP."
    ::= { sapBaseInfoEntry 16 }

sapCollectAcctStats OBJECT-TYPE
    SYNTAX          TruthValue
    MAX-ACCESS      read-create
    STATUS          current
    DESCRIPTION     "When the value of this object is 'true' the agent
                     collects accounting statistics on this SAP."
    DEFVAL          { false }
    ::= { sapBaseInfoEntry 17 }

sapAccountingPolicyId OBJECT-TYPE
    SYNTAX          Unsigned32
    MAX-ACCESS      read-create
    STATUS          current
    DESCRIPTION     "This object specifies the policy to use to collect
                     accounting statistics on this SAP. The value zero
                     indicates that the agent should use the default
                     accounting policy, if one exists."
    DEFVAL          { 0 }
    ::= { sapBaseInfoEntry 18 }

sapVpnId OBJECT-TYPE
    SYNTAX          VpnId
    MAX-ACCESS      read-only
    STATUS          current
    DESCRIPTION     "The VPN ID of the associated service."
    ::= { sapBaseInfoEntry 19 }

sapCustId OBJECT-TYPE
    SYNTAX          TmnxCustId
    MAX-ACCESS      read-only
    STATUS          current
    DESCRIPTION     "The Customer ID of the associated service."
    ::= { sapBaseInfoEntry 20 }

sapCustMultSvcSite OBJECT-TYPE
    SYNTAX          ServObjName
    MAX-ACCESS      read-create
    STATUS          current
    DESCRIPTION     "The value of this object, when not null, indicates
                     the Multi-Service Site this SAP is a member of. This
                     information is used to configure the ingress and
                     egress QoS schedulers for this SAP."
    DEFVAL          { "" }
    ::= { sapBaseInfoEntry 21 }

sapIngressQosSchedulerPolicy OBJECT-TYPE
    SYNTAX          ServObjName
    MAX-ACCESS      read-create
    STATUS          current
    DESCRIPTION     "This object can be set only when sapCustMultSvcSite
                     is null. It indicates the ingress QoS scheduler for
                     this SAP."
    DEFVAL          { "" }
    ::= { sapBaseInfoEntry 22 }

sapEgressQosSchedulerPolicy OBJECT-TYPE
    SYNTAX          ServObjName
    MAX-ACCESS      read-create
    STATUS          current
    DESCRIPTION     "This object can be set only when sapCustMultSvcSite
                     is null. It indicates the egress QoS scheduler for
                     this SAP."
    DEFVAL          { "" }
    ::= { sapBaseInfoEntry 23 }

sapSplitHorizonGrp OBJECT-TYPE
    SYNTAX          ServObjName
    MAX-ACCESS      read-create
    STATUS          current
    DESCRIPTION     "This object specifies the name of the split-horizon
                     group where the SAP belongs to. This object can be
                     set only at the time the row is created. Per default
                     a SAP does not belong to any split-horizon group. The
                     name specified must correspond to an existing split-
                     horizon group in the TLS service where this SAP is
                     defined."
    DEFVAL          { "" }
    ::= { sapBaseInfoEntry 24 }

sapIngressSharedQueuePolicy OBJECT-TYPE
    SYNTAX          ServObjName
    MAX-ACCESS      read-create
    STATUS          current
    DESCRIPTION     "This object indicates the ingress shared queue policy
                     used by this SAP. When the value of this object is null
                     it means that the SAP will use individual ingress QoS
                     queues, instead of the shared ones."
    DEFVAL          { "" }
    ::= { sapBaseInfoEntry 25 }

sapIngressMatchQinQDot1PBits OBJECT-TYPE
    SYNTAX          INTEGER {
                        default (1),
                        top     (2),
                        bottom  (3)
                    }
    MAX-ACCESS      read-create
    STATUS          current
    DESCRIPTION     "This object applies only to SAP's defined on a port
                     configured for qinq service encapsulation. It indicates
                     which 802.1P bits will be used to match a QoS or a MAC
                     filter policy when a double-tagged frame is received on
                     this SAP."
    DEFVAL          { default }
    ::= { sapBaseInfoEntry 26 }

sapOperFlags OBJECT-TYPE
    SYNTAX          BITS {
                        sapAdminDown         (0),  -- SAP is admin down
                        svcAdminDown         (1),  -- Service is admin down
                        iesIfAdminDown       (2),  -- IP interface is admin down
                                                   -- (IES and VPRN only)
                        portOperDown         (3),  -- Access port is oper down
                        portMtuTooSmall      (4),  -- Access port's MTU is less 
                                                   -- than Service MTU
                        l2OperDown           (5),  -- L2 PVC/PVP is oper down 
                                                   -- (FR and ATM only)
                        ingressQosMismatch   (6),  -- Mismatch between ingress 
                                                   -- QoS and Scheduler policies
                        egressQosMismatch    (7),  -- Mismatch between egress 
                                                   -- QoS and Scheduler policies
                        relearnLimitExceeded (8),  -- MAC relearn limit was 
                                                   -- exceeded (TLS only)
                        recProtSrcMac        (9),  -- Received a packet with a 
                                                   -- protected source MAC 
                                                   -- (TLS only)
                        subIfAdminDown       (10), -- Subscriber interface is 
                                                   -- admin down (group-
                                                   -- interface SAP only)
                        sapIpipeNoCeIpAddr   (11), -- CE IP Address not 
                                                   -- configured for Ipipe SAP 
                                                   -- (IPIPE SAP only)
                        sapTodResourceUnavail (12),-- SAP with ToD had 
                                                   -- insufficient resources
                                                   -- at boot time and got
                                                   -- default policies.
                        sapTodMssResourceUnavail (13), -- MSS of this SAP uses
                                                       -- ToD and due to
                                                       -- insufficient resources
                                                       -- at boot time got
                                                       -- default scheduler
                                                       -- policies.
                        sapParamMismatch      (14),    -- Service specific local
                                                       -- parameter mismatch
                        sapCemNoEcidOrMacAddr (15),    -- ECID or MAC address
                                                       -- not configured (CEM
                                                       -- SAP only)
                        sapStandbyForMcRing   (16),    -- mc-ring keeps this SAP
                                                       -- standby for the
                                                       -- corresponding SAP on
                                                       -- peer
                        sapSvcMtuTooSmall     (17),    -- Service MTU is less
                                                       -- than the SAP payload
                        ingressNamedPoolMismatch (18), -- Invalid named-pool
                                                       -- on the ingress side
                        egressNamedPoolMismatch  (19), -- Invalid named-pool
                                                       -- on the egress side
                        ipMirrorNoMacAddr     (20),    -- No MAC Address
                                                       -- configured for the
                                                       -- ip-mirror
                        sapEpipeNoRingNode (21),-- No TIMETRA-MC-REDUNDANCY-MIB
                                                -- ::tmnxMcEpipeSapEntry object
                                                -- configured for Epipe SAP
                                                -- (EPIPE SAP only)
                        mcStandby          (22),-- indicates the SAP is standby
                                        -- because of a mutli-chassis protocol
                        mhStandby          (23),-- indicates the SAP is standby
                                        -- because of a BGP multi-home protocol
                        oamDownMepFault (24), -- ETH-CFM down MEP fault detected
                        oamUpMepFault   (25),  -- ETH-CFM up MEP fault detected 
                        ethTunTagMisconfig (26),-- missing tag(s) for Eth-Tunnel
                                                -- SAP
                        ingressPolicerMismatch (27),-- indicate ingress policer 
                                     -- is parented to non-existent arbiter
                        egressPolicerMismatch (28),  -- indicate egress policer 
                                     -- is parented to non-existent arbiter
                        sapTlsNoRingNode (29),-- No TIMETRA-MC-REDUNDANCY-MIB
                                                -- ::tmnxMcTlsSapEntry object
                                                -- configured for TLS SAP
                                                -- (VPLS SAP only)
                        ethRingPathBlocked (30), -- indicates eth-ring path is
                                                 -- blocked.
                        oamTunnelMepFault (31),  -- indicates eth-cfm Tunnel
                                                 -- MEP fault detected.
                        operGrpDown (32), -- indicates operational-group is down
                        portBouncing (33)  -- indicates port is oper down and bouncing.
                    }
    MAX-ACCESS      read-only
    STATUS          current
    DESCRIPTION     "This object specifies all the conditions that
                     affect the operating status of this SAP.

                     The bit values are:

             sapAdminDown           (0) - SAP is admin down.
             svcAdminDown           (1) - Service is admin down.
             iesIfAdminDown         (2) - IP interface is admin down (IES and
                                          VPRN only).
             portOperDown           (3) - Access port is oper down.
             portMtuTooSmall        (4) - Access port's MTU is < Service MTU
             l2OperDown             (5) - L2 PVC/PVP is oper down (FR and ATM
                                          only).
             ingressQosMismatch     (6) - Mismatch between ingress QoS and
                                          Scheduler policies.
             egressQosMismatch      (7) - Mismatch between egress QoS and
                                          Scheduler policies.
             relearnLimitExceeded   (8) - MAC relearn limit was exceeded (TLS
                                          only).
             recProtSrcMac          (9) - Received a packet with a protected
                                          source MAC (TLS only).
             subIfAdminDown        (10) - Subscriber interface is admin down
                                          (group-interface SAP only).
             sapIpipeNoCeIpAddr    (11) - CE IP Address not configured for Ipipe
                                          SAP (IPIPE SAP only).
             sapTodResourceUnavail (12) - SAP with ToD had insufficient
                                          resources at boot time and got default
                                          policies.
             sapTodMssResourceUnavail (13)
                                        - MSS of this SAP uses ToD and due to
                                          insufficient resources at boot time
                                          got default scheduler policies.
             sapParamMismatch      (14) - Service specific local parameter
                                          mismatch.
             sapCemNoEcidOrMacAddr (15) - ECID or MAC address not configured
                                          (CEM SAP only).
             sapStandbyForMcRing   (16) - mc-ring keeps this SAP standby for the
                                          corresponding SAP on peer.
             sapSvcMtuTooSmall     (17) - Service MTU is < SAP payload.
             ingressNamedPoolMismatch (18)
                                        - Invalid named-pool on the ingress
                                          side.
             egressNamedPoolMismatch (19)
                                        - Invalid named-pool on the egress side.
             ipMirrorNoMacAddr     (20) - No MAC Address configured for the
                                          ip-mirror.
             sapEpipeNoRingNode    (21) - No TIMETRA-MC-REDUNDANCY-MIB
                                          ::tmnxMcEpipeSapEntry object
                                          configured for Epipe SAP (EPIPE SAP
                                          only).
             mcStandby             (22) - indicates the SAP is standby because
                                          of a mutli-chassis protocol.
             mhStandby             (23) - indicates the SAP is standby because
                                          of a BGP multi-home protocol.
             oamDownMepFault       (24) - ETH-CFM down MEP fault detected.
             oamUpMepFault         (25) - ETH-CFM up MEP fault detected.
             ethTunTagMisconfig    (26) - Missing Eth-tunnel SAP tag(s).
             ingressPolicerMismatch (27)- indicate ingress policer
                                        - is parented to non-existent arbiter
             egressPolicerMismatch (28) - indicate egress policer
                                        - is parented to non-existent arbiter.
             sapTlsNoRingNode      (29) - No TIMETRA-MC-REDUNDANCY-MIB
                                          ::tmnxMcTlsSapEntry object
                                          configured for TLS SAP (VPLS SAP
                                          only).
             ethRingPathBlocked (30)    - indicates eth-ring path is
                                          blocked.
             oamTunnelMepFault (31)     - ETH-CFM Tunnel MEP fault detected.
             operGrpDown (32)           - indicates operational-group is down.
             portBouncing (33)          - indicates port is oper down and bouncing."

    ::= { sapBaseInfoEntry 27 }

sapLastStatusChange OBJECT-TYPE
    SYNTAX          TimeStamp
    MAX-ACCESS      read-only
    STATUS          current
    DESCRIPTION     "The value of sysUpTime at the time of the
                     most recent operating status change to this
                     SAP."
    ::= { sapBaseInfoEntry 28 }

sapAntiSpoofing OBJECT-TYPE
    SYNTAX          INTEGER {
                        disabled            (0),
                        sourceIpAddr        (1),
                        sourceMacAddr       (2),
                        sourceIpAndMacAddr  (3),
                        nextHopIpAndMacAddr (4)
                    }
    MAX-ACCESS      read-create
    STATUS          current
    DESCRIPTION     "The value of the object sapAntiSpoofing specifies
                     the type of anti-spoof filtering applicable on this SAP."
    DEFVAL { disabled }
    ::= { sapBaseInfoEntry 29 }

sapIngressIpv6FilterId OBJECT-TYPE
    SYNTAX          TFilterID
    MAX-ACCESS      read-create
    STATUS          current
    DESCRIPTION     "The value of the object sapIngressIpv6FilterId specifies
                     the row index in the tIPv6FilterTable corresponding to
                     this ingress ipv6 filter, or zero if no ipv6 filter is
                     specified."
    DEFVAL          { 0 }
    ::= { sapBaseInfoEntry 30 }

sapEgressIpv6FilterId OBJECT-TYPE
    SYNTAX          TFilterID
    MAX-ACCESS      read-create
    STATUS          current
    DESCRIPTION     "The value of the object sapEgressIpv6FilterId specifies
                     the row index in the tIPv6FilterTable corresponding to
                     this egress ipv6 filter, or zero if no ipv6 filter is
                     specified."
    DEFVAL          { 0 }
    ::= { sapBaseInfoEntry 31 }

sapTodSuite OBJECT-TYPE
    SYNTAX          TNamedItemOrEmpty
    MAX-ACCESS      read-create
    STATUS          current
    DESCRIPTION     "The value of the object sapTodSuite specifies the Time of
                     Day (ToD) suite to be applied on this SAP.
                     An empty string indicates that no ToD suite is applied
                     on this SAP.
                     A set request will only be allowed, if the indicated suite
                     is defined in TIMETRA-SCHEDULER-MIB::tmnxTodSuiteTable."
    DEFVAL          { ''H }
    ::= { sapBaseInfoEntry 32 }

sapIngUseMultipointShared       OBJECT-TYPE
    SYNTAX          TruthValue
    MAX-ACCESS      read-create
    STATUS          current
    DESCRIPTION     "When the value of sapIngressSharedQueuePolicy is not null,
                     the value of the object sapIngUseMultipointShared
                     specifies whether this SAP uses the multipoint-shared
                     queues of the shared policy."
    DEFVAL          { false }
    ::= { sapBaseInfoEntry 33 }
    
sapEgressQinQMarkTopOnly OBJECT-TYPE
    SYNTAX          TruthValue
    MAX-ACCESS      read-create
    STATUS          current
    DESCRIPTION     "When the encapsulation type of the access port where
                     this SAP is defined is qinq, the value of the object
                     sapEgressQinQMarkTopOnly specifies which P-bits to mark
                     during packet egress. When the value is false both set
                     of P-bits are marked. When the value is true, only the
                     P-bits in the top Q-tag are marked."
    DEFVAL          { false }
    ::= { sapBaseInfoEntry 34 }

sapEgressAggRateLimit   OBJECT-TYPE
    SYNTAX          TPortSchedulerAggRateLimitPIR
    UNITS           "kbps"
    MAX-ACCESS      read-create
    STATUS          obsolete
    DESCRIPTION     "The value of the object sapEgressAggRateLimit
                     specifies the maximum total rate of all egress queues for
                     this SAP. The value '-1' means that there
                     is no limit.
                     
                     This object is obsoleted in 13.0 release and replaced by 
                     sapEgressAggRateLmt."
    DEFVAL          { -1 }
    ::= { sapBaseInfoEntry 35 }

sapEndPoint         OBJECT-TYPE
    SYNTAX          ServObjName
    MAX-ACCESS      read-create
    STATUS          current
    DESCRIPTION     "The value of the object sapEndPoint specifies the service
                     endpoint to which this SAP is attached. The svcId of the 
                     SAP MUST match the svcId of the service endpoint."
    DEFVAL          { "" }
    ::= { sapBaseInfoEntry 36 }

sapIngressVlanTranslation OBJECT-TYPE
    SYNTAX          INTEGER {
                        none        (1),
                        vlanId      (2),
                        copyOuter   (3)
                        }
    MAX-ACCESS      read-create
    STATUS          current
    DESCRIPTION     "The value of sapIngressVlanTranslation specifies the 
                     desired Ingress Vlan Translation.
                     
                     A value of 'vlanId' specifies that the value of
                     sapIngressVlanTranslationId is to be used to overwrite
                     the preserved VLAN id in the packet.

                     A value of 'copyOuter' specifies that the outer VLAN
                     id should be used to overwrite the preserved VLAN id in
                     the packet.

                     An 'inconsistentValue' error is returned when an attempt
                     is made to set the value of sapIngressVlanTranslation
                     to 'vlanId' and sapIngressVlanTranslationId is
                     set to '-1'."
    DEFVAL          { none }
    ::= { sapBaseInfoEntry 37 }

sapIngressVlanTranslationId OBJECT-TYPE
    SYNTAX          Integer32  (-1|0..4094)
    MAX-ACCESS      read-create
    STATUS          current
    DESCRIPTION     "The value of sapIngressVlanTranslationId specifies the
                     VLAN id to be used to overwrite the preserved VLAN id
                     in the packet.
                     
                     An 'inconsistentValue' error is returned when an
                     attempt is made to set the value of
                     sapIngressVlanTranslationId to other than '-1' and
                     sapIngressVlanTranslation is not set to 'vlanId'."
    DEFVAL          { -1 }
    ::= { sapBaseInfoEntry 38 }

sapSubType          OBJECT-TYPE
    SYNTAX          INTEGER {
                        regular  (0),
                        capture  (1),
                        managed  (2),
                        video    (3),
                        internal (4)
                    }
    MAX-ACCESS      read-create
    STATUS          current
    DESCRIPTION     "The value of the object sapSubType indicates the
                     sub-type for this SAP.

                     A value of 'regular' indicates a standard SAP.

                     A value of 'capture' specifies a capturing SAP
                     in which triggering packets will be sent to the CPM.
                     Non-triggering packets captured by the 'capture' SAP
                     will be dropped.

                     A value of 'managed' indicates a managed SAP which
                     was created dynamically after receiving triggering
                     packets on a SAP with a sapSubType value of
                     'capture'. Entries with a value of 'managed'
                     are not user editable and are not maintained
                     in the configuration file.

                     A value of 'video' indicates a video SAP which
                     terminates on a video SAP. Entries with a value of
                     'video' are not user editable and are not maintained 
                     in the configuration file.

                     A value of 'internal' indicates an internal SAP which
                     was created by the system. Entries with a value of
                     'internal' are not user editable and are not
                     maintained in the configuration file.

                     Whereas any of the five values may be returned in
                     in response to an SNMP GET request, only two values
                     may be specified in an SNMP SET request: 'regular'
                     and 'capture'. An attempt to specify a value
                     of 'managed', 'video' or 'internal' in an SNMP SET
                     request will fail with an error of 'inconsistentValue'.

                     The value of this object cannot be changed after creation."
    DEFVAL          { regular }
    ::= { sapBaseInfoEntry 39 }

sapCpmProtPolicyId  OBJECT-TYPE
    SYNTAX          TCpmProtPolicyID
    MAX-ACCESS      read-create
    STATUS          current
    DESCRIPTION     
        "The value of sapCpmProtPolicyId associates a CPM Protection
         policy with a SAP.

         A value of zero (0) specifies that no CPM Protection policy
         is associated with this SAP.

         A value of 254 specifies that the default CPM Protection 
         policy is associated with this SAP.

         If no value for sapCpmProtPolicyId is specified when the 
         sapBaseInfoEntry is created, the system assigns a default
         value as follows: if the system creates a corresponding
         entry in the sapSubMgmtInfoTable, the default value is
         254; otherwise, the default value is 'zero'. This means
         that all SAP's that support Enhanced Subscriber Management
         get a default value of 254.

         If a SAP would get a default value of 254, it is not
         allowed to set the value of sapCpmProtPolicyId to 'zero'.

         If a SAP would get a default value of 'zero', it is not
         allowed to modify the value of sapCpmProtPolicyId.

         This object is not supported on 7710, where the value of
         TIMETRA-CHASSIS-MIB::tmnxChassisType is '7' or '9'."
    ::= { sapBaseInfoEntry 40 }

sapCpmProtMonitorMac OBJECT-TYPE
    SYNTAX          TruthValue
    MAX-ACCESS      read-create
    STATUS          current
    DESCRIPTION
        "The value of sapCpmProtMonitorMac specifies whether or not to apply the
         tmnxCpmProtPolPerSrcRateLimit of this SAP's CPM Protection policy to
         packets served by the SAP, on a per source MAC address basis.

         For example, suppose sapCpmProtMonitorMac is 'true', and this SAP's
         sapCpmProtPolicyId points to a policy table row with
         tmnxCpmProtPolPerSrcRateLimit set to 100 packets/second.  Suppose two
         source MAC addresses each send 150 packets/second to this SAP.  Approx.
         50 packets/second from each source will be discarded.

         If the value of sapCpmProtPolicyId is equal to zero, the value of
         sapCpmProtMonitorMac is irrelevant and will be ignored.

         At most one of the following options can be enabled on this SAP:
           1.  sapCpmProtMonitorMac,
           2.  The sapCpmProtEthCfmMonitorFlags option 'ethCfmMonitor(0)',
           3.  sapCpmProtMonitorIP.

         This object is not supported on 7710, where the value of
         TIMETRA-CHASSIS-MIB::tmnxChassisType is '7' or '9'."
    DEFVAL          { false }
    ::= { sapBaseInfoEntry 41 }

sapEgressFrameBasedAccounting OBJECT-TYPE
    SYNTAX       TruthValue
    MAX-ACCESS   read-create
    STATUS       current
    DESCRIPTION     "The value of sapEgressFrameBasedAccounting specifies
                     whether to use frame-based accounting when evaluating
                     sapEgressAggRateLmt for all egress queues for this SAP.

                     If the value is 'false', the default packet-based
                     accounting method will be used."
    DEFVAL { false }
    ::= { sapBaseInfoEntry 42 }

sapIngressAggRateLimit   OBJECT-TYPE
    SYNTAX          TPortSchedulerPIR
    UNITS           "kbps"
    MAX-ACCESS      read-create
    STATUS          obsolete
    DESCRIPTION     "The value of the object sapIngressAggRateLimit
                     specifies the maximum total rate of all ingress queues for
                     this SAP. The value '-1' means that there
                     is no limit.

                     This object is obsoleted in 10.0 Release."
    DEFVAL          { -1 }
    ::= { sapBaseInfoEntry 43 }

sapEgressHsmdaShaperOverride   OBJECT-TYPE
    SYNTAX          TNamedItemOrEmpty
    MAX-ACCESS      read-create
    STATUS          current
    DESCRIPTION     "The value of the object sapEgressHsmdaShaperOverride
                     specifies the name of the secondary shaper for this SAP.
                     The value must correspond to an entry in the
                     tmnxPortEgrShaperTable.  If the empty string is specified,
                     the default secondary shaper will be used."
    DEFVAL          { "" }
    ::= { sapBaseInfoEntry 44 }

sapIngressHsmdaPacketOffOvr        OBJECT-TYPE
    SYNTAX      TIngHsmdaPerPacketOffsetOvr
    UNITS       "bytes"
    MAX-ACCESS  read-create
    STATUS      obsolete
    DESCRIPTION     "The value of sapIngressHsmdaPacketOffOvr specifies the
                     value, in bytes, of the adjustment to make to the size of
                     each packet for HSMDA queue accounting on ingress.

                     This object is obsoleted in 10.0 Release."                     
    DEFVAL { -128 }
    ::= { sapBaseInfoEntry 45 }

sapEgressHsmdaPacketOffOverride        OBJECT-TYPE
    SYNTAX      TEgrHsmdaPerPacketOffsetOvr
    UNITS       "bytes"
    MAX-ACCESS  read-create
    STATUS      current
    DESCRIPTION     "The value of sapEgressHsmdaPacketOffOverride specifies the
                     value, in bytes, of the adjustment to make to the size of
                     each packet for HSMDA queue accounting on ingress."
    DEFVAL { -128 }
    ::= { sapBaseInfoEntry 46 }

sapCallingStationId OBJECT-TYPE
    SYNTAX          DisplayString (SIZE (0..64))
    MAX-ACCESS      read-create
    STATUS          current
    DESCRIPTION     "The value of sapCallingStationId specifies the
                     calling-station-id to be included in all RADIUS
                     authentication and accounting requests if configured
                     to be included in the corresponding RADIUS authentication
                     or accounting policy.

                     If the empty string is specified, no calling-station-id
                     will be included."
    DEFVAL { "" }
    ::= { sapBaseInfoEntry 47 }

sapIsaAaApplicationProfile OBJECT-TYPE
    SYNTAX          ServObjName
    MAX-ACCESS      read-create
    STATUS          current
    DESCRIPTION     "The value of sapIsaAaApplicationProfile specifies
                     the ISA-AA application profile for this sap. The
                     specified application profile needs to exist in the
                     TIMETRA-BSX-NG-MIB::tmnxBsxAppProfTable."
    DEFVAL          { "" }
    ::= { sapBaseInfoEntry  48 }

sapIngPolicerPolicy OBJECT-TYPE
    SYNTAX      TNamedItemOrEmpty
    MAX-ACCESS  read-create
    STATUS      current
    DESCRIPTION     "The value of sapIngPolicerPolicy specifies the ingress
                     policer control policy applicable to this subscriber
                     profile."
    DEFVAL { ''H }
    ::= { sapBaseInfoEntry 49 }

sapEgrPolicerPolicy OBJECT-TYPE
    SYNTAX      TNamedItemOrEmpty
    MAX-ACCESS  read-create
    STATUS      current
    DESCRIPTION     "The value of sapEgrPolicerPolicy specifies the egress
                     policer control policy applicable to this subscriber
                     profile."
    DEFVAL { ''H }
    ::= { sapBaseInfoEntry 50 }

sapTmplUsed OBJECT-TYPE
    SYNTAX      TNamedItemOrEmpty
    MAX-ACCESS  read-only
    STATUS      current
    DESCRIPTION     "The value of sapTmplUsed indicates the name of the
                     sap-template used to create this sap.

                     A value of empty-string indicates that this sap was not
                     created using a sap-template."
    ::= { sapBaseInfoEntry 51 }

sapEthRingIndex  OBJECT-TYPE
    SYNTAX          Unsigned32
    MAX-ACCESS      read-create
    STATUS          current
    DESCRIPTION     "The value of sapEthRingIndex specifies the Ethernet Ring
                     associated with this SAP.

                     This object, if required, MUST be configured during the
                     row creation of the sapBaseInfoTable row, and MUST
                     reference an existing row in
                     TIMETRA-ETH-RING-MIB::tmnxEthRingConfigTable.

                     The value zero, the default value, specifies there is no
                     Ethernet Ring associated with this SAP.

                     This object can not be changed once set; the SAP MUST be
                     destroyed and re-created to change the sapEthRingIndex
                     object."
    DEFVAL           { 0 }
    ::= { sapBaseInfoEntry 52 }

sapIngressFlowspec   OBJECT-TYPE
    SYNTAX      TruthValue
    MAX-ACCESS  read-create
    STATUS      current
    DESCRIPTION
        "The value of sapIngressFlowspec specifies whether IPv4 ingress Flowspec 
         is enabled for this sap."
    DEFVAL { false }
    ::= { sapBaseInfoEntry 53 }

sapCpmProtEthCfmMonitorFlags   OBJECT-TYPE
    SYNTAX      BITS {
        ethCfmMonitor(0),
        ethCfmMonitorAggregate(1),
        ethCfmMonitorCommittedAccessRate(2)
    }
    MAX-ACCESS  read-create
    STATUS      current
    DESCRIPTION
        "The value of sapCpmProtEthCfmMonitorFlags specifies whether or not to
         apply rate limiting (using the tmnxCpmProtEthCfmPolTable configuration)
         to Ethernet Connectivity Fault Management (Eth-CFM) packets served by
         the SAP.  Two associated options are also specified.

         Five combinations of flag values are supported, as shown in the
         following table.

         Flag                                    Value (0=Disabled, 1=Enabled)
         -------------------------------------   -----------------------------
         'ethCfmMonitor(0)'                      0   0   0   0   1   1   1   1
         'ethCfmMonitorAggregate(1)'             0   0   1   1   0   0   1   1
         'ethCfmMonitorCommittedAccessRate(2)'   0   1   0   1   0   1   0   1
         -------------------------------------   -----------------------------
         Supported Combination?                  Y   N   N   N   Y   Y   Y   Y

         If 'ethCfmMonitor(0)' is disabled, Eth-CFM rate limiting is disabled on
         this SAP.

         If 'ethCfmMonitor(0)' is enabled, Eth-CFM rate limiting is enabled on
         this SAP.  Excess packets are discarded.  The configured information
         used to perform the Eth-CFM rate limiting (e.g. the rate limit(s))
         resides in the tmnxCpmProtEthCfmPolTable row(s) indexed by the SAP's
         sapCpmProtPolicyId.

         At most one of the following options can be enabled on this SAP:
           1.  sapCpmProtMonitorMac,
           2.  The sapCpmProtEthCfmMonitorFlags option 'ethCfmMonitor(0)',
           3.  sapCpmProtMonitorIP.

         The flags 'ethCfmMonitorAggregate(1)' and
         'ethCfmMonitorCommittedAccessRate(2)' adjust the behavior of Eth-CFM
         rate limiting.  Therefore, they are only significant if Eth-CFM rate
         limiting is enabled (i.e. when 'ethCfmMonitor(0)' is enabled).  The
         remainder of this DESCRIPTION assumes 'ethCfmMonitor(0)' is enabled.

         If 'ethCfmMonitorAggregate(1)' is disabled, the applicable Eth-CFM
         packet rate limit (tmnxCpmProtEthCfmPolRateLimit) applies per peer
         (i.e. on a source MAC address basis).  For example, if the SAP's rate
         limit for all Eth-CFM packets is 100 packets/sec, and two peers are
         served by the SAP, then 100 Eth-CFM packets/sec from each peer is
         within the limit.

         If 'ethCfmMonitorAggregate(1)' is enabled, the applicable Eth-CFM
         packet rate limit (tmnxCpmProtEthCfmPolRateLimit) applies to the
         aggregated traffic flow.  For example, if the SAP's rate limit for all
         Eth-CFM packets is 100 packets/sec, and two peers are served by this
         SAP, then the combined rate of the two peers cannot exceed 100
         packets/sec.

         'ethCfmMonitorCommittedAccessRate(2)' controls the interaction
         between two features:  Eth-CFM rate limiting, and overall rate limiting
         (as configured using tmnxCpmProtPolOverallRateLimit).

         If 'ethCfmMonitorCommittedAccessRate(2)' is disabled, an Eth-CFM
         packet is subjected to two rate limits, in the following order.
         a) The applicable tmnxCpmProtEthCfmPolRateLimit is applied, as
            described above.  If the packet exceeds the limit, it is discarded.
            Otherwise...
         b) The SAP's tmnxCpmProtPolOverallRateLimit (which is applied
            to Eth-CFM packets, and the other rate limited packet types) is
            applied.

         If 'ethCfmMonitorCommittedAccessRate(2)' is enabled, an Eth-CFM packet
         is subjected to one rate limit:  the applicable
         tmnxCpmProtEthCfmPolRateLimit, as described above.  Eth-CFM packets
         are neither counted nor discarded when performing the
         tmnxCpmProtPolOverallRateLimit rate limiting."
    DEFVAL { {} }
    ::= { sapBaseInfoEntry 54 }

sapTransitIpPolicyId     OBJECT-TYPE
    SYNTAX      TmnxBsxTransitIpPolicyIdOrZero
    MAX-ACCESS  read-create
    STATUS      current
    DESCRIPTION
        "The value of sapTransitIpPolicyId specifies the transit IP 
         policy to be associated with this SAP. The value must either
         be '0' indicating an invalid transit IP policy or the specified
         transit IP policy needs to exist in the 
         TIMETRA-BSX-NG-MIB::tmnxBsxTransitIpPolicyTable.
        
         At most one of sapTransitIpPolicyId and sapTransitPrefixPolicyId can
         be non-zero."
    DEFVAL { 0 }
    ::= { sapBaseInfoEntry 55 }

sapOperGrp OBJECT-TYPE
    SYNTAX          TNamedItemOrEmpty
    MAX-ACCESS      read-create
    STATUS          current
    DESCRIPTION     "The value of the sapOperGrp specifies the
                     Operational-Group identifier associated with this SAP.

                     An 'inconsistentValue' error is returned when
                     both sapOperGrp and sapMonitorOperGrp are set together
                     and atleast one of them to a non-default value."
    DEFVAL { "" }
    ::= { sapBaseInfoEntry 56 }

sapMonitorOperGrp OBJECT-TYPE
    SYNTAX          TNamedItemOrEmpty
    MAX-ACCESS      read-create
    STATUS          current
    DESCRIPTION     "The value of the sapMonitorOperGrp specifies the
                     Operational-Group identifier which will affect the state
                     of this SAP.

                     An 'inconsistentValue' error is returned when
                     both sapOperGrp and sapMonitorOperGrp are set together
                     and atleast one of them to a non-default value."
    DEFVAL { "" }
    ::= { sapBaseInfoEntry 57 }

sapEgressHsmdaWrrPolicyOvr OBJECT-TYPE
    SYNTAX          TNamedItemOrEmpty
    MAX-ACCESS      read-create
    STATUS          current
    DESCRIPTION     "The value of the sapEgressHsmdaWrrPolicyOvr specifies the 
                     egress hsmda weighted round-robin policy override for this
                     SAP. When no policy is given, the hsmda weighted 
                     round-robin policy specified in the sap-egress policy is 
                     honored. When a valid policy is given, it is used instead 
                     of the hsmda weighted round-robin policy given in the 
                     sap-egress policy."
    DEFVAL { "" }
    ::= { sapBaseInfoEntry 58 }

sapTransitPrefixPolicyId      OBJECT-TYPE
    SYNTAX      TmnxBsxTransPrefPolicyIdOrZero
    MAX-ACCESS  read-create
    STATUS      current
    DESCRIPTION
        "The value of sapTransitPrefixPolicyId specifies the transit prefix 
         policy to be associated with this SAP. The value must either
         be '0' indicating an invalid transit prefix policy or the specified
         transit prefix policy needs to exist in the 
         TIMETRA-BSX-NG-MIB::tmnxBsxTransPrefPolicyTable.
         
         At most one of sapTransitIpPolicyId and sapTransitPrefixPolicyId can
         be non-zero."
    DEFVAL { 0 }
    ::= { sapBaseInfoEntry 59 }

sapCpmProtMonitorIP OBJECT-TYPE
    SYNTAX          TruthValue
    MAX-ACCESS      read-create
    STATUS          current
    DESCRIPTION
        "The value of sapCpmProtMonitorIP specifies whether or not to apply the
         tmnxCpmProtPolPerSrcRateLimit of this SAP's CPM Protection policy to
         IPv4 DHCP packets served by the SAP, on a per source IP address basis.

         For example, suppose sapCpmProtMonitorIP is 'true', and this SAP's
         sapCpmProtPolicyId points to a policy table row with
         tmnxCpmProtPolPerSrcRateLimit set to 100 packets/second.  Suppose two
         source IP addresses (e.g. 138.120.141.173 and 138.120.141.174)
         each send 150 DHCP packets/second to this SAP.  Approx. 50 DCHP
         packets/second from each source will be discarded.

         If the value of sapCpmProtPolicyId is equal to zero, the value of
         sapCpmProtMonitorIP is irrelevant and will be ignored.

         At most one of the following options can be enabled on this SAP:
           1.  sapCpmProtMonitorMac,
           2.  The sapCpmProtEthCfmMonitorFlags option 'ethCfmMonitor(0)',
           3.  sapCpmProtMonitorIP."
    DEFVAL { false }
    ::= { sapBaseInfoEntry 60 }

sapHostsAdminState  OBJECT-TYPE
    SYNTAX          ServiceAdminStatus
    MAX-ACCESS      read-create
    STATUS          current
    DESCRIPTION     "The value of the object sapHostsAdminState
                     specifies the administrative state of all hosts on this SAP.
                     If set to 'down' no dynamic subscriber hosts can be created,
                     and any active dynamic host on the SAP will be removed."
    DEFVAL          { up }
    ::= { sapBaseInfoEntry 61 }

sapHostLockoutPolicy OBJECT-TYPE
    SYNTAX          TNamedItemOrEmpty
    MAX-ACCESS      read-create
    STATUS          current
    DESCRIPTION     "The value of sapHostLockoutPolicy specifies the
                     Host Lockout Policy for this SAP."
    DEFVAL { "" }
    ::= { sapBaseInfoEntry 62 }

sapAarpId OBJECT-TYPE
    SYNTAX          TmnxBsxAarpIdOrZero
    MAX-ACCESS      read-create
    STATUS          current
    DESCRIPTION     "The value of sapAarpId specifies the AA Redundancy
                     Protocol (AARP) instance associated with this SAP.
                     If set to 0, no AARP instance is associated with 
                     this SAP."
    DEFVAL          { 0 }
    ::= { sapBaseInfoEntry 63 }

sapIngressFPQGrp OBJECT-TYPE
    SYNTAX          TNamedItemOrEmpty
    MAX-ACCESS      read-create
    STATUS          current
    DESCRIPTION     "The value of sapIngressFPQGrp specifies the
                     forwarding-plane queue group Policy for this SAP.
                    
                     This object must be set along with 
                     sapIngressFPQGrpInstanceId object.

                     An 'inconsistentValue' error is returned if 
                     sapIngressFPQGrp is set to a non-default value and an entry
                     corresponding to tmnxFPNum to which this SAP belongs does
                     not exist in  tmnxFPAccIngQGrpTable."
    DEFVAL { "" }
    ::= { sapBaseInfoEntry 64 }

sapIngressFPQGrpInstanceId  OBJECT-TYPE
    SYNTAX          TQosQGrpInstanceIDorZero
    MAX-ACCESS      read-create
    STATUS          current
    DESCRIPTION     "The value of sapIngressFPQGrpInstanceId specifies the 
                     instance of the forwarding-plane ingress Queue Group for
                     this SAP.

                     This object must be set along with sapIngressFPQGrp object.
                     
                     An 'inconsistentValue' error is returned if 
                     sapIngressFPQGrp is set to a non-default value and an entry
                     corresponding to tmnxFPNum to which this SAP belongs does
                     not exist in  tmnxFPAccIngQGrpTable."
    DEFVAL           { 0 }
    ::= { sapBaseInfoEntry 65 }

sapAarpServRefType   OBJECT-TYPE
    SYNTAX          TmnxBsxAarpServiceRefType
    MAX-ACCESS      read-create
    STATUS          current
    DESCRIPTION     "The value of sapAarpServRefType specifies the role of
                     the SAP referenced by the AA Redundancy Protocol (AARP) 
                     instance identified by sapAarpId. If sapAarpId 
                     is the invalid AARP instance '0', then the 
                     service reference type is 'none(0)'."
    DEFVAL          { none }
    ::= { sapBaseInfoEntry 66 }

sapSiteName OBJECT-TYPE
    SYNTAX          TNamedItemOrEmpty
    MAX-ACCESS      read-only
    STATUS          current
    DESCRIPTION     "The value of sapSiteName indicates the site-name
                     associated with this SAP."
    ::= { sapBaseInfoEntry 67 }

sapIgnoreOperDown OBJECT-TYPE
    SYNTAX          TruthValue
    MAX-ACCESS      read-create
    STATUS          current
    DESCRIPTION
        "The value of sapIgnoreOperDown specifiy whether service will ignore
         when sap is operationally down."
    DEFVAL          { false }
    ::= { sapBaseInfoEntry 68 }

sapLagLinkMapProfile OBJECT-TYPE
    SYNTAX          TmnxLinkMapProfileIdOrZero
    MAX-ACCESS      read-create
    STATUS          current
    DESCRIPTION
        "The value of sapLagLinkMapProfile specifies the LAG link map profile
         identifier associated with this SAP."
    DEFVAL          { 0 }
    ::= { sapBaseInfoEntry 69 }

sapIngressIPv6Flowspec   OBJECT-TYPE
    SYNTAX      TruthValue
    MAX-ACCESS  read-create
    STATUS      current
    DESCRIPTION
        "The value of sapIngressIPv6Flowspec specifies whether IPv6 ingress
         Flowspec is enabled for this sap."
    DEFVAL { false }
    ::= { sapBaseInfoEntry 70 }

sapEgressPortQGrp OBJECT-TYPE
    SYNTAX          TNamedItemOrEmpty
    MAX-ACCESS      read-create
    STATUS          current
    DESCRIPTION      
        "The value of sapEgressPortQGrp specifies the egress access port
         queue-group policy for this SAP. This object must be set along with
         sapEgressPortQGrpInstanceId object. 
 
         An 'inconsistentValue' error is returned if sapEgressPortQGrp and 
         sapEgressPortQGrpInstanceId are set to non-default values and an
         entry in tmnxPortPortID to which this SAP belongs does not exist
         in tPortAccEgrQGrpTable."
    DEFVAL { ''H }
    ::= { sapBaseInfoEntry 71 }
 
sapEgressPortQGrpInstanceId OBJECT-TYPE
    SYNTAX          TQosQGrpInstanceIDorZero
    MAX-ACCESS      read-create
    STATUS          current
    DESCRIPTION     
        "The value of sapEgressPortQGrpInstanceId specifies the egress access
         port queue-group policy for this SAP. This object must be set along 
         with sapEgressPortQGrp object.
                     
         An 'inconsistentValue' error is returned if sapEgressPortQGrp and
         sapEgressPortQGrpInstanceId are set to  non-default values and an
         entry in tmnxPortPortID to which this SAP belongs does not exist
         in tPortAccEgrQGrpTable."
    DEFVAL { 0 }
    ::= { sapBaseInfoEntry 72 }

sapEtreeRootLeafTag                    OBJECT-TYPE
    SYNTAX     TruthValue
    MAX-ACCESS read-create
    STATUS     current
    DESCRIPTION
        "The value of sapEtreeRootLeafTag specifies whether or not this SAP is
         e-tree tagging in this service, with the first VLAN tag in the SAP 
         identifier being the VLAN tag for e-tree root traffic.

         An 'inconsistentValue' error is returned if the value of this object
         is set to 'true' when TIMETRA-SERV-MIB::svcType for the service
         is not set to 'tls'.

         An 'inconsistentValue' error is returned if the value of this object
         is set to 'true' when TIMETRA-SERV-MIB::svcTlsModeEtree for the
         service is set to 'false'.

         An 'inconsistentValue' error is returned if the value of sapEtreeRootLeafTag 
         and sapEtreeLeafTag are not set together.

         An 'inconsistentValue' error is returned if sapEtreeRootLeafTag and 
         sapEtreeLeafTag are set to non-default values and sapEtreeLeafAc is also 
         set to a non-default value for the same SAP instance.
         
         The value of this object can be set only during the creation of the
         SAP instance."
    DEFVAL { false }
    ::= { sapBaseInfoEntry 74 }

sapEtreeLeafTag                    OBJECT-TYPE
    SYNTAX     Integer32 (0|1..4094)
    MAX-ACCESS read-create
    STATUS     current
    DESCRIPTION
        "The value of sapEtreeLeafTag specifies the VLAN tag to be used for
         e-tree leaf traffic in the service.
         
         An 'inconsistentValue' error is returned if the value of sapEtreeRootLeafTag 
         and sapEtreeLeafTag are not set together.
         
         An 'inconsistentValue' error is returned if sapEtreeRootLeafTag and 
         sapEtreeLeafTag are set to non-default values and sapEtreeLeafAc is also 
         set to a non-default value for the same SAP instance.
         
         The value of this object can be set only during the creation of the
         SAP instance."
    DEFVAL { 0 }
    ::= { sapBaseInfoEntry 75 }

sapEtreeLeafAc OBJECT-TYPE
    SYNTAX     TruthValue
    MAX-ACCESS read-create
    STATUS     current
    DESCRIPTION
        "The value of sapEtreeLeafAc specifies whether or not this SAP is
         an e-tree leaf access circuit of the service.

         An 'inconsistentValue' error is returned if the value of this object
         is set to 'true' when TIMETRA-SERV-MIB::svcTlsModeEtree for the 
         service is set to 'false'.

         An 'inconsistentValue' error is returned if sapEtreeLeafAc is set to a
         non-default value and sapEtreeRootLeafTag and sapEtreeLeafTag are also set 
         to non-default values for the same SAP instance.
         
         The value of this object can be set only during the creation of the
         SAP instance."
    DEFVAL { false }
    ::= { sapBaseInfoEntry 76 }

sapEgressAggRateLUB   OBJECT-TYPE
    SYNTAX      TruthValue
    MAX-ACCESS  read-create
    STATUS      current
    DESCRIPTION 
        "The value of sapEgressAggRateLUB specifies whether to limit the unused
         bandwidth and allow a tighter control in allocation of bandwidth by
         HQos.

         When the value of sapEgressAggRateLUB is set to 'true', HQos algorithm
         distributes any unused aggregate bandwidth between queues operating
         below their fair share rates. This allows a simplified aggregate rate
         protection while allocating bandwidth by HQos scheduling algorithm."
    DEFVAL { false }
    ::= { sapBaseInfoEntry 77 }


sapEgressAggRateLmt                 OBJECT-TYPE
    SYNTAX          Unsigned32 (1..3200000000 | 4294967295)
    UNITS           "kbps"
    MAX-ACCESS      read-create
    STATUS          current
    DESCRIPTION
        "The value of sapEgressAggRateLmt specifies the maximum total rate
         of all egress queues for this SAP.
         The value of 4294967295 (0xFFFFFFFF) means that there is no limit."
    DEFVAL { 4294967295 }
    ::= { sapBaseInfoEntry 80 }


-- -------------------------------------
-- TLS SAP Table
-- -------------------------------------
sapTlsInfoTable OBJECT-TYPE
    SYNTAX          SEQUENCE OF SapTlsInfoEntry
    MAX-ACCESS      not-accessible
    STATUS          current
    DESCRIPTION     "A table that contains TLS SAP information."
    ::= { tmnxSapObjs 3 }

sapTlsInfoEntry OBJECT-TYPE
    SYNTAX          SapTlsInfoEntry
    MAX-ACCESS      not-accessible
    STATUS          current
    DESCRIPTION     "TLS specific information about a SAP."
    INDEX           { svcId, sapPortId, sapEncapValue }
    ::= { sapTlsInfoTable 1 }

SapTlsInfoEntry ::=
    SEQUENCE {
        sapTlsStpAdminStatus            TmnxEnabledDisabled,
        sapTlsStpPriority               INTEGER,
        sapTlsStpPortNum                INTEGER,
        sapTlsStpPathCost               INTEGER,
        sapTlsStpRapidStart             TmnxEnabledDisabled,
        sapTlsStpBpduEncap              INTEGER,
        sapTlsStpPortState              TStpPortState,
        sapTlsStpDesignatedBridge       BridgeId,
        sapTlsStpDesignatedPort         Integer32,
        sapTlsStpForwardTransitions     Gauge32,
        sapTlsStpInConfigBpdus          Gauge32,
        sapTlsStpInTcnBpdus             Gauge32,
        sapTlsStpInBadBpdus             Gauge32,
        sapTlsStpOutConfigBpdus         Gauge32,
        sapTlsStpOutTcnBpdus            Gauge32,
        sapTlsStpOperBpduEncap          INTEGER,
        sapTlsVpnId                     VpnId,
        sapTlsCustId                    TmnxCustId,
        sapTlsMacAddressLimit           Integer32,
        sapTlsNumMacAddresses           Integer32,
        sapTlsNumStaticMacAddresses     Integer32,
        sapTlsMacLearning               TmnxEnabledDisabled,
        sapTlsMacAgeing                 TmnxEnabledDisabled,
        sapTlsStpOperEdge               TruthValue,
        sapTlsStpAdminPointToPoint      INTEGER,
        sapTlsStpPortRole               StpPortRole,
        sapTlsStpAutoEdge               TmnxEnabledDisabled,
        sapTlsStpOperProtocol           StpProtocol,
        sapTlsStpInRstBpdus             Gauge32,
        sapTlsStpOutRstBpdus            Gauge32,
        sapTlsLimitMacMove              TlsLimitMacMove,
        sapTlsDhcpSnooping              TmnxEnabledDisabled,
        sapTlsMacPinning                TmnxEnabledDisabled,
        sapTlsDiscardUnknownSource      TmnxEnabledDisabled,
        sapTlsMvplsPruneState           MvplsPruneState,
        sapTlsMvplsMgmtService          TmnxServId,
        sapTlsMvplsMgmtPortId           TmnxPortID,
        sapTlsMvplsMgmtEncapValue       TmnxEncapVal,
        sapTlsArpReplyAgent             INTEGER,
        sapTlsStpException              StpExceptionCondition,
        sapTlsAuthenticationPolicy      TPolicyStatementNameOrEmpty,
        sapTlsL2ptTermination           TmnxEnabledDisabled,
        sapTlsBpduTranslation           TlsBpduTranslation,
        sapTlsStpRootGuard              TruthValue,
        sapTlsStpInsideRegion           TruthValue,
        sapTlsEgressMcastGroup          TNamedItemOrEmpty,
        sapTlsStpInMstBpdus             Gauge32,
        sapTlsStpOutMstBpdus            Gauge32,
        sapTlsRestProtSrcMac            TruthValue,
        sapTlsRestUnprotDstMac          TruthValue,
        sapTlsStpRxdDesigBridge         BridgeId,
        sapTlsStpRootGuardViolation     TruthValue,
        sapTlsShcvAction                TmnxSubShcvAction,
        sapTlsShcvSrcIp                 IpAddress,
        sapTlsShcvSrcMac                MacAddress,
        sapTlsShcvInterval              TmnxSubShcvInterval,
        sapTlsMvplsMgmtMsti             MstiInstanceIdOrZero,
        sapTlsMacMoveNextUpTime         Unsigned32,
        sapTlsMacMoveRateExcdLeft       Unsigned32,
        sapTlsRestProtSrcMacAction      INTEGER,
        sapTlsL2ptForceBoundary         TruthValue,
        sapTlsLimitMacMoveLevel         TlsLimitMacMoveLevel,
        sapTlsBpduTransOper             INTEGER,
        sapTlsDefMsapPolicy             TPolicyStatementNameOrEmpty,
        sapTlsL2ptProtocols             L2ptProtocols,
        sapTlsL2ptForceProtocols        L2ptProtocols,
        sapTlsPppoeMsapTrigger          TruthValue,
        sapTlsDhcpMsapTrigger           TruthValue,
        sapTlsMrpJoinTime               Unsigned32,
        sapTlsMrpLeaveTime              Unsigned32,
        sapTlsMrpLeaveAllTime           Unsigned32,
        sapTlsMrpPeriodicTime           Unsigned32,
        sapTlsMrpPeriodicEnabled        TruthValue,
        sapTlsPppoePolicy               TNamedItemOrEmpty,
        sapTlsArpMsapTrigger            TruthValue,
        sapTlsDefMsapService            TmnxServId,
        sapTlsDefMsapGroupIf            TNamedItemOrEmpty,
        sapTlsMrpPolicy                 TNamedItemOrEmpty,
        sapTlsSiteName                  TNamedItemOrEmpty,
        sapTlsDhcp6MsapTrigger          TruthValue,
        sapTlsShcvRetryTimeout          TmnxSubShcvRetryTimeout,
        sapTlsShcvRetryCount            TmnxSubShcvRetryCount,
        sapTlsDataSapInstStatus         TmnxSapInstStatus,
        sapTlsDataSapInstLastErr        DisplayString,
        sapTlsMvrpAdminStatus           TmnxEnabledDisabled,
        sapTlsMvrpOperStatus            TmnxEnabledDisabled,
        sapTlsInTcBitBpdus              Counter32,
        sapTlsOutTcBitBpdus             Counter32,
        sapTlsPppMsapTrigger            TruthValue,
        sapTlsPppPolicy                 TNamedItemOrEmpty,
        sapTlsTrackSrrpInst             Unsigned32,
        sapTlsPppUserDb                 TNamedItemOrEmpty,
        sapTlsPppoeUserDb               TNamedItemOrEmpty,
        sapTlsDhcpUserDb                TNamedItemOrEmpty,
        sapTlsAutoLearnMacProtect       TruthValue,
        sapTlsDhcp6UserDb               TNamedItemOrEmpty,
        sapTlsShcvPolicyIpv4             TNamedItemOrEmpty
    }

sapTlsStpAdminStatus OBJECT-TYPE
    SYNTAX          TmnxEnabledDisabled
    MAX-ACCESS      read-write
    STATUS          current
    DESCRIPTION     "The value of the object sapTlsStpAdminStatus specifies
                     whether this SAP participates in the TLS's Spanning Tree
                     Protocol.

                     A SAP with a non-zero sapEthRingIndex does not participate
                     in the TLS's Spanning Tree Protocol. The default value for
                     sapTlsStpAdminStatus for these SAPs is 'disabled' and may
                     not be set to 'enabled'."
    DEFVAL          { enabled }
    ::= { sapTlsInfoEntry 1 }

sapTlsStpPriority OBJECT-TYPE
    SYNTAX          INTEGER (0..255)
    MAX-ACCESS      read-write
    STATUS          current
    DESCRIPTION     "The value of the object sapTlsStpPriority specifies
                     the value of the port priority field which is contained in
                     the most significant 4 bits of the 16-bit Port ID
                     associated with this SAP. As only the most significant 4
                     bits of the value are used, the actual value of this object
                     is limited to multiples of 16: e.g. the agent rounds down
                     the value to one of: 0, 16, 32, .. , 224, 240."
    DEFVAL          { 128 }
    ::= { sapTlsInfoEntry 2 }

sapTlsStpPortNum OBJECT-TYPE
    SYNTAX          INTEGER (0..4094)
    MAX-ACCESS      read-write
    STATUS          current
    DESCRIPTION     "The value of the object sapTlsStpPortNum specifies the
                     value of the port number field which is contained in the
                     least significant 12 bits of the 16-bit Port ID associated
                     with this SAP. Values in the range 2048..4094 are
                     automatically assigned by the agent when the SAP is
                     created or when the value of this object is set to zero
                     via management. Values in the range 1..2047 can be set
                     via management, to allow this object to have a
                     deterministic value across system reboots."
    ::= { sapTlsInfoEntry 3 }

sapTlsStpPathCost OBJECT-TYPE
    SYNTAX          INTEGER (1..200000000)
    MAX-ACCESS      read-write
    STATUS          current
    DESCRIPTION     "The value of the object  sapTlsStpPathCost specifies the
                     contribution of this port to the path cost of paths
                     towards the spanning tree root which include this port."
    DEFVAL          { 10 }
    ::= { sapTlsInfoEntry 4 }

sapTlsStpRapidStart OBJECT-TYPE
    SYNTAX          TmnxEnabledDisabled
    MAX-ACCESS      read-write
    STATUS          current
    DESCRIPTION     "The value of the object sapTlsStpRapidStart specifies
                     whether Rapid Start is enabled on this SAP. When the value
                     is 'enabled' the Spanning Tree Protocol state transitions
                     on this SAP are driven by the value of the 'HelloTime'
                     instead of the value of 'ForwardDelay', thus allowing a
                     faster transition into the forwarding state. This
                     parameter is also referred to as 'adminEdge'. "
    DEFVAL          { disabled }
    ::= { sapTlsInfoEntry 5 }

sapTlsStpBpduEncap OBJECT-TYPE
    SYNTAX          INTEGER {
                        dynamic (1),
                        dot1d   (2),
                        pvst    (3)
                    }
    MAX-ACCESS      read-write
    STATUS          current
    DESCRIPTION     "The value of the object sapTlsStpBpduEncap specifies the
                     type of encapsulation used on BPDUs sent out and received
                     on this SAP."
    DEFVAL          { dynamic }
    ::= { sapTlsInfoEntry 6 }

sapTlsStpPortState OBJECT-TYPE
    SYNTAX          TStpPortState
    MAX-ACCESS      read-only
    STATUS          current
    DESCRIPTION     "The value of the object sapTlsStpPortState indicates the
                     port's current state as defined by application of the
                     Spanning Tree Protocol. This state controls what action a
                     port takes on reception of a frame. If the bridge has
                     detected a port that is malfunctioning it will
                     place that port into the 'broken' state."
    ::= { sapTlsInfoEntry 7 }

sapTlsStpDesignatedBridge OBJECT-TYPE
    SYNTAX          BridgeId
    MAX-ACCESS      read-only
    STATUS          current
    DESCRIPTION     "The value of the object sapTlsStpDesignatedBridge
                     indicates  the Bridge Identifier of the bridge which this
                     port considers to be the Designated Bridge for this port's
                     segment."
    ::= { sapTlsInfoEntry 8 }

sapTlsStpDesignatedPort OBJECT-TYPE
    SYNTAX          Integer32
    MAX-ACCESS      read-only
    STATUS          current
    DESCRIPTION     "The value of the object sapTlsStpDesignatedPort indicates
                     the Port Identifier of the port on the Designated Bridge
                     for this port's segment."
    ::= { sapTlsInfoEntry 9 }

sapTlsStpForwardTransitions OBJECT-TYPE
    SYNTAX          Gauge32
    MAX-ACCESS      read-only
    STATUS          current
    DESCRIPTION     "The value of the object sapTlsStpForwardTransitions
                     indicates the number of times this port has transitioned
                     from the Learning state to the Forwarding state."
    ::= { sapTlsInfoEntry 10 }

sapTlsStpInConfigBpdus OBJECT-TYPE
    SYNTAX          Gauge32
    MAX-ACCESS      read-only
    STATUS          current
    DESCRIPTION     "The value of the object sapTlsStpInConfigBpdus indicates
                     the number of Configuration BPDUs received on this SAP."
    ::= { sapTlsInfoEntry 11 }

sapTlsStpInTcnBpdus OBJECT-TYPE
    SYNTAX          Gauge32
    MAX-ACCESS      read-only
    STATUS          current
    DESCRIPTION     "The value of the object  sapTlsStpInTcnBpdus indicates the
                     number of Topology Change Notification BPDUs received on
                     this SAP."
    ::= { sapTlsInfoEntry 12 }

sapTlsStpInBadBpdus OBJECT-TYPE
    SYNTAX          Gauge32
    MAX-ACCESS      read-only
    STATUS          current
    DESCRIPTION     "This object specifies the number of bad
                     BPDUs received on this SAP."
    ::= { sapTlsInfoEntry 13 }

sapTlsStpOutConfigBpdus OBJECT-TYPE
    SYNTAX          Gauge32
    MAX-ACCESS      read-only
    STATUS          current
    DESCRIPTION     "The value of the object sapTlsStpOutConfigBpdus indicates
                     the number of Configuration BPDUs sent out this SAP."
    ::= { sapTlsInfoEntry 14 }

sapTlsStpOutTcnBpdus OBJECT-TYPE
    SYNTAX          Gauge32
    MAX-ACCESS      read-only
    STATUS          current
    DESCRIPTION     "This object specifies the number of Topology
                     Change Notification BPDUs sent out this SAP."
    ::= { sapTlsInfoEntry 15 }

sapTlsStpOperBpduEncap OBJECT-TYPE
    SYNTAX          INTEGER {
                        dynamic (1),
                        dot1d   (2),
                        pvst    (3)
                    }
    MAX-ACCESS      read-only
    STATUS          current
    DESCRIPTION     "The value of the object sapTlsStpOperBpduEncap indicates
                     the operating encapsulation  type used on BPDUs sent out
                     and received on this SAP."
    ::= { sapTlsInfoEntry 16 }

sapTlsVpnId OBJECT-TYPE
    SYNTAX          VpnId
    MAX-ACCESS      read-only
    STATUS          current
    DESCRIPTION     "The value of the object sapTlsVpnId indicates the VPN ID
                     of the associated service."
    ::= { sapTlsInfoEntry 17 }

sapTlsCustId OBJECT-TYPE
    SYNTAX          TmnxCustId
    MAX-ACCESS      read-only
    STATUS          current
    DESCRIPTION     "The Customer ID of the associated service."
    ::= { sapTlsInfoEntry 18 }

sapTlsMacAddressLimit OBJECT-TYPE
    SYNTAX          Integer32(0..511999)
    MAX-ACCESS      read-write
    STATUS          current
    DESCRIPTION     "The value of the object sapTlsMacAddressLimit specifies
                     the maximum number of learned and static entries allowed
                     in the FDB of this SAP. The value 0 means: no limit for
                     this SAP.

                     The maximum value of sapTlsMacAddressLimit is '511999',
                     when the the value of
                     TIMETRA-CHASSIS-MIB::tmnxChassisOperMode is 'd'.

                     The maximum value of sapTlsMacAddressLimit is '196607',
                     when the the value of
                     TIMETRA-CHASSIS-MIB::tmnxChassisOperMode is 'c'.

                     In other cases, the maximum value of
                     sapTlsMacAddressLimit is '131071'."
    DEFVAL          { 0 }
    ::= { sapTlsInfoEntry 19 }

sapTlsNumMacAddresses OBJECT-TYPE
    SYNTAX          Integer32
    MAX-ACCESS      read-only
    STATUS          current
    DESCRIPTION     "The value of the object sapTlsNumMacAddresses indicates
                     the number of MAC addresses  currently present in the FDB
                     that belong to this  SAP  (Both  learned and static MAC
                     addresses are counted)."
    ::= { sapTlsInfoEntry 20 }

sapTlsNumStaticMacAddresses OBJECT-TYPE
    SYNTAX          Integer32
    MAX-ACCESS      read-only
    STATUS          current
    DESCRIPTION     "The value of the object sapTlsNumStaticMacAddresses
                     indicates the number of static MAC addresses currently
                     present in the FDB that belong to this SAP."
    ::= { sapTlsInfoEntry 21 }

sapTlsMacLearning OBJECT-TYPE
    SYNTAX          TmnxEnabledDisabled
    MAX-ACCESS      read-write
    STATUS          current
    DESCRIPTION     "The value of the object sapTlsMacLearning specifies
                     whether the MAC learning process  is enabled for this SAP.
                     The value is ignored if MAC learning is disabled on
                     service level."
    DEFVAL          { enabled }
    ::= { sapTlsInfoEntry 22 }

sapTlsMacAgeing OBJECT-TYPE
    SYNTAX          TmnxEnabledDisabled
    MAX-ACCESS      read-write
    STATUS          current
    DESCRIPTION     "The value of the object sapTlsMacAgeing specifies whether
                     the MAC aging process  is enabled for this SAP. the value
                     is ignored if MAC aging is disabled on service level."
    DEFVAL          { enabled }
    ::= { sapTlsInfoEntry 23 }

sapTlsStpOperEdge OBJECT-TYPE
    SYNTAX          TruthValue
    MAX-ACCESS      read-only
    STATUS          current
    DESCRIPTION     "The value of the object sapTlsStpOperEdge indicates the
                     operational value of the Edge Port parameter. The object
                     is initialized to the value of sapTlsStpRapidStart and is
                     set FALSE on reception of a BPDU."
    REFERENCE
                    "IEEE 802.1t clause 14.8.2, 18.3.4"
    ::= { sapTlsInfoEntry 24 }

sapTlsStpAdminPointToPoint OBJECT-TYPE
    SYNTAX          INTEGER {
                        forceTrue  (0),
                        forceFalse (1)
                    }
    MAX-ACCESS      read-write
    STATUS          current
    DESCRIPTION     "The value of the object sapTlsStpAdminPointToPoint
                     specifies the administrative point-to-point  status  of
                     the LAN segment attached to this  sap. The value
                     'forceTrue' means that this port should  always  be
                     treated as if it is connected to a point-to-point link.
                     The value of 'forceFalse' means that this port should
                     be treated as having a shared media connection."
    REFERENCE
                    "IEEE 802.1w clause 6.4.3, 6.5, 14.8.2"
    DEFVAL          { forceTrue }
    ::= { sapTlsInfoEntry 25 }

sapTlsStpPortRole OBJECT-TYPE
    SYNTAX          StpPortRole
    MAX-ACCESS      read-only
    STATUS          current
    DESCRIPTION     "sapTlsStpPortRole indicates the current role of the
                     sap as defined by the Rapid Spanning Tree Protocol."
    ::= { sapTlsInfoEntry 26 }

sapTlsStpAutoEdge OBJECT-TYPE
    SYNTAX          TmnxEnabledDisabled
    MAX-ACCESS      read-write
    STATUS          current
    DESCRIPTION     "sapTlsStpAutoEdge specifies whether this SAP
                     is enabled for auto-edge detection as defined by Rapid
                     Spanning Tree Protocol."
    DEFVAL          { enabled }
    ::= { sapTlsInfoEntry 27 }

sapTlsStpOperProtocol OBJECT-TYPE
    SYNTAX          StpProtocol
    MAX-ACCESS      read-only
    STATUS          current
    DESCRIPTION     "sapTlsStpOperProtocol indicates whether stp, rstp or
                     mstp is  running  on this SAP. If the protocol is not
                     enabled  on  this  SAP,  the  value  notApplicable  is
                     returned."
    ::= { sapTlsInfoEntry 28 }

sapTlsStpInRstBpdus OBJECT-TYPE
    SYNTAX          Gauge32
    MAX-ACCESS      read-only
    STATUS          current
    DESCRIPTION     "The value of the object  sapTlsStpInRstBpdus indicates
                     the number of Rapid Spanning Tree (RST) BPDUs received on
                     this SAP."
    ::= { sapTlsInfoEntry 29 }

sapTlsStpOutRstBpdus OBJECT-TYPE
    SYNTAX          Gauge32
    MAX-ACCESS      read-only
    STATUS          current
    DESCRIPTION     "The value of the  object sapTlsStpOutRstBpdus indicates
                     the number of Rapid Spanning Tree (RST) BPDUs sent out on
                     this SAP."
    ::= { sapTlsInfoEntry 30 }

sapTlsLimitMacMove OBJECT-TYPE
    SYNTAX          TlsLimitMacMove
    MAX-ACCESS      read-write
    STATUS          current
    DESCRIPTION     "When sapTlsLimitMacMove value is set  to  'blockable'
                     the  agent will monitor the MAC relearn rate on this
                     SAP,  and it will  block  it  when the re-learn rate
                     specified  by  svcTlsMacMoveMaxRate  is exceeded. When
                     the  value is  'nonBlockable'  this  SAP will not be
                     blocked,  and  another  blockable  SAP will be blocked
                     instead."
    DEFVAL          { blockable }
    ::= { sapTlsInfoEntry 31 }

sapTlsDhcpSnooping OBJECT-TYPE
    SYNTAX          TmnxEnabledDisabled
    MAX-ACCESS      read-write
    STATUS          obsolete
    DESCRIPTION     "The value of the object sapTlsDhcpSnooping specifies
                     whether or not DHCP packets received on this SAP will be
                     snooped. This object was made obsolete in the 3.0 release."
    DEFVAL          { disabled }
    ::= { sapTlsInfoEntry 32 }

sapTlsMacPinning OBJECT-TYPE
    SYNTAX          TmnxEnabledDisabled
    MAX-ACCESS      read-write
    STATUS          current
    DESCRIPTION     "The value of the object sapTlsMacPinning specifies whether
                     or not MAC address pinning is active on this SAP. The
                     value will be set by default to disabled. However for a
                     SAP that belongs to a residential SHG, the value is set to
                     enabled by the system, and cannot be altered by the
                     operator. Setting the value to enable disables
                     re-learning of MAC addresses on other SAPs or
                     spoke-SDPs within the same VPLS; the MAC address will
                     hence remain attached to the SAP for the duration of
                     its age-timer. This object has effect only for MAC
                     addresses learned via the normal MAC learning
                     process, and not for entries learned via DHCP."
    ::= { sapTlsInfoEntry 33 }

sapTlsDiscardUnknownSource OBJECT-TYPE
    SYNTAX          TmnxEnabledDisabled
    MAX-ACCESS      read-write
    STATUS          current
    DESCRIPTION     "with   the object sapTlsMacAddressLimit a limit can be
                     configured  for  the  max number of MAC addresses that
                     will  be learned on this  SAP.  When  this limit is
                     reached, packets with unknown source MAC address are
                     forwarded by default. By setting
                     sapTlsDiscardUnknownSource  to enabled, packets with
                     unknown source MAC will be dropped in stead."
    DEFVAL          { disabled }
    ::= { sapTlsInfoEntry 34 }

sapTlsMvplsPruneState OBJECT-TYPE
    SYNTAX          MvplsPruneState
    MAX-ACCESS      read-only
    STATUS          current
    DESCRIPTION     "The value of sapTlsMvplsPruneState indicates the mVPLS
                     prune state of the SAP. The object will be set to
                     notApplicable if the SAP is not managed by a mVPLS. If
                     the SAP is managed the state reflects whether or not
                     the SAP is pruned by the STP instance running in the
                     mVPLS instance."
    ::= { sapTlsInfoEntry 35 }

sapTlsMvplsMgmtService OBJECT-TYPE
    SYNTAX          TmnxServId
    MAX-ACCESS      read-only
    STATUS          current
    DESCRIPTION     "The value of sapTlsMvplsMgmtService indicates the
                     service Id of the service where the STP instance is
                     running that is managing this SAP. This object is
                     only valid if sapTlsMvplsPruneState is different from
                     notApplicable."
    ::= { sapTlsInfoEntry 36 }

sapTlsMvplsMgmtPortId OBJECT-TYPE
    SYNTAX          TmnxPortID
    MAX-ACCESS      read-only
    STATUS          current
    DESCRIPTION     "The value of sapTlsMvplsMgmtPortId indicates the SAP
                     port Id of the SAP in the mVPLS instance specified in
                     sapTlsMvplsMgmtService that is controlling this SAP.
                     This object is only valid if sapTlsMvplsPruneState is
                     different from notApplicable."
    ::= { sapTlsInfoEntry 37 }

sapTlsMvplsMgmtEncapValue OBJECT-TYPE
    SYNTAX          TmnxEncapVal
    MAX-ACCESS      read-only
    STATUS          current
    DESCRIPTION     "The value of sapTlsMvplsMgmtEncapValue indicates the
                     SAP Encap value of the SAP in the mVPLS instance
                     specified in sapTlsMvplsMgmtService that is
                     controlling this SAP. This object is only valid if
                     sapTlsMvplsPruneState is different from notApplicable."
    ::= { sapTlsInfoEntry 38 }

sapTlsArpReplyAgent OBJECT-TYPE
    SYNTAX          INTEGER {
                        disabled               (1),
                        enabled                (2),
                        enabledWithSubscrIdent (3)
                    }
    MAX-ACCESS      read-write
    STATUS          current
    DESCRIPTION     "The value of the object sapTlsArpReplyAgent specifies
                     the status of the special ARP response mechanism in the
                     system for ARP requests destined to static or dynamic hosts
                     associated with this SAP.
                     disabled: the ARP reply function is not operational
                     enabled: the ARP reply function is enabled without
                              subscriber identification.
                     enabledWithSubscrIdent: the ARP reply function is enabled
                                             with subscriber identification."
    DEFVAL { disabled }
    ::= { sapTlsInfoEntry 39 }

sapTlsStpException OBJECT-TYPE
    SYNTAX          StpExceptionCondition
    MAX-ACCESS      read-only
    STATUS          current
    DESCRIPTION     "The value of the object sapTlsStpException indicates
                     whether an STP exception condition is present on this
                     Sap.
                     - none : no exception condition found.
                     - oneWayCommuniation : The neighbor RSTP peer on this link
                                            is not able to detect our presence.
                     - downstreamLoopDetected :A loop is detected on this link."
    ::= { sapTlsInfoEntry 40 }

sapTlsAuthenticationPolicy OBJECT-TYPE
    SYNTAX      TPolicyStatementNameOrEmpty
    MAX-ACCESS  read-write
    STATUS      current
    DESCRIPTION  "The value of the object sapTlsAuthenticationPolicy specifies
                  which subscriber authentication policy  must  be applied when
                  a DHCP msg is received on the interface.  The  authentication
                  policies  must be defined  in  tmnxSubAuthPlcyTable. The policy
                  will only be applied when sapTlsDhcpSnoop is enabled."
    DEFVAL { ''H }
    ::= { sapTlsInfoEntry 41 }

sapTlsL2ptTermination OBJECT-TYPE
    SYNTAX          TmnxEnabledDisabled
    MAX-ACCESS      read-write
    STATUS          current
    DESCRIPTION     "The value of the object sapTlsL2ptTermination specifies
                     whether received Layer 2 Protocol Tunnel (L2PT) pdu's 
                     are terminated on this port or sap."
    DEFVAL          { disabled }
    ::= { sapTlsInfoEntry 42 }

sapTlsBpduTranslation OBJECT-TYPE
    SYNTAX          TlsBpduTranslation
    MAX-ACCESS      read-write
    STATUS          current
    DESCRIPTION     "The value of the object sapTlsBpduTranslation specifies
                     whether received L2 Protocol Tunnel pdu's are
                     translated before being sent out on this port or sap."
    DEFVAL          { disabled }
    ::= { sapTlsInfoEntry 43 }

sapTlsStpRootGuard OBJECT-TYPE
    SYNTAX          TruthValue
    MAX-ACCESS      read-write
    STATUS          current
    DESCRIPTION     "The value of the object sapTlsStpRootGuard specifies
                     whether this port is allowed to become STP root port.
                     It corresponds to the parameter 'restrictedRole' in 802.1Q.
                     If set, it can cause lack of spanning tree connectivity."
    DEFVAL          { false }
    ::= { sapTlsInfoEntry 44 }

sapTlsStpInsideRegion OBJECT-TYPE
    SYNTAX          TruthValue
    MAX-ACCESS      read-only
    STATUS          current
    DESCRIPTION     "The value of the object sapTlsStpInsideRegion indicates
                     whether the network connected to the SAP is in the same
                     MST region. It corresponds to the parameter 'infoInternal'
                     in 802.1Q."
    ::= { sapTlsInfoEntry 45 }

sapTlsEgressMcastGroup OBJECT-TYPE
    SYNTAX          TNamedItemOrEmpty
    MAX-ACCESS      read-write
    STATUS          current
    DESCRIPTION     "The value of the object sapTlsEgressMcastGroup specifies
                     the Egress Multicast Group this SAP belongs to."
    DEFVAL          { "" }
    ::= { sapTlsInfoEntry 46 }

sapTlsStpInMstBpdus OBJECT-TYPE
    SYNTAX          Gauge32
    MAX-ACCESS      read-only
    STATUS          current
    DESCRIPTION     "The value of the object sapTlsStpInMstBpdus indicates
                     the number of Multiple Spanning Tree (MST) BPDUs received
                     on this SAP."
    ::= { sapTlsInfoEntry 47 }

sapTlsStpOutMstBpdus OBJECT-TYPE
    SYNTAX          Gauge32
    MAX-ACCESS      read-only
    STATUS          current
    DESCRIPTION     "The value of the object sapTlsStpOutMstBpdus indicates
                     the number of Multiple Spanning Tree (MST) BPDUs sent out
                     on this SAP."
    ::= { sapTlsInfoEntry 48 }

sapTlsRestProtSrcMac OBJECT-TYPE
    SYNTAX          TruthValue
    MAX-ACCESS      read-write
    STATUS          current
    DESCRIPTION     "The value of the object sapTlsRestProtSrcMac specifies
                     how the agent will handle relearn requests for protected
                     MAC addresses. When the value of this object is 'true'
                     requests to relearn a protected MAC address will be
                     ignored.
                     In addition, if the value of sapTlsRestProtSrcMacAction
                     is 'disable', then the SAP where the protected source
                     MAC was seen will be brought operationally down."
    DEFVAL          { false }
    ::= { sapTlsInfoEntry 49 }

sapTlsRestUnprotDstMac OBJECT-TYPE
    SYNTAX          TruthValue
    MAX-ACCESS      read-write
    STATUS          current
    DESCRIPTION     "The value of the object sapTlsRestUnprotDstMac specifies
                     how the system will forward packets destined to an
                     unprotected MAC address. When the value of this object is
                     'true' packets destined to an unprotected MAC address
                     will be dropped."
    DEFVAL          { false }
    ::= { sapTlsInfoEntry 50 }

sapTlsStpRxdDesigBridge OBJECT-TYPE
    SYNTAX          BridgeId
    MAX-ACCESS      read-only
    STATUS          current
    DESCRIPTION     "The value of the object sapTlsStpRxdDesigBridge
                     indicates  the designated Bridge Identifier in the last
                     BPDU which was received on this SAP. It identifies
                     which bridge is connected to the SAP."
    ::= { sapTlsInfoEntry 51 }

sapTlsStpRootGuardViolation OBJECT-TYPE
    SYNTAX          TruthValue
    MAX-ACCESS      read-only
    STATUS          current
    DESCRIPTION     "The value of the object sapTlsStpRootGuardViolation
                     indicates whether there is a root-guard violation at the
                     present time. This can only happen when sapTlsStpRootGuard
                     is set to true."
    ::= { sapTlsInfoEntry 52 }


sapTlsShcvAction OBJECT-TYPE
    SYNTAX          TmnxSubShcvAction
    MAX-ACCESS      read-write
    STATUS          current
    DESCRIPTION     "The value of the object sapTlsShcvAction
                     indicates whether any action should be triggered when
                     the connectivity check fails."
    DEFVAL          { alarm }
    ::= { sapTlsInfoEntry 53 }


sapTlsShcvSrcIp OBJECT-TYPE
    SYNTAX          IpAddress
    MAX-ACCESS      read-write
    STATUS          current
    DESCRIPTION     "The value of the object sapTlsShcvSrcIp
                     specifies the source IP address used when doing the
                     connectivity check. The value 0.0.0.0 indicates that
                     no host IP address is specified."
    ::= { sapTlsInfoEntry 54 }

sapTlsShcvSrcMac OBJECT-TYPE
    SYNTAX          MacAddress
    MAX-ACCESS      read-write
    STATUS          current
    DESCRIPTION     "The value of the object sapTlsShcvSrcMac
                     specifies the MAC address used when doing the connectivity
                     check. The value 0:0:0:0:0:0 indicates that no host MAC
                     address is specified."
    ::= { sapTlsInfoEntry 55 }

sapTlsShcvInterval OBJECT-TYPE
    SYNTAX          TmnxSubShcvInterval
    UNITS           "minutes"
    MAX-ACCESS      read-write
    STATUS          current
    DESCRIPTION     "The value of the object sapTlsShcvInterval specifies
                     the interval in minutes between connectivity checks.
                     Zero means no connectivity checking."
    DEFVAL          { 0 }
    ::= { sapTlsInfoEntry 56 }

sapTlsMvplsMgmtMsti OBJECT-TYPE
    SYNTAX          MstiInstanceIdOrZero
    MAX-ACCESS      read-only
    STATUS          current
    DESCRIPTION     "The value of the object sapTlsMvplsMgmtMsti indicates the
                     MST-instance in the mVPLS instance specified in
                     sapTlsMvplsMgmtService that is controlling this SAP. A
                     value of 0 indicates the CIST.
                     This object is only valid if sapTlsMvplsPruneState is
                     different from notApplicable."
    ::= { sapTlsInfoEntry 57 }

sapTlsMacMoveNextUpTime OBJECT-TYPE
    SYNTAX          Unsigned32
    UNITS           "seconds"
    MAX-ACCESS      read-only
    STATUS          current
    DESCRIPTION     "The value of the object sapTlsMacMoveNextUpTime counts down
                     the time in seconds until a SAP that has been brought down
                     due to exceeding the TLS svcTlsMacMoveMaxRate, sapOperFlags
                     'relearnLimitExceeded', is automatically brought up again. 

                     When this value is 0xffff, the SAP will never be 
                     automatically brought up.

                     When sapOperStatus is 'up', this object counts down the
                     time in seconds until the value of
                     sapTlsMacMoveRateExcdLeft is reset."
    ::= { sapTlsInfoEntry 58 }

sapTlsMacMoveRateExcdLeft   OBJECT-TYPE
    SYNTAX          Unsigned32
    MAX-ACCESS      read-only
    STATUS          current
    DESCRIPTION     "The value of the object sapTlsMacMoveRateExcdLeft
                     counts down the number of times this SAP can exceed the 
                     TLS svcTlsMacMoveMaxRate and still be automatically
                     brought up."
    ::= { sapTlsInfoEntry 59 }
    
sapTlsRestProtSrcMacAction OBJECT-TYPE
    SYNTAX          INTEGER {
                        disable      (1),
                        alarm-only   (2),
                        discardFrame (3)
                    }
    MAX-ACCESS      read-write
    STATUS          current
    DESCRIPTION     "The value of the object sapTlsRestProtSrcMacAction
                     indicates the action to take whenever a relearn request
                     for a protected MAC is received on a restricted SAP.
                     When the value of this object is 'disable' the SAP
                     will be placed in the operational down state, with the
                     operating flag 'recProtSrcMac' set.
                     
                     When the value of this object is 'alarm-only', the SAP
                     will be left up and only a notification,
                     sapReceivedProtSrcMac,  will be generated.

                     When the value of this object is 'discardFrame', the
                     SAP will start discarding the frame in addition to 
                     generating sapReceivedProtSrcMac notification."
    DEFVAL          { disable }    
    ::= { sapTlsInfoEntry 60 }

sapTlsL2ptForceBoundary OBJECT-TYPE
    SYNTAX          TruthValue
    MAX-ACCESS      read-write
    STATUS          current
    DESCRIPTION     "The value of sapTlsL2ptForceBoundary specifies if
                     sapTlsL2ptTermination is enforced for its managed SAP's.  
                     Setting the value of the object sapTlsL2ptForceBoundary of
                     a SAP in a Management VPLS to `true' forces all its 
                     managed SAP's to have sapTlsL2ptTermination enabled. This
                     value can only be `true' if the SAP belongs to a 
                     management VPLS. 
                     If this SAP has managed SAP's already with
                     sapTlsL2ptTermination disabled, it is not allowed
                     to set sapTlsL2ptForceBoundary to `true'."
    DEFVAL          { false }
    ::= { sapTlsInfoEntry 61 }

sapTlsLimitMacMoveLevel OBJECT-TYPE
    SYNTAX          TlsLimitMacMoveLevel
    MAX-ACCESS      read-write
    STATUS          current
    DESCRIPTION     "The value of the object sapTlsLimitMacMoveLevel
                     specifies the hierarchy in which SAPs are
                     blocked when a MAC-move limit is exceeded. When a MAC is
                     moving among multiple SAPs or spoke-SDPs, the SAP bind
                     or spoke-SDP bind with the lower level is blocked first.
                     (tertiary is the lowest)"
    DEFVAL          { tertiary }
    ::= { sapTlsInfoEntry 62 }

sapTlsBpduTransOper OBJECT-TYPE
    SYNTAX          INTEGER {
                        undefined (1),
                        disabled  (2),
                        pvst      (3),
                        stp       (4),
                        pvst-rw   (5)
                    }
    MAX-ACCESS      read-only
    STATUS          current
    DESCRIPTION     "The value of the object sapTlsBpduTransOper indicates
                     the operational bpdu encapsulation used for BPDU 
                     translated frames."
    ::= { sapTlsInfoEntry 63 }

sapTlsDefMsapPolicy OBJECT-TYPE
    SYNTAX          TPolicyStatementNameOrEmpty
    MAX-ACCESS      read-write
    STATUS          current
    DESCRIPTION     "The value of sapTlsDefMsapPolicy specifies the
                     default Managed SAP policy to use to create
                     Managed SAPs when the response from the Radius
                     server does not specify a Managed SAP policy.

                     The value of sapTlsDefMsapPolicy is only valid for
                     a SAP with a sapSubType value of 'capture'.
                     If the value is set to a non-empty string for a 
                     SAP with a sapSubType value other than 'capture',
                     an 'inconsistentValue' error will be returned.

                     The Managed SAP policy must be defined in
                     msapPlcyTable, otherwise an 'inconsistentValue'
                     error will be returned."
    DEFVAL         { "" }
    ::= { sapTlsInfoEntry 64 }

sapTlsL2ptProtocols OBJECT-TYPE
    SYNTAX          L2ptProtocols
    MAX-ACCESS      read-write
    STATUS          current
    DESCRIPTION     "The value of the object sapTlsL2ptTermination specifies
                     which L2 Protocol Tunnel pdu's are terminated
                     on this port or sap."
    DEFVAL          { { stp } }
    ::= { sapTlsInfoEntry 65 }

sapTlsL2ptForceProtocols OBJECT-TYPE
    SYNTAX          L2ptProtocols
    MAX-ACCESS      read-write
    STATUS          current
    DESCRIPTION     "The value of the object sapTlsL2ptForceProtocols specifies
                     which L2 Protocol Tunnel pdu's must be terminated by 
                     SAP's managed by this SAP.
                     This object is only relevant if the value of the object 
                     sapTlsL2ptForceBoundary is 'true'.
                     For every SAP managed by this SAP, each L2 protocol
                     specified by sapTlsL2ptForceProtocols must be terminated,
                     while other L2 protocols may or may not be terminated,
                     depending on the value of sapTlsL2ptProtocols of that
                     managed SAP."
    DEFVAL          { { stp } }
    ::= { sapTlsInfoEntry 66 }

sapTlsPppoeMsapTrigger OBJECT-TYPE
    SYNTAX          TruthValue
    MAX-ACCESS      read-write
    STATUS          current
    DESCRIPTION     "The value of sapTlsPppoeMsapTrigger specifies whether 
                     the receipt of PPPoE trigger packets on a VPLS SAP
                     with a sapSubType value of 'capture' will result in
                     a Radius authentication that will provide a service
                     context and the creation of a SAP with a sapSubType
                     value of 'managed'.

                     An attempt to set the value sapTlsPppoeMsapTrigger to 
                     'true' on a SAP with sapSubType other than 'capture'
                     will return an 'inconsistentValue' error."
    DEFVAL         { false }
    ::= { sapTlsInfoEntry 67 }

sapTlsDhcpMsapTrigger OBJECT-TYPE
    SYNTAX          TruthValue
    MAX-ACCESS      read-write
    STATUS          current
    DESCRIPTION     "The value of sapTlsDhcpMsapTrigger specifies whether
                     the receipt of DHCP trigger packets on this VPLS SAP
                     with a sapSubType value of 'capture' will result in
                     a Radius authentication that will provide a service
                     context and the creation of a SAP with a sapSubType
                     value of 'managed'.

                     An attempt to set the value sapTlsDhcpMsapTrigger to 
                     'true' on a SAP with sapSubType other than 'capture'
                     will return an 'inconsistentValue' error."
    DEFVAL         { false }
    ::= { sapTlsInfoEntry 68 }

sapTlsMrpJoinTime OBJECT-TYPE
    SYNTAX          Unsigned32 (1..10)
    UNITS           "deci-seconds"
    MAX-ACCESS      read-write
    STATUS          current
    DESCRIPTION     "The value of sapTlsMrpJoinTime specifies a timer value in
                    10ths of seconds which determines the maximum rate at
                    which attribute join messages can be sent on the SAP."
    DEFVAL         { 2 }
    ::= { sapTlsInfoEntry 69 }

sapTlsMrpLeaveTime OBJECT-TYPE
    SYNTAX          Unsigned32 (30..60)
    UNITS           "deci-seconds"
    MAX-ACCESS      read-write
    STATUS          current
    DESCRIPTION     "The value of sapTlsMrpLeaveTime specifies a timer value in
                    10ths of seconds which determines the amount of time a
                    registered attribute is held in leave state before the
                    registration is removed."
    DEFVAL         { 30 }
    ::= { sapTlsInfoEntry 70 }
    
sapTlsMrpLeaveAllTime OBJECT-TYPE
    SYNTAX          Unsigned32 (60..300)
    UNITS           "deci-seconds"
    MAX-ACCESS      read-write
    STATUS          current
    DESCRIPTION     "The value of sapTlsMrpLeaveAllTime specifies the a timer
                    value in 10ths of seconds which determines the frequency
                    where all attribute declarations on the SAP are all
                    refreshed."
    DEFVAL         { 100 }
    ::= { sapTlsInfoEntry 71 }
    
sapTlsMrpPeriodicTime OBJECT-TYPE
    SYNTAX          Unsigned32 (10..100)
    UNITS           "deci-seconds"
    MAX-ACCESS      read-write
    STATUS          current
    DESCRIPTION     "The value of sapTlsMrpPeriodicTime specifies a timer value
                    in 10ths of seconds which determines the frequency of
                    re-transmission of attribute declarations."
    DEFVAL         { 10 }
    ::= { sapTlsInfoEntry 72 }
    
sapTlsMrpPeriodicEnabled OBJECT-TYPE
    SYNTAX          TruthValue
    MAX-ACCESS      read-write
    STATUS          current
    DESCRIPTION     "The value of sapTlsMrpPeriodicEnabled specifies whether
                    re-transmission of attribute declarations is enabled."
    DEFVAL         { false }
    ::= { sapTlsInfoEntry 73 }

sapTlsPppoePolicy OBJECT-TYPE
    SYNTAX          TNamedItemOrEmpty
    MAX-ACCESS      read-write
    STATUS          current
    DESCRIPTION     "The value of sapTlsPppoePolicy specifies the PPPoE
                     policy (defined in TIMETRA-PPPOE-MIB::tmnxPppoePlcyTable)
                     to use to create Managed SAPs via PPPoE with PAP/CHAP
                     authentication.

                     The value of sapTlsPppoePolicy is only valid for a SAP
                     with a sapSubType value of 'capture'. If the value is set
                     to a  non-empty string for a SAP with a sapSubType value
                     other than 'capture', an 'inconsistentValue' error will
                     be returned.
                     
                     The value of sapTlsPppoePolicy is used for PPP sessions
                     where the value of 
                     TIMETRA-SUBSCRIBER-MGMT-MIB::tmnxSubPppType is equal to 
                     'oE' or 'oEoA'.
                     
                     In general, the default value is empty; for a SAP
                     with a sapSubType value of 'capture', the default value
                     is equal to default."
    DEFVAL         { "" }
    ::= { sapTlsInfoEntry 74 }

sapTlsArpMsapTrigger OBJECT-TYPE
    SYNTAX          TruthValue
    MAX-ACCESS      read-write
    STATUS          current
    DESCRIPTION     "The value of sapTlsArpMsapTrigger specifies whether
                     the receipt of ARP trigger packets on this VPLS SAP
                     with a sapSubType value of 'capture' will result in
                     a Radius authentication that will provide a service
                     context and the creation of a SAP with a sapSubType
                     value of 'managed'.

                     An attempt to set the value sapTlsArpMsapTrigger to 
                     'true' on a SAP with sapSubType other than 'capture'
                     will return an 'inconsistentValue' error."
    DEFVAL         { false }
    ::= { sapTlsInfoEntry 75 }

sapTlsDefMsapService OBJECT-TYPE
    SYNTAX          TmnxServId
    MAX-ACCESS      read-write
    STATUS          current
    DESCRIPTION     "The value of sapTlsDefMsapService specifies the
                     service ID of the service where Managed SAP's are created
                     when there is no Radius server available, or the Radius
                     server does not specify the service ID.

                     The value of sapTlsDefMsapService is only relevant for
                     a SAP with a sapSubType value of 'capture'.

                     While the value of sapTlsDefMsapService is equal to zero,
                     no Managed SAP's are created when there is no 
                     Radius server-specified service ID available. 

                     For a SAP with a sapSubType value other than 'capture',
                     zero is the only value allowed."
    DEFVAL         { 0 }
    ::= { sapTlsInfoEntry 76 }

sapTlsDefMsapGroupIf OBJECT-TYPE
    SYNTAX          TNamedItemOrEmpty
    MAX-ACCESS      read-write
    STATUS          current
    DESCRIPTION     "The value of sapTlsDefMsapGroupIf specifies the name of
                     the group interface where Managed SAP's are created
                     when there is no Radius server available, or the Radius
                     server does not specify the group interface.

                     The value of sapTlsDefMsapGroupIf is only relevant for
                     a SAP with a sapSubType value of 'capture'.

                     While the value of sapTlsDefMsapGroupIf is the empty 
                     string, no Managed SAP's are created when there is no 
                     Radius server-specified group interface available. 

                     For a SAP with a sapSubType value other than 'capture',
                     zero is the only value allowed."
    DEFVAL         { "" }
    ::= { sapTlsInfoEntry 77 }

sapTlsMrpPolicy OBJECT-TYPE
    SYNTAX          TNamedItemOrEmpty
    MAX-ACCESS      read-write
    STATUS          current
    DESCRIPTION     "The value of sapTlsMrpPolicy specifies the mrp
                     policy to control which Group BMAC attributes will 
                     advertise on the egress SAP-SDP.
                    "
    DEFVAL         { "" }
    ::= { sapTlsInfoEntry 78 }

sapTlsSiteName OBJECT-TYPE
    SYNTAX          TNamedItemOrEmpty
    MAX-ACCESS      read-only
    STATUS          current
    DESCRIPTION     "The value of sapTlsSiteName indicates the site-name
                     associated with this SAP."
    ::= { sapTlsInfoEntry 79 }

sapTlsDhcp6MsapTrigger OBJECT-TYPE
    SYNTAX          TruthValue
    MAX-ACCESS      read-write
    STATUS          current
    DESCRIPTION     "The value of sapTlsDhcp6MsapTrigger specifies whether
                     the receipt of DHCPv6 trigger packets on this VPLS SAP
                     with a sapSubType value of 'capture' will result in
                     a Radius authentication that will provide a service
                     context and the creation of a SAP with a sapSubType
                     value of 'managed'.

                     An attempt to set the value sapTlsDhcp6MsapTrigger to 
                     'true' on a SAP with sapSubType other than 'capture'
                     will return an 'inconsistentValue' error."
    DEFVAL         { false }
    ::= { sapTlsInfoEntry 80 }

sapTlsShcvRetryTimeout OBJECT-TYPE
    SYNTAX          TmnxSubShcvRetryTimeout
    UNITS           "seconds"
    MAX-ACCESS      read-write
    STATUS          current
    DESCRIPTION     "The value of the object sapTlsShcvRetryTimeout specifies
                     the timeout in seconds before a connectivity check
                     retransmission."
    DEFVAL          { 10 }
    ::= { sapTlsInfoEntry 81 }

sapTlsShcvRetryCount OBJECT-TYPE
    SYNTAX          TmnxSubShcvRetryCount
    MAX-ACCESS      read-write
    STATUS          current
    DESCRIPTION     "The value of the object sapTlsShcvRetryCount specifies
                     the number of connectivity check retransmissions.
                     
                     Setting the value to n specifies that, for any given host,
                     at most (n+1) probes are done each interval, 
                     and (n+1) missed replies are considered as a connectivity 
                     failure."
    DEFVAL          { 2 }
    ::= { sapTlsInfoEntry 82 }

sapTlsDataSapInstStatus OBJECT-TYPE
    SYNTAX          TmnxSapInstStatus
    MAX-ACCESS      read-only
    STATUS          current
    DESCRIPTION     "The value of sapTlsDataSapInstStatus indicates the status
                     of the SAP which is instantiating other SAPs controlled
                     by this SAP. 
                     
                     This object is valid for services with 
                     TIMETRA-SERV-MIB::svcMgmtVpls set to 'true'."
    ::= { sapTlsInfoEntry 83 }

sapTlsDataSapInstLastErr OBJECT-TYPE
    SYNTAX          DisplayString
    MAX-ACCESS      read-only
    STATUS          current
    DESCRIPTION     "The value of sapTlsDataSapInstLastErr indicates last
                     error encountered while instantiating SAPs controlled
                     by this SAP.
                     
                     This object is valid for services with 
                     TIMETRA-SERV-MIB::svcMgmtVpls set to 'true'."
    ::= { sapTlsInfoEntry 84 }

sapTlsMvrpAdminStatus OBJECT-TYPE
    SYNTAX        TmnxEnabledDisabled
    MAX-ACCESS    read-write
    STATUS        current
    DESCRIPTION
        "The value of sapTlsMvrpAdminStatus specifies whether MVRP
        is enabled on this SAP.

        The default value of sapTlsMvrpAdminStatus is set to 'enabled' for
        MVRP enabled services."
    DEFVAL { disabled }
    ::= { sapTlsInfoEntry 85 }

sapTlsMvrpOperStatus OBJECT-TYPE
    SYNTAX        TmnxEnabledDisabled
    MAX-ACCESS    read-only
    STATUS        current
    DESCRIPTION
        "The value of sapTlsMvrpOperStatus indicates operational status
        of MVRP on this SAP."
    ::= { sapTlsInfoEntry 86 }

sapTlsInTcBitBpdus OBJECT-TYPE
    SYNTAX          Counter32
    MAX-ACCESS      read-only
    STATUS          current
    DESCRIPTION     "The value of the object  sapTlsInTcBitBpdus indicates the
                     number of BPDUs received on this SAP
                     with the Topology Change bit set."
    ::= { sapTlsInfoEntry 87 }

sapTlsOutTcBitBpdus OBJECT-TYPE
    SYNTAX          Counter32
    MAX-ACCESS      read-only
    STATUS          current
    DESCRIPTION     "The value of the object  sapTlsOutTcBitBpdus indicates the
                     number of BPDUs sent out this SAP
                     with the Topology Change bit set."
    ::= { sapTlsInfoEntry 88 }

sapTlsPppMsapTrigger OBJECT-TYPE
    SYNTAX          TruthValue
    MAX-ACCESS      read-write
    STATUS          current
    DESCRIPTION     "The value of sapTlsPppMsapTrigger specifies whether 
                     the receipt of PPP trigger packets on a VPLS SAP
                     with a sapSubType value of 'capture' will result in
                     a Radius authentication that will provide a service
                     context and the creation of a SAP with a sapSubType
                     value of 'managed'.

                     An attempt to set the value sapTlsPppoeMsapTrigger to 
                     'true' on a SAP with sapSubType other than 'capture'
                     will return an 'inconsistentValue' error."
    DEFVAL         { false }
    ::= { sapTlsInfoEntry 89 }

sapTlsPppPolicy OBJECT-TYPE
    SYNTAX          TNamedItemOrEmpty
    MAX-ACCESS      read-write
    STATUS          current
    DESCRIPTION     "The value of sapTlsPppPolicy specifies the 
                     policy (defined in TIMETRA-PPPOE-MIB::tmnxPppoePlcyTable)
                     to use to create Managed SAPs via PPP with PAP/CHAP
                     authentication.

                     The value of sapTlsPppPolicy is only valid for a SAP
                     with a sapSubType value of 'capture'. If the value is set
                     to a  non-empty string for a SAP with a sapSubType value
                     other than 'capture', an 'inconsistentValue' error will
                     be returned.
                     
                     The value of sapTlsPppPolicy is used for PPP sessions
                     where the value of 
                     TIMETRA-SUBSCRIBER-MGMT-MIB::tmnxSubPppType is equal to 
                     'oA', as opposed to 'oE' or 'oEoA'.
                     
                     In general, the default value is empty; for a SAP
                     with a sapSubType value of 'capture', the default value
                     is equal to default."
    DEFVAL         { "" }
    ::= { sapTlsInfoEntry 90 }

sapTlsTrackSrrpInst OBJECT-TYPE
    SYNTAX          Unsigned32
    MAX-ACCESS      read-write
    STATUS          current
    DESCRIPTION     "The value of sapTlsTrackSrrpInst specifies the 
                     SRRP instance to track."
    DEFVAL         { 0 }
    ::= { sapTlsInfoEntry 91 }

sapTlsPppUserDb OBJECT-TYPE
    SYNTAX      TNamedItemOrEmpty
    MAX-ACCESS  read-write
    STATUS      current
    DESCRIPTION
        "The value of sapTlsPppUserDb specifies the local user database
         to use for PPP PAP/CHAP based authentication.

         If no authentication with the local user database is required, the
         value of this object must be set to the empty string.

         The value of sapTlsPppUserDb is only valid for a SAP
         with a sapSubType value of 'capture'. If the value is set
         to a  non-empty string for a SAP with a sapSubType value
         other than 'capture', an 'inconsistentValue' error will
         be returned.
         
         The value of sapTlsPppUserDb is used for PPP sessions
         where the value of 
         TIMETRA-SUBSCRIBER-MGMT-MIB::tmnxSubPppType is equal to 
         'oA', as opposed to 'oE' or 'oEoA'."
    DEFVAL { "" }
    ::= { sapTlsInfoEntry 92 }

sapTlsPppoeUserDb OBJECT-TYPE
    SYNTAX      TNamedItemOrEmpty
    MAX-ACCESS  read-write
    STATUS      current
    DESCRIPTION
        "The value of sapTlsPppoeUserDb specifies the local user database
         to use for PPPoE PADI PAP/CHAP based authentication.

         If no authentication with the local user database is required, the
         value of this object must be set to the empty string.

         The value of sapTlsPppoeUserDb is only valid for a SAP
         with a sapSubType value of 'capture'. If the value is set
         to a  non-empty string for a SAP with a sapSubType value
         other than 'capture', an 'inconsistentValue' error will
         be returned.
         
         The value of sapTlsPppoeUserDb is used for PPP sessions
         where the value of 
         TIMETRA-SUBSCRIBER-MGMT-MIB::tmnxSubPppType is equal to 
         'oE' or 'oEoA', as opposed to 'oA'."
    DEFVAL { "" }
    ::= { sapTlsInfoEntry 93 }

sapTlsDhcpUserDb OBJECT-TYPE
    SYNTAX      TNamedItemOrEmpty
    MAX-ACCESS  read-write
    STATUS      current
    DESCRIPTION
        "The value of sapTlsDhcpUserDb specifies the local user database
         to use for DHCP based authentication.

         If no authentication with the local user database is required, the
         value of this object must be set to the empty string.

         The value of sapTlsDhcpUserDb is only valid for a SAP
         with a sapSubType value of 'capture'. If the value is set
         to a  non-empty string for a SAP with a sapSubType value
         other than 'capture', an 'inconsistentValue' error will
         be returned."
    DEFVAL { "" }
    ::= { sapTlsInfoEntry 94 }

sapTlsAutoLearnMacProtect   OBJECT-TYPE
    SYNTAX      TruthValue
    MAX-ACCESS  read-write
    STATUS      current
    DESCRIPTION
        "The value of sapTlsAutoLearnMacProtect specifies whether
         to enable automatic population of the MAC protect list with
         source MAC addresses learned on the associated SAP."
    DEFVAL { false }
    ::= { sapTlsInfoEntry 95 }

sapTlsDhcp6UserDb OBJECT-TYPE
    SYNTAX      TNamedItemOrEmpty
    MAX-ACCESS  read-write
    STATUS      current
    DESCRIPTION
        "The value of sapTlsDhcp6UserDb specifies the local user database
         to use for DHCP6 based authentication.

         If no authentication with the local user database is required, the
         value of this object must be set to the empty string.

         The value of sapTlsDhcp6UserDb is only valid for a SAP
         with a sapSubType value of 'capture'. If the value is set
         to a  non-empty string for a SAP with a sapSubType value
         other than 'capture', an 'inconsistentValue' error will
         be returned."
    DEFVAL { "" }
    ::= { sapTlsInfoEntry 96 }

sapTlsShcvPolicyIpv4 OBJECT-TYPE
    SYNTAX      TNamedItemOrEmpty
    MAX-ACCESS  read-write
    STATUS      current
    DESCRIPTION
        "The value of sapTlsShcvPolicyIpv4 specifies the Subscriber Host Connectivity Verification (SHCV)
         policy for IPv4 only.

         A non empty value must correspond to a conceptual row in the TIMETRA-SUBSCRIBER-MGMT-MIB::tmnxSubShcvPlcyTable.
         
         A non empty value is only allowed while the value of sapTlsShcvInterval is equal to zero."
    DEFVAL { "" }
    ::= { sapTlsInfoEntry 98 }

-- ---------------------------------------------------------------------
-- ATM SAP Table
--
--
--  Sparse Dependent Extention of the sapBaseInfoTable.
--
--  The same indexes are used for both the base table, sapBaseInfoTable,
--  and the sparse dependent table, sapAtmInfoTable.
--
--  This in effect extends the sapBaseInfoTable with additional columns.
--  Rows are created in the sapAtmInfoTable only for those entries
--  in the sapBaseInfoTable that are created on a port that 'atmEncap' set
--- for port encapsulation.
--
--  Deletion of a row in the sapBaseInfoTable results in the
--  same fate for the row in the sapAtmInfoTable.
-- ---------------------------------------------------------------------
sapAtmInfoTable OBJECT-TYPE
    SYNTAX          SEQUENCE OF SapAtmInfoEntry
    MAX-ACCESS      not-accessible
    STATUS          current
    DESCRIPTION     "A table that contains ATM SAP information."
    ::= { tmnxSapObjs 4 }

sapAtmInfoEntry OBJECT-TYPE
    SYNTAX          SapAtmInfoEntry
    MAX-ACCESS      not-accessible
    STATUS          current
    DESCRIPTION     "Information about a specific ATM SAP."
    INDEX           { svcId, sapPortId, sapEncapValue }
    ::= { sapAtmInfoTable 1 }

SapAtmInfoEntry ::=
    SEQUENCE {
        sapAtmEncapsulation              TmnxSapAtmEncapsulation,
        sapAtmIngressTrafficDescIndex    AtmTrafficDescrParamIndex,
        sapAtmEgressTrafficDescIndex     AtmTrafficDescrParamIndex,
        sapAtmOamAlarmCellHandling       ServiceAdminStatus,
        sapAtmOamTerminate               ServiceAdminStatus,
        sapAtmOamPeriodicLoopback        ServiceAdminStatus,
        sapAtmLLFAdminStatus             ServiceAdminStatus,
        sapAtmLLFOperStatus              INTEGER,
        sapAtmSubPppIndex                Unsigned32,
        sapAtmDetectedEncapsulation      TmnxSapAtmEncapsulation,
        sapAtmIngressTrafficDescIndexOvr AtmTrafficDescrParamIndex,
        sapAtmEgressTrafficDescIndexOvr  AtmTrafficDescrParamIndex
  }

sapAtmEncapsulation OBJECT-TYPE
    SYNTAX           TmnxSapAtmEncapsulation
    MAX-ACCESS       read-write
    STATUS           current
    DESCRIPTION      "This object specifies the data encapsulation used
                      over the AAL5 SSCS layer.  The definition references
                      RFC 2684 Multiprotocol Encapsulation over ATM AAL5
                      and to the ATM Forum LAN Emulation specification."
    DEFVAL           { llcSnapRoutedProtocol }
    ::= { sapAtmInfoEntry 1 }

sapAtmIngressTrafficDescIndex OBJECT-TYPE
    SYNTAX           AtmTrafficDescrParamIndex(1..1000)
    MAX-ACCESS       read-write
    STATUS           current
    DESCRIPTION      "This object specifies the index of the ATM traffic
                      descriptor in the ATM traffic data encapsulation used
                      in for the ingress direction over the AAL5 SSCS layer.
                      The definition references RFC 2684 Multiprotocol
                      Encapsulation over ATM AAL5 and to the ATM Forum LAN
                      Emulation specification."
    DEFVAL           { 1 }
    ::= { sapAtmInfoEntry 2 }

sapAtmEgressTrafficDescIndex OBJECT-TYPE
    SYNTAX           AtmTrafficDescrParamIndex(1..1000)
    MAX-ACCESS       read-write
    STATUS           current
    DESCRIPTION      "This object specifies the index of the ATM traffic
                      descriptor in the ATM traffic data encapsulation used
                      in for the egress direction over the AAL5 SSCS layer.
                      The definition references RFC 2684 Multiprotocol
                      Encapsulation over ATM AAL5 and to the ATM Forum LAN
                      Emulation specification."
    DEFVAL           { 1 }
    ::= { sapAtmInfoEntry 3 }

sapAtmOamAlarmCellHandling OBJECT-TYPE
    SYNTAX           ServiceAdminStatus
    MAX-ACCESS       read-write
    STATUS           current
    DESCRIPTION      "A value of up specifies that the OAM status of a pvc
                      affects  the  sap  operational  status and OAM AIS/RDI
                      cell generation upon a sap operational status of down.
                      A value of down specifies that the OAM status of a pvc
                      will   not   affect  the  operational  status  of  the
                      associated   sap   and   no   OAM  AIS/RDI  cells  are
                      generated."
    DEFVAL          { up }
    ::= { sapAtmInfoEntry 4 }

sapAtmOamTerminate OBJECT-TYPE
    SYNTAX           ServiceAdminStatus
    MAX-ACCESS       read-write
    STATUS           current
    DESCRIPTION      "The sapAtmOamTerminate object specifies whether this
                      SAP will act as an OAM termination point.
                      If enabled, OAM cells will be sunk by the SAP and can
                      affect the SAP's operational status (if
                      sapAtmOamAlarmCellHandling is also enabled). Otherwise
                      the OAM cells will be passed into the APIPE service.
                      This object is only configurable for ATM SAPs that are
                      part of an APIPE service SDU or VCC mode. If the 
                      sapPortId belongs to an Multi-Chassis APS port, the
                      default value is up."
    DEFVAL           { down }
    ::= { sapAtmInfoEntry 5 }

sapAtmOamPeriodicLoopback OBJECT-TYPE
    SYNTAX           ServiceAdminStatus
    MAX-ACCESS       read-write
    STATUS           current
    DESCRIPTION      "The sapAtmOamPeriodicLoopback object specifies whether
                      this SAP will run periodic OAM loopbacks or not.  If
                      enabled, an ATM OAM loopback cell will be transmitted
                      every period as configured in tAtmSysOamLoopbackPeriod.
                      If a response is not received and tAtmSysOamRetryDown
                      consecutive retries also result in failure, the endpoint
                      will transition to the eteAisLoc state.  Once in the
                      eteAisLoc state, an ATM OAM loopback cell will be
                      transmitted every period as configured in
                      tAtmSysOamLoopbackPeriod. If a response is received for
                      the periodic loopback and tAtmSysOamRetryUp consecutive
                      retries also each receive a response, the endpoint will
                      transition back to the up state.  This object is only
                      configurable on IES or VPRN service endpoints."
    DEFVAL           { down }
    ::= { sapAtmInfoEntry 6 }

sapAtmLLFAdminStatus OBJECT-TYPE
    SYNTAX          ServiceAdminStatus
    MAX-ACCESS      read-write
    STATUS          current
    DESCRIPTION     "sapAtmLLFAdminStatus specifies whether or not Link-
                    Loss Forwarding is enabled ('up'). When this object is set
                    to 'up' the underlying port will be forced into the
                    operationally 'down' state if the service is operationally
                    'down', or any of the 'sdpBindPwPeerStatusBits' are set,
                    and will set the underlying port's
                    tmnxPortReasonDownFlags 'linklossFwd' bit. Setting
                    this object to 'down' will clear the 'linklossFwd' reason.
                    sapAtmLLFAdminStatus can only be enabled on saps 
                    configured for an APIPE service using an 
                    port with the tmnxPortEncapType set to 'atmEncap' and
                    sapEncapValue set for ATM ports."
    DEFVAL          { down }
    ::= { sapAtmInfoEntry 7 }

sapAtmLLFOperStatus OBJECT-TYPE
    SYNTAX          INTEGER {
                        fault (1),   -- service is down or fault detected.
                        clear (2)    -- service is up and no fault detected.
                    }
    MAX-ACCESS      read-only
    STATUS          current
    DESCRIPTION     "sapAtmLLFOperStatus indicates whether or not the
                    underlying port is forced operationally 'down' due to the
                    service being operationally 'down' or an
                    sdpBindPwPeerStatusBits bit is set. 
                    sapAtmLLFOperStatus is set to 'fault' when the 
                    sapAtmLLFAdminStatus is set to 'up,' and either a 
                    fault has occurred on the pseudo-wire, or the service is 
                    down, otherwise sapAtmLLFOperStatus is set to 'clear.'"
    ::= { sapAtmInfoEntry 8 }

sapAtmSubPppIndex OBJECT-TYPE
    SYNTAX          Unsigned32
    MAX-ACCESS      read-only
    STATUS          current
    DESCRIPTION     "The value of sapAtmSubPppIndex indicates 
                     the local identifier of the subscriber PPP session.
    
                     It is the index of the corresponding conceptual row in the
                     TIMETRA-SUBSCRIBER-MGMT-MIB::tmnxSubPppTable.
                     
                     The value zero indicates that there is no subscriber PPP
                     session associated with this SAP."
    ::= { sapAtmInfoEntry 10 }
    
sapAtmDetectedEncapsulation OBJECT-TYPE
    SYNTAX          TmnxSapAtmEncapsulation
    MAX-ACCESS      read-only
    STATUS          current
    DESCRIPTION     "This object indicates the AAL5 data encapsulation 
                     detected by PPPoA (PPP over ATM) or PPPoEoA (PPP over
                     Ethernet over ATM).
                     
                     The value is only applicable if sapAtmEncapsulation is
                     set to 'auto' and returns 'unknown' as long as no
                     encapsulation is detected.
                     
                     If sapAtmEncapsulation is set to a value different than
                     'auto', sapAtmDetectedEncapsulation always returns the
                     same value as sapAtmEncapsulation."
    ::= { sapAtmInfoEntry 11 }
    
sapAtmIngressTrafficDescIndexOvr OBJECT-TYPE
    SYNTAX           AtmTrafficDescrParamIndex(0|1..1000)
    MAX-ACCESS       read-only
    STATUS           current
    DESCRIPTION      "This object indicates the index of the ATM 
                      ingress traffic descriptor override.
                      
                      This override value is given by an AAA server 
                      such as a RADIUS server.
                      
                      The value zero indicates that no override is given."
    ::= { sapAtmInfoEntry 12 }

sapAtmEgressTrafficDescIndexOvr OBJECT-TYPE
    SYNTAX           AtmTrafficDescrParamIndex(0|1..1000)
    MAX-ACCESS       read-only
    STATUS           current
    DESCRIPTION      "This object indicates the index of the ATM 
                      egress traffic descriptor override.
                      
                      This override value is given by an AAA server 
                      such as a RADIUS server.
                      
                      The value zero indicates that no override is given."
    ::= { sapAtmInfoEntry 13 }

-- ---------------------------------
-- Base SAP Statistics Table
-- ---------------------------------
sapBaseStatsTable OBJECT-TYPE
    SYNTAX          SEQUENCE OF SapBaseStatsEntry
    MAX-ACCESS      not-accessible
    STATUS          current
    DESCRIPTION     "A table that contains basic SAP statistics.
                     In the descriptions below 'Pchip' refers
                     to the Nokia SROS series Packet Processing
                     chip, while 'Qchip' refers to the Nokia
                     SROS series QoS Queueing Engine chip."
    ::= { tmnxSapObjs 6 }

sapBaseStatsEntry OBJECT-TYPE
    SYNTAX          SapBaseStatsEntry
    MAX-ACCESS      not-accessible
    STATUS          current
    DESCRIPTION     "Basic statistics about a specific SAP."
    INDEX           { svcId, sapPortId, sapEncapValue }
    ::= { sapBaseStatsTable 1 }

SapBaseStatsEntry ::=
    SEQUENCE {
        sapBaseStatsIngressPchipDroppedPackets          Counter64,
        sapBaseStatsIngressPchipDroppedOctets           Counter64,
        sapBaseStatsIngressPchipOfferedHiPrioPackets    Counter64,
        sapBaseStatsIngressPchipOfferedHiPrioOctets     Counter64,
        sapBaseStatsIngressPchipOfferedLoPrioPackets    Counter64,
        sapBaseStatsIngressPchipOfferedLoPrioOctets     Counter64,
        sapBaseStatsIngressQchipDroppedHiPrioPackets    Counter64,
        sapBaseStatsIngressQchipDroppedHiPrioOctets     Counter64,
        sapBaseStatsIngressQchipDroppedLoPrioPackets    Counter64,
        sapBaseStatsIngressQchipDroppedLoPrioOctets     Counter64,
        sapBaseStatsIngressQchipForwardedInProfPackets  Counter64,
        sapBaseStatsIngressQchipForwardedInProfOctets   Counter64,
        sapBaseStatsIngressQchipForwardedOutProfPackets Counter64,
        sapBaseStatsIngressQchipForwardedOutProfOctets  Counter64,
        sapBaseStatsEgressQchipDroppedInProfPackets     Counter64,
        sapBaseStatsEgressQchipDroppedInProfOctets      Counter64,
        sapBaseStatsEgressQchipDroppedOutProfPackets    Counter64,
        sapBaseStatsEgressQchipDroppedOutProfOctets     Counter64,
        sapBaseStatsEgressQchipForwardedInProfPackets   Counter64,
        sapBaseStatsEgressQchipForwardedInProfOctets    Counter64,
        sapBaseStatsEgressQchipForwardedOutProfPackets  Counter64,
        sapBaseStatsEgressQchipForwardedOutProfOctets   Counter64,
        sapBaseStatsCustId                              TmnxCustId,
        sapBaseStatsIngressPchipOfferedUncoloredPackets Counter64,
        sapBaseStatsIngressPchipOfferedUncoloredOctets  Counter64,
        sapBaseStatsAuthenticationPktsDiscarded         Counter32,
        sapBaseStatsAuthenticationPktsSuccess           Counter32,
        sapBaseStatsLastClearedTime                     TimeStamp,
        sapBaseStatsIngressCPMPackets                   Counter64,
        sapBaseStatsIngressCPMPacketsHi                 Counter32,
        sapBaseStatsIngressCPMPacketsLo                 Counter32,
        sapBaseStatsIngressCPMOctets                    Counter64,
        sapBaseStatsIngressCPMOctetsHi                  Counter32,
        sapBaseStatsIngressCPMOctetsLo                  Counter32,
        sapBaseStatsIngPchipRcvdValidPkt                Counter64,
        sapBaseStatsIngPchipRcvdValidOct                Counter64
    }

sapBaseStatsIngressPchipDroppedPackets OBJECT-TYPE
    SYNTAX          Counter64
    MAX-ACCESS      read-only
    STATUS          current
    DESCRIPTION     "The number of packets dropped by the
                     ingress Pchip due to: SAP state,
                     ingress MAC, IP or IPv6 filter, same segment
                     discard, bad checksum, etc."
    ::= { sapBaseStatsEntry 1 }

sapBaseStatsIngressPchipDroppedOctets OBJECT-TYPE
    SYNTAX          Counter64
    MAX-ACCESS      read-only
    STATUS          current
    DESCRIPTION     "The number of octets dropped by the
                     ingress Pchip due to: SAP state,
                     ingress MAC, IP or IPv6 filter, same segment
                     discard, bad checksum, etc."
    ::= { sapBaseStatsEntry 2 }

sapBaseStatsIngressPchipOfferedHiPrioPackets OBJECT-TYPE
    SYNTAX          Counter64
    MAX-ACCESS      read-only
    STATUS          current
    DESCRIPTION     "The number of high priority packets,
                     as determined by the SAP ingress QoS
                     policy, offered by the Pchip to the
                     Qchip."
    ::= { sapBaseStatsEntry 3 }

sapBaseStatsIngressPchipOfferedHiPrioOctets OBJECT-TYPE
    SYNTAX          Counter64
    MAX-ACCESS      read-only
    STATUS          current
    DESCRIPTION     "The number of high priority octets,
                     as determined by the SAP ingress QoS
                     policy, offered by the Pchip to the
                     Qchip."
    ::= { sapBaseStatsEntry 4 }

sapBaseStatsIngressPchipOfferedLoPrioPackets OBJECT-TYPE
    SYNTAX          Counter64
    MAX-ACCESS      read-only
    STATUS          current
    DESCRIPTION     "The number of low priority packets,
                     as determined by the SAP ingress QoS
                     policy, offered by the Pchip to the
                     Qchip."
    ::= { sapBaseStatsEntry 5 }

sapBaseStatsIngressPchipOfferedLoPrioOctets OBJECT-TYPE
    SYNTAX          Counter64
    MAX-ACCESS      read-only
    STATUS          current
    DESCRIPTION     "The number of low priority octets,
                     as determined by the SAP ingress QoS
                     policy, offered by the Pchip to the
                     Qchip."
    ::= { sapBaseStatsEntry 6 }

sapBaseStatsIngressQchipDroppedHiPrioPackets OBJECT-TYPE
    SYNTAX          Counter64
    MAX-ACCESS      read-only
    STATUS          current
    DESCRIPTION     "The number of high priority packets,
                     as determined by the SAP ingress QoS
                     policy, dropped by the Qchip due to:
                     MBS exceeded, buffer pool limit
                     exceeded, etc."
    ::= { sapBaseStatsEntry 7 }

sapBaseStatsIngressQchipDroppedHiPrioOctets OBJECT-TYPE
    SYNTAX          Counter64
    MAX-ACCESS      read-only
    STATUS          current
    DESCRIPTION     "The number of high priority octets,
                     as determined by the SAP ingress QoS
                     policy, dropped by the Qchip due to:
                     MBS exceeded, buffer pool limit
                     exceeded, etc."
    ::= { sapBaseStatsEntry 8 }

sapBaseStatsIngressQchipDroppedLoPrioPackets OBJECT-TYPE
    SYNTAX          Counter64
    MAX-ACCESS      read-only
    STATUS          current
    DESCRIPTION     "The number of low priority packets,
                     as determined by the SAP ingress QoS
                     policy, dropped by the Qchip due to:
                     MBS exceeded, buffer pool limit
                     exceeded, etc."
    ::= { sapBaseStatsEntry 9 }

sapBaseStatsIngressQchipDroppedLoPrioOctets OBJECT-TYPE
    SYNTAX          Counter64
    MAX-ACCESS      read-only
    STATUS          current
    DESCRIPTION     "The number of low priority octets,
                     as determined by the SAP ingress QoS
                     policy, dropped by the Qchip due to:
                     MBS exceeded, buffer pool limit
                     exceeded, etc."
    ::= { sapBaseStatsEntry 10 }

sapBaseStatsIngressQchipForwardedInProfPackets OBJECT-TYPE
    SYNTAX          Counter64
    MAX-ACCESS      read-only
    STATUS          current
    DESCRIPTION     "The number of in-profile packets
                     (rate below CIR) forwarded by the
                     ingress Qchip."
    ::= { sapBaseStatsEntry 11 }

sapBaseStatsIngressQchipForwardedInProfOctets OBJECT-TYPE
    SYNTAX          Counter64
    MAX-ACCESS      read-only
    STATUS          current
    DESCRIPTION     "The number of in-profile octets
                     (rate below CIR) forwarded by the
                     ingress Qchip."
    ::= { sapBaseStatsEntry 12 }

sapBaseStatsIngressQchipForwardedOutProfPackets OBJECT-TYPE
    SYNTAX          Counter64
    MAX-ACCESS      read-only
    STATUS          current
    DESCRIPTION     "The number of out-of-profile packets
                     (rate above CIR) forwarded by the
                     ingress Qchip."
    ::= { sapBaseStatsEntry 13 }

sapBaseStatsIngressQchipForwardedOutProfOctets OBJECT-TYPE
    SYNTAX          Counter64
    MAX-ACCESS      read-only
    STATUS          current
    DESCRIPTION     "The number of out-of-profile octets
                     (rate above CIR) forwarded by the
                     ingress Qchip."
    ::= { sapBaseStatsEntry 14 }

sapBaseStatsEgressQchipDroppedInProfPackets OBJECT-TYPE
    SYNTAX          Counter64
    MAX-ACCESS      read-only
    STATUS          current
    DESCRIPTION     "The number of in-profile packets
                     discarded by the egress Qchip due
                     to: MBS exceeded, buffer pool limit
                     exceeded, etc."
    ::= { sapBaseStatsEntry 15 }

sapBaseStatsEgressQchipDroppedInProfOctets OBJECT-TYPE
    SYNTAX          Counter64
    MAX-ACCESS      read-only
    STATUS          current
    DESCRIPTION     "The number of in-profile octets
                     discarded by the egress Qchip due
                     to: MBS exceeded, buffer pool limit
                     exceeded, etc."
    ::= { sapBaseStatsEntry 16 }

sapBaseStatsEgressQchipDroppedOutProfPackets OBJECT-TYPE
    SYNTAX          Counter64
    MAX-ACCESS      read-only
    STATUS          current
    DESCRIPTION     "The number of out-of-profile packets
                     discarded by the egress Qchip due
                     to: MBS exceeded, buffer pool limit
                     exceeded, etc."
    ::= { sapBaseStatsEntry 17 }

sapBaseStatsEgressQchipDroppedOutProfOctets OBJECT-TYPE
    SYNTAX          Counter64
    MAX-ACCESS      read-only
    STATUS          current
    DESCRIPTION     "The number of out-of-profile packets
                     discarded by the egress Qchip due
                     to: MBS exceeded, buffer pool limit
                     exceeded, etc."
    ::= { sapBaseStatsEntry 18 }

sapBaseStatsEgressQchipForwardedInProfPackets OBJECT-TYPE
    SYNTAX          Counter64
    MAX-ACCESS      read-only
    STATUS          current
    DESCRIPTION     "The number of in-profile packets
                     (rate below CIR) forwarded by the
                     egress Qchip."
    ::= { sapBaseStatsEntry 19 }

sapBaseStatsEgressQchipForwardedInProfOctets OBJECT-TYPE
    SYNTAX          Counter64
    MAX-ACCESS      read-only
    STATUS          current
    DESCRIPTION     "The number of in-profile octets
                     (rate below CIR) forwarded by the
                     egress Qchip."
    ::= { sapBaseStatsEntry 20 }

sapBaseStatsEgressQchipForwardedOutProfPackets OBJECT-TYPE
    SYNTAX          Counter64
    MAX-ACCESS      read-only
    STATUS          current
    DESCRIPTION     "The number of out-of-profile packets
                     (rate above CIR) forwarded by the
                     egress Qchip."
    ::= { sapBaseStatsEntry 21 }

sapBaseStatsEgressQchipForwardedOutProfOctets OBJECT-TYPE
    SYNTAX          Counter64
    MAX-ACCESS      read-only
    STATUS          current
    DESCRIPTION     "The number of out-of-profile octets
                     (rate above CIR) forwarded by the
                     egress Qchip."
    ::= { sapBaseStatsEntry 22 }

sapBaseStatsCustId OBJECT-TYPE
    SYNTAX          TmnxCustId
    MAX-ACCESS      read-only
    STATUS          current
    DESCRIPTION     "The Customer ID for the associated service."
    ::= { sapBaseStatsEntry 23 }

sapBaseStatsIngressPchipOfferedUncoloredPackets OBJECT-TYPE
    SYNTAX          Counter64
    MAX-ACCESS      read-only
    STATUS          current
    DESCRIPTION     "The number of uncolored packets,
                     as determined by the SAP ingress QoS
                     policy, offered by the Pchip to the
                     Qchip."
    ::= { sapBaseStatsEntry 24 }

sapBaseStatsIngressPchipOfferedUncoloredOctets OBJECT-TYPE
    SYNTAX          Counter64
    MAX-ACCESS      read-only
    STATUS          current
    DESCRIPTION     "The number of uncolored octets,
                     as determined by the SAP ingress QoS
                     policy, offered by the Pchip to the
                     Qchip."
    ::= { sapBaseStatsEntry 25 }

sapBaseStatsAuthenticationPktsDiscarded OBJECT-TYPE
    SYNTAX          Counter32
    MAX-ACCESS      read-only
    STATUS          current
    DESCRIPTION     "The number of DHCP packets discarded
                     as result of authentication."
    ::= { sapBaseStatsEntry 26 }

sapBaseStatsAuthenticationPktsSuccess OBJECT-TYPE
    SYNTAX          Counter32
    MAX-ACCESS      read-only
    STATUS          current
    DESCRIPTION     "The number of DHCP packets successfully authenticated."
    ::= { sapBaseStatsEntry 27 }

sapBaseStatsLastClearedTime OBJECT-TYPE
    SYNTAX          TimeStamp
    MAX-ACCESS      read-only
    STATUS          current
    DESCRIPTION     "The value of sapBaseStatsLastClearedTime indicates
                     the sysUpTime when the counters in this table were
                     last cleared."
    ::= { sapBaseStatsEntry 28 }

sapBaseStatsIngressCPMPackets OBJECT-TYPE
    SYNTAX          Counter64
    MAX-ACCESS      read-only
    STATUS          current
    DESCRIPTION     "The value of sapBaseStatsIngressCPMPackets indicates
                     ingress traffic in terms of packets destined to CPM
                     associated with this SAP."
    ::= { sapBaseStatsEntry 29 }

sapBaseStatsIngressCPMPacketsHi OBJECT-TYPE
    SYNTAX          Counter32
    MAX-ACCESS      read-only
    STATUS          current
    DESCRIPTION     "The value of sapBaseStatsIngressCPMPacketsHi indicates
                     upper 32 bits of sapBaseStatsIngressCPMPackets object."
    ::= { sapBaseStatsEntry 30 }

sapBaseStatsIngressCPMPacketsLo OBJECT-TYPE
    SYNTAX          Counter32
    MAX-ACCESS      read-only
    STATUS          current
    DESCRIPTION     "The value of sapBaseStatsIngressCPMPacketsHi indicates
                     lower 32 bits of sapBaseStatsIngressCPMPackets object."
    ::= { sapBaseStatsEntry 31 }

sapBaseStatsIngressCPMOctets OBJECT-TYPE
    SYNTAX          Counter64
    MAX-ACCESS      read-only
    STATUS          current
    DESCRIPTION     "The value of sapBaseStatsIngressCPMOctets indicates
                     ingress traffic in terms of bytes destined to CPM
                     associated with this SAP."
    ::= { sapBaseStatsEntry 32 }

sapBaseStatsIngressCPMOctetsHi OBJECT-TYPE
    SYNTAX          Counter32
    MAX-ACCESS      read-only
    STATUS          current
    DESCRIPTION     "The value of sapBaseStatsIngressCPMOctetsHi indicates
                     upper 32 bits of sapBaseStatsIngressCPMOctets object."
    ::= { sapBaseStatsEntry 33 }

sapBaseStatsIngressCPMOctetsLo OBJECT-TYPE
    SYNTAX          Counter32
    MAX-ACCESS      read-only
    STATUS          current
    DESCRIPTION     "The value of sapBaseStatsIngressCPMOctetsHi indicates
                     lower 32 bits of sapBaseStatsIngressCPMOctets object."
    ::= { sapBaseStatsEntry 34 }

sapBaseStatsIngPchipRcvdValidPkt    OBJECT-TYPE
    SYNTAX          Counter64
    MAX-ACCESS      read-only
    STATUS          current
    DESCRIPTION     "The value of sapBaseStatsIngPchipRcvdValidPkt indicates
                     number of received valid packets, as determined by the SAP
                     ingress QoS policy, offered by the Pchip to the Qchip."
    ::= { sapBaseStatsEntry 35 }

sapBaseStatsIngPchipRcvdValidOct    OBJECT-TYPE
    SYNTAX          Counter64
    MAX-ACCESS      read-only
    STATUS          current
    DESCRIPTION     "The value of sapBaseStatsIngPchipRcvdValidOct indicates
                     number of received valid octets, as determined by the SAP
                     ingress QoS policy, offered by the Pchip to the Qchip."
    ::= { sapBaseStatsEntry 36 }

-- ----------------------------------------
-- Ingress QoS Queue SAP Statistics Table
-- ----------------------------------------
sapIngQosQueueStatsTable OBJECT-TYPE
    SYNTAX          SEQUENCE OF SapIngQosQueueStatsEntry
    MAX-ACCESS      not-accessible
    STATUS          current
    DESCRIPTION     "A table that contains ingress QoS queue SAP
                     statistics."
    ::= { tmnxSapObjs 7 }

sapIngQosQueueStatsEntry OBJECT-TYPE
    SYNTAX          SapIngQosQueueStatsEntry
    MAX-ACCESS      not-accessible
    STATUS          current
    DESCRIPTION     "Ingress statistics about a specific SAP's
                     QoS queue."
    INDEX           { svcId, sapPortId, sapEncapValue, sapIngQosQueueId }
    ::= { sapIngQosQueueStatsTable 1 }

SapIngQosQueueStatsEntry ::=
    SEQUENCE {
        sapIngQosQueueId                           TSapIngQueueId,
        sapIngQosQueueStatsOfferedHiPrioPackets    Counter64,
        sapIngQosQueueStatsDroppedHiPrioPackets    Counter64,
        sapIngQosQueueStatsOfferedLoPrioPackets    Counter64,
        sapIngQosQueueStatsDroppedLoPrioPackets    Counter64,
        sapIngQosQueueStatsOfferedHiPrioOctets     Counter64,
        sapIngQosQueueStatsDroppedHiPrioOctets     Counter64,
        sapIngQosQueueStatsOfferedLoPrioOctets     Counter64,
        sapIngQosQueueStatsDroppedLoPrioOctets     Counter64,
        sapIngQosQueueStatsForwardedInProfPackets  Counter64,
        sapIngQosQueueStatsForwardedOutProfPackets Counter64,
        sapIngQosQueueStatsForwardedInProfOctets   Counter64,
        sapIngQosQueueStatsForwardedOutProfOctets  Counter64,
        sapIngQosCustId                            TmnxCustId,
        sapIngQosQueueStatsUncoloredPacketsOffered Counter64,
        sapIngQosQueueStatsUncoloredOctetsOffered  Counter64
    }

sapIngQosQueueId OBJECT-TYPE
    SYNTAX          TSapIngQueueId
    MAX-ACCESS      read-only
    STATUS          current
    DESCRIPTION     "The index of the ingress QoS queue of
                     this SAP."
    ::= { sapIngQosQueueStatsEntry 1 }

sapIngQosQueueStatsOfferedHiPrioPackets OBJECT-TYPE
    SYNTAX          Counter64
    MAX-ACCESS      read-only
    STATUS          current
    DESCRIPTION     "The number of high priority packets,
                     as determined by the SAP ingress QoS
                     policy, offered by the Pchip to the
                     Qchip."
    ::= { sapIngQosQueueStatsEntry 2 }

sapIngQosQueueStatsDroppedHiPrioPackets OBJECT-TYPE
    SYNTAX          Counter64
    MAX-ACCESS      read-only
    STATUS          current
    DESCRIPTION     "The number of high priority packets,
                     as determined by the SAP ingress QoS
                     policy, dropped by the Qchip due to:
                     MBS exceeded, buffer pool limit
                     exceeded, etc."
    ::= { sapIngQosQueueStatsEntry 3 }

sapIngQosQueueStatsOfferedLoPrioPackets OBJECT-TYPE
    SYNTAX          Counter64
    MAX-ACCESS      read-only
    STATUS          current
    DESCRIPTION     "The number of low priority packets,
                     as determined by the SAP ingress QoS
                     policy, offered by the Pchip to the
                     Qchip."
    ::= { sapIngQosQueueStatsEntry 4 }

sapIngQosQueueStatsDroppedLoPrioPackets OBJECT-TYPE
    SYNTAX          Counter64
    MAX-ACCESS      read-only
    STATUS          current
    DESCRIPTION     "The number of low priority packets,
                     as determined by the SAP ingress QoS
                     policy, dropped by the Qchip due to:
                     MBS exceeded, buffer pool limit
                     exceeded, etc."
    ::= { sapIngQosQueueStatsEntry 5 }

sapIngQosQueueStatsOfferedHiPrioOctets OBJECT-TYPE
    SYNTAX          Counter64
    MAX-ACCESS      read-only
    STATUS          current
    DESCRIPTION     "The number of high priority octets,
                     as determined by the SAP ingress QoS
                     policy, offered by the Pchip to the
                     Qchip."
    ::= { sapIngQosQueueStatsEntry 6 }

sapIngQosQueueStatsDroppedHiPrioOctets OBJECT-TYPE
    SYNTAX          Counter64
    MAX-ACCESS      read-only
    STATUS          current
    DESCRIPTION     "The number of high priority octets,
                     as determined by the SAP ingress QoS
                     policy, dropped by the Qchip due to:
                     MBS exceeded, buffer pool limit
                     exceeded, etc."
    ::= { sapIngQosQueueStatsEntry 7 }

sapIngQosQueueStatsOfferedLoPrioOctets OBJECT-TYPE
    SYNTAX          Counter64
    MAX-ACCESS      read-only
    STATUS          current
    DESCRIPTION     "The number of low priority octets,
                     as determined by the SAP ingress QoS
                     policy, offered by the Pchip to the
                     Qchip."
    ::= { sapIngQosQueueStatsEntry 8 }

sapIngQosQueueStatsDroppedLoPrioOctets OBJECT-TYPE
    SYNTAX          Counter64
    MAX-ACCESS      read-only
    STATUS          current
    DESCRIPTION     "The number of low priority octets,
                     as determined by the SAP ingress QoS
                     policy, dropped by the Qchip due to:
                     MBS exceeded, buffer pool limit
                     exceeded, etc."
    ::= { sapIngQosQueueStatsEntry 9 }

sapIngQosQueueStatsForwardedInProfPackets OBJECT-TYPE
    SYNTAX          Counter64
    MAX-ACCESS      read-only
    STATUS          current
    DESCRIPTION     "The number of in-profile packets
                     (rate below CIR) forwarded by the
                     ingress Qchip."
    ::= { sapIngQosQueueStatsEntry 10 }

sapIngQosQueueStatsForwardedOutProfPackets OBJECT-TYPE
    SYNTAX          Counter64
    MAX-ACCESS      read-only
    STATUS          current
    DESCRIPTION     "The number of out-of-profile packets
                     (rate above CIR) forwarded by the
                     ingress Qchip."
    ::= { sapIngQosQueueStatsEntry 11 }

sapIngQosQueueStatsForwardedInProfOctets OBJECT-TYPE
    SYNTAX          Counter64
    MAX-ACCESS      read-only
    STATUS          current
    DESCRIPTION     "The number of in-profile octets
                     (rate below CIR) forwarded by the
                     ingress Qchip."
    ::= { sapIngQosQueueStatsEntry 12 }

sapIngQosQueueStatsForwardedOutProfOctets OBJECT-TYPE
    SYNTAX          Counter64
    MAX-ACCESS      read-only
    STATUS          current
    DESCRIPTION     "The number of out-of-profile octets
                     (rate above CIR) forwarded by the
                     ingress Qchip."
    ::= { sapIngQosQueueStatsEntry 13 }

sapIngQosCustId OBJECT-TYPE
    SYNTAX          TmnxCustId
    MAX-ACCESS      read-only
    STATUS          current
    DESCRIPTION     "The Customer ID for the associated service."
    ::= { sapIngQosQueueStatsEntry 14 }

sapIngQosQueueStatsUncoloredPacketsOffered OBJECT-TYPE
    SYNTAX          Counter64
    MAX-ACCESS      read-only
    STATUS          current
    DESCRIPTION     "The number of uncolored packets offered to
                     the ingress Qchip."
    ::= { sapIngQosQueueStatsEntry 15 }

sapIngQosQueueStatsUncoloredOctetsOffered OBJECT-TYPE
    SYNTAX          Counter64
    MAX-ACCESS      read-only
    STATUS          current
    DESCRIPTION     "The number of uncolored octets offered to
                     the ingress Qchip."
    ::= { sapIngQosQueueStatsEntry 16 }

-- ----------------------------------------
-- Egress QoS Queue SAP Statistics Table
-- ----------------------------------------
sapEgrQosQueueStatsTable OBJECT-TYPE
    SYNTAX          SEQUENCE OF SapEgrQosQueueStatsEntry
    MAX-ACCESS      not-accessible
    STATUS          current
    DESCRIPTION     "A table that contains egress QoS queue SAP
                     statistics."
    ::= { tmnxSapObjs 8 }

sapEgrQosQueueStatsEntry OBJECT-TYPE
    SYNTAX          SapEgrQosQueueStatsEntry
    MAX-ACCESS      not-accessible
    STATUS          current
    DESCRIPTION     "Egress statistics about a specific SAP's
                     QoS queue."
    INDEX           { svcId, sapPortId, sapEncapValue, sapEgrQosQueueId }
    ::= { sapEgrQosQueueStatsTable 1 }

SapEgrQosQueueStatsEntry ::=
    SEQUENCE {
        sapEgrQosQueueId                           TSapEgrQueueId,
        sapEgrQosQueueStatsForwardedInProfPackets  Counter64,
        sapEgrQosQueueStatsDroppedInProfPackets    Counter64,
        sapEgrQosQueueStatsForwardedOutProfPackets Counter64,
        sapEgrQosQueueStatsDroppedOutProfPackets   Counter64,
        sapEgrQosQueueStatsForwardedInProfOctets   Counter64,
        sapEgrQosQueueStatsDroppedInProfOctets     Counter64,
        sapEgrQosQueueStatsForwardedOutProfOctets  Counter64,
        sapEgrQosQueueStatsDroppedOutProfOctets    Counter64,
        sapEgrQosCustId                            TmnxCustId
    }

sapEgrQosQueueId OBJECT-TYPE
    SYNTAX          TSapEgrQueueId
    MAX-ACCESS      read-only
    STATUS          current
    DESCRIPTION     "The index of the egress QoS queue of
                     this SAP."
    ::= { sapEgrQosQueueStatsEntry 1 }

sapEgrQosQueueStatsForwardedInProfPackets OBJECT-TYPE
    SYNTAX          Counter64
    MAX-ACCESS      read-only
    STATUS          current
    DESCRIPTION     "The number of in-profile packets
                     (rate below CIR) forwarded by the
                     egress Qchip."
    ::= { sapEgrQosQueueStatsEntry 2 }

sapEgrQosQueueStatsDroppedInProfPackets OBJECT-TYPE
    SYNTAX          Counter64
    MAX-ACCESS      read-only
    STATUS          current
    DESCRIPTION     "The number of in-profile packets
                     discarded by the egress Qchip due
                     to: MBS exceeded, buffer pool limit
                     exceeded, etc."
    ::= { sapEgrQosQueueStatsEntry 3 }

sapEgrQosQueueStatsForwardedOutProfPackets OBJECT-TYPE
    SYNTAX          Counter64
    MAX-ACCESS      read-only
    STATUS          current
    DESCRIPTION     "The number of out-of-profile packets
                     (rate above CIR) forwarded by the
                     egress Qchip."
    ::= { sapEgrQosQueueStatsEntry 4 }

sapEgrQosQueueStatsDroppedOutProfPackets OBJECT-TYPE
    SYNTAX          Counter64
    MAX-ACCESS      read-only
    STATUS          current
    DESCRIPTION     "The number of out-of-profile packets
                     discarded by the egress Qchip due
                     to: MBS exceeded, buffer pool limit
                     exceeded, etc."
    ::= { sapEgrQosQueueStatsEntry 5 }

sapEgrQosQueueStatsForwardedInProfOctets OBJECT-TYPE
    SYNTAX          Counter64
    MAX-ACCESS      read-only
    STATUS          current
    DESCRIPTION     "The number of in-profile octets
                     (rate below CIR) forwarded by the
                     egress Qchip."
    ::= { sapEgrQosQueueStatsEntry 6 }

sapEgrQosQueueStatsDroppedInProfOctets OBJECT-TYPE
    SYNTAX          Counter64
    MAX-ACCESS      read-only
    STATUS          current
    DESCRIPTION     "The number of in-profile octets
                     discarded by the egress Qchip due
                     to: MBS exceeded, buffer pool limit
                     exceeded, etc."
    ::= { sapEgrQosQueueStatsEntry 7 }

sapEgrQosQueueStatsForwardedOutProfOctets OBJECT-TYPE
    SYNTAX          Counter64
    MAX-ACCESS      read-only
    STATUS          current
    DESCRIPTION     "The number of out-of-profile octets
                     (rate above CIR) forwarded by the
                     egress Qchip."
    ::= { sapEgrQosQueueStatsEntry 8 }

sapEgrQosQueueStatsDroppedOutProfOctets OBJECT-TYPE
    SYNTAX          Counter64
    MAX-ACCESS      read-only
    STATUS          current
    DESCRIPTION     "The number of out-of-profile octets
                     discarded by the egress Qchip due
                     to: MBS exceeded, buffer pool limit
                     exceeded, etc."
    ::= { sapEgrQosQueueStatsEntry 9 }

sapEgrQosCustId OBJECT-TYPE
    SYNTAX          TmnxCustId
    MAX-ACCESS      read-only
    STATUS          current
    DESCRIPTION     "The Customer ID for the associated service."
    ::= { sapEgrQosQueueStatsEntry 10 }

-- -------------------------------------------------
-- Ingress QoS Scheduler SAP Statistics Table
-- -------------------------------------------------
sapIngQosSchedStatsTable OBJECT-TYPE
    SYNTAX          SEQUENCE OF SapIngQosSchedStatsEntry
    MAX-ACCESS      not-accessible
    STATUS          current
    DESCRIPTION     "A table that contains ingress QoS queue SAP
                     statistics."
    ::= { tmnxSapObjs 9 }

sapIngQosSchedStatsEntry OBJECT-TYPE
    SYNTAX          SapIngQosSchedStatsEntry
    MAX-ACCESS      not-accessible
    STATUS          current
    DESCRIPTION     "Ingress statistics about a specific SAP's
                     QoS queue."
    INDEX           { svcId, sapPortId, sapEncapValue,
                      IMPLIED sapIngQosSchedName }
    ::= { sapIngQosSchedStatsTable 1 }

SapIngQosSchedStatsEntry ::=
    SEQUENCE {
        sapIngQosSchedName                     TNamedItem,
        sapIngQosSchedStatsForwardedPackets    Counter64,
        sapIngQosSchedStatsForwardedOctets     Counter64,
        sapIngQosSchedCustId                   TmnxCustId
    }

sapIngQosSchedName OBJECT-TYPE
    SYNTAX          TNamedItem
    MAX-ACCESS      not-accessible
    STATUS          current
    DESCRIPTION     "The index of the ingress QoS scheduler of
                     this SAP."
    ::= { sapIngQosSchedStatsEntry 1 }

sapIngQosSchedStatsForwardedPackets OBJECT-TYPE
    SYNTAX          Counter64
    MAX-ACCESS      read-only
    STATUS          current
    DESCRIPTION     "The number of forwarded packets, as
                     determined by the SAP ingress scheduler
                     policy, offered by the Pchip to the
                     Qchip."
    ::= { sapIngQosSchedStatsEntry 2 }

sapIngQosSchedStatsForwardedOctets OBJECT-TYPE
    SYNTAX          Counter64
    MAX-ACCESS      read-only
    STATUS          current
    DESCRIPTION     "The number of forwarded octets, as
                     determined by the SAP ingress scheduler
                     policy, offered by the Pchip to the
                     Qchip."
    ::= { sapIngQosSchedStatsEntry 3 }

sapIngQosSchedCustId OBJECT-TYPE
    SYNTAX          TmnxCustId
    MAX-ACCESS      read-only
    STATUS          current
    DESCRIPTION     "The Customer ID for the associated service."
    ::= { sapIngQosSchedStatsEntry 4 }

-- ---------------------------------------------
-- Egress QoS Scheduler SAP Statistics Table
-- ---------------------------------------------
sapEgrQosSchedStatsTable OBJECT-TYPE
    SYNTAX          SEQUENCE OF SapEgrQosSchedStatsEntry
    MAX-ACCESS      not-accessible
    STATUS          current
    DESCRIPTION     "A table that contains ingress QoS queue SAP
                     statistics."
    ::= { tmnxSapObjs 10 }

sapEgrQosSchedStatsEntry OBJECT-TYPE
    SYNTAX          SapEgrQosSchedStatsEntry
    MAX-ACCESS      not-accessible
    STATUS          current
    DESCRIPTION     "Egress statistics about a specific SAP's
                     QoS queue."
    INDEX           { svcId, sapPortId, sapEncapValue,
                      IMPLIED sapEgrQosSchedName }
    ::= { sapEgrQosSchedStatsTable 1 }

SapEgrQosSchedStatsEntry ::=
    SEQUENCE {
        sapEgrQosSchedName                     TNamedItem,
        sapEgrQosSchedStatsForwardedPackets    Counter64,
        sapEgrQosSchedStatsForwardedOctets     Counter64,
        sapEgrQosSchedCustId                   TmnxCustId
    }

sapEgrQosSchedName OBJECT-TYPE
    SYNTAX          TNamedItem
    MAX-ACCESS      not-accessible
    STATUS          current
    DESCRIPTION     "The index of the egress QoS scheduler of
                     this SAP."
    ::= { sapEgrQosSchedStatsEntry 1 }

sapEgrQosSchedStatsForwardedPackets OBJECT-TYPE
    SYNTAX          Counter64
    MAX-ACCESS      read-only
    STATUS          current
    DESCRIPTION     "The number of forwarded packets by the
                     egress Qchip, as determined by the SAP
                     egress scheduler policy."
    ::= { sapEgrQosSchedStatsEntry 2 }

sapEgrQosSchedStatsForwardedOctets OBJECT-TYPE
    SYNTAX          Counter64
    MAX-ACCESS      read-only
    STATUS          current
    DESCRIPTION     "The number of forwarded octets by the
                     egress Qchip, as determined by the SAP
                     egress scheduler policy."
    ::= { sapEgrQosSchedStatsEntry 3 }

sapEgrQosSchedCustId OBJECT-TYPE
    SYNTAX          TmnxCustId
    MAX-ACCESS      read-only
    STATUS          current
    DESCRIPTION     "The Customer ID for the associated service."
    ::= { sapEgrQosSchedStatsEntry 4 }

-- -----------------------------------------
-- TLS SAP Managed VLAN List Table
-- -----------------------------------------
sapTlsManagedVlanListTable OBJECT-TYPE
    SYNTAX          SEQUENCE OF SapTlsManagedVlanListEntry
    MAX-ACCESS      not-accessible
    STATUS          current
    DESCRIPTION     "This table is used only for SAPs that are part
                     of a management VPLS. It indicates for each SAP the
                     ranges of associated VLANs that will be affected when
                     the SAP changes state."
    ::= { tmnxSapObjs 11 }

sapTlsManagedVlanListEntry OBJECT-TYPE
    SYNTAX          SapTlsManagedVlanListEntry
    MAX-ACCESS      not-accessible
    STATUS          current
    DESCRIPTION     "Each row specifies a range of VLANS associated
                     with a SAP of a MVPLS. Ranges may contains overlapping
                     sections only for Mvpls SAPs that belong to the same
                     service."
    INDEX           { svcId,
                      sapPortId,
                      sapEncapValue,
                      sapTlsMvplsMinVlanTag,
                      sapTlsMvplsMaxVlanTag }
    ::= { sapTlsManagedVlanListTable 1 }

SapTlsManagedVlanListEntry ::=
    SEQUENCE {
        sapTlsMvplsMinVlanTag     Unsigned32,
        sapTlsMvplsMaxVlanTag     Unsigned32,
        sapTlsMvplsRowStatus      RowStatus
    }

sapTlsMvplsMinVlanTag OBJECT-TYPE
    SYNTAX          Unsigned32(0 .. 4095)
    MAX-ACCESS      not-accessible
    STATUS          current
    DESCRIPTION     "The value of sapTlsMvplsMinVlanTag specifies
                     the left bound (i.e. min. value) of a range of VLANs
                     that are associated with the Mvpls SAP.
                     sapTlsMvplsMinVlanTag must be smaller than (or equal
                     to) sapTlsMvplsMaxVlanTag.
                     Special values are:
                     0: this value is reserved for the null tag.
                     4095: this value denotes the default SAP."
    ::= { sapTlsManagedVlanListEntry 1 }

sapTlsMvplsMaxVlanTag OBJECT-TYPE
    SYNTAX          Unsigned32(0 .. 4095)
    MAX-ACCESS      not-accessible
    STATUS          current
    DESCRIPTION     "The value of sapTlsMvplsMaxVlanTag specifies the
                     right bound (i.e. max. value) of a range of VLANs that
                     are associated with the Mvpls SAP.
                     Special values are:
                     0: this value is reserved for the null tag.
                     4095: this value denotes the default SAP."
    ::= { sapTlsManagedVlanListEntry 2 }

sapTlsMvplsRowStatus OBJECT-TYPE
    SYNTAX           RowStatus
    MAX-ACCESS       read-create
    STATUS           current
    DESCRIPTION      "The value of sapTlsMvplsRowStatus specifies
                      the status of this row. The only values supported
                      during a set operation are 'createAndGo' and
                      'destroy'. A row (i.e. a range of VLAN tags) can be
                      destroyed only if there are no SAPs defined in
                      regular VPLSses in this range."
    ::= { sapTlsManagedVlanListEntry 3 }

-- ----------------------------------------------------
-- SAP Anti-spoof Table
-- ----------------------------------------------------
sapAntiSpoofTable OBJECT-TYPE
    SYNTAX          SEQUENCE OF SapAntiSpoofEntry
    MAX-ACCESS      not-accessible
    STATUS          obsolete
    DESCRIPTION     "The sapAntiSpoofTable contains information about
                     anti-spoofing filters on a SAP."
    ::= { tmnxSapObjs 12 }

sapAntiSpoofEntry OBJECT-TYPE
    SYNTAX          SapAntiSpoofEntry
    MAX-ACCESS      not-accessible
    STATUS          obsolete
    DESCRIPTION     "An entry in the sapAntiSpoofTable."
    INDEX           { sapPortId,
                      sapEncapValue,
                      sapAntiSpoofIpAddress,
                      sapAntiSpoofMacAddress }
    ::= { sapAntiSpoofTable 1 }

SapAntiSpoofEntry ::=
    SEQUENCE {
        sapAntiSpoofIpAddress  IpAddress,
        sapAntiSpoofMacAddress MacAddress
    }

sapAntiSpoofIpAddress OBJECT-TYPE
    SYNTAX          IpAddress
    MAX-ACCESS      read-only
    STATUS          obsolete
    DESCRIPTION     "The value of sapAntiSpoofIpAddress indicates the IP
                     address for which this table entry contains information."
    ::= { sapAntiSpoofEntry 1 }

sapAntiSpoofMacAddress OBJECT-TYPE
    SYNTAX          MacAddress
    MAX-ACCESS      read-only
    STATUS          obsolete
    DESCRIPTION     "The value of sapAntiSpoofMacAddress indicates the MAC
                     address for which this table entry contains information."
    ::= { sapAntiSpoofEntry 2 }

-- -----------------------------------------
-- SAP Static Host Table
-- -----------------------------------------
sapStaticHostTable OBJECT-TYPE
    SYNTAX          SEQUENCE OF SapStaticHostEntry
    MAX-ACCESS      not-accessible
    STATUS          current
    DESCRIPTION     "The sapStaticHostTable is used to configure static hosts
                     on a SAP."
    ::= { tmnxSapObjs 13 }

sapStaticHostEntry OBJECT-TYPE
    SYNTAX          SapStaticHostEntry
    MAX-ACCESS      not-accessible
    STATUS          current
    DESCRIPTION     "Each row entry represents information on a statically
                     configured host. Entries can be created and deleted via
                     SNMP SET operations."
    INDEX           { svcId,
                      sapPortId,
                      sapEncapValue,
                      sapStaticHostIpAddress,
                      sapStaticHostMacAddress }
    ::= { sapStaticHostTable 1 }

SapStaticHostEntry ::=
    SEQUENCE {
        sapStaticHostRowStatus          RowStatus,
        sapStaticHostIpAddress          IpAddress,
        sapStaticHostMacAddress         MacAddress,
        sapStaticHostSubscrIdent        DisplayString,
        sapStaticHostSubProfile         ServObjName,
        sapStaticHostSlaProfile         ServObjName,
        sapStaticHostShcvOperState      INTEGER,
        sapStaticHostShcvChecks         Unsigned32,
        sapStaticHostShcvReplies        Unsigned32,
        sapStaticHostShcvReplyTime      TimeStamp,
        sapStaticHostDynMacAddress      MacAddress,
        sapStaticHostRetailerSvcId      TmnxServId,
        sapStaticHostRetailerIf         InterfaceIndexOrZero,
        sapStaticHostFwdingState        TmnxOperState,
        sapStaticHostAncpString         TmnxAncpStringOrZero,
        sapStaticHostSubIdIsSapId       TruthValue,
        sapStaticHostAppProfile         ServObjName,
        sapStaticHostIntermediateDestId DisplayString,
        sapStaticHostAdminStatus        ServiceAdminStatus,
        sapStaticHostFilterProfile      TNamedItemOrEmpty,
        sapStaticHostAdminRetailSvcId  TmnxServId,
        sapStaticHostRipPolicy         TNamedItemOrEmpty
    }

sapStaticHostRowStatus OBJECT-TYPE
    SYNTAX          RowStatus
    MAX-ACCESS      read-create
    STATUS          current
    DESCRIPTION     "The value of the object sapStaticHostRowStatus controls
                     the creation and deletion of rows in this table."
    ::= { sapStaticHostEntry 1 }

sapStaticHostIpAddress OBJECT-TYPE
    SYNTAX          IpAddress
    MAX-ACCESS      not-accessible
    STATUS          current
    DESCRIPTION     "The value of the object sapStaticHostIpAddress specifies
                     the IP address associated with this static host. The value
                     0.0.0.0 indicates that no host IP address is specified."
    ::= { sapStaticHostEntry 2 }

sapStaticHostMacAddress OBJECT-TYPE
    SYNTAX          MacAddress
    MAX-ACCESS      not-accessible
    STATUS          current
    DESCRIPTION     "The value of the object sapStaticHostMacAddress specifies
                     the MAC address associated with this static host. The
                     value 0:0:0:0:0:0 indicates that no host MAC address is
                     specified."
    ::= { sapStaticHostEntry 3 }

sapStaticHostSubscrIdent OBJECT-TYPE
    SYNTAX          DisplayString (SIZE (0..32))
    MAX-ACCESS      read-create
    STATUS          current
    DESCRIPTION     "The value of the object sapStaticHostSubscrIdent specifies
                     the subscriber identification for this static host."
    DEFVAL          { "" }
    ::= { sapStaticHostEntry 4 }

sapStaticHostSubProfile OBJECT-TYPE
    SYNTAX          ServObjName
    MAX-ACCESS      read-create
    STATUS          current
    DESCRIPTION     "The value of the object sapStaticHostSubProfile specifies
                     the subscriber profile for this static host. The specified
                     subscriber profile needs to exists in the
                     TIMETRA-SUBSCRIBER-MGMT-MIB::tmnxSubProfileTable."
    DEFVAL          { "" }
    ::= { sapStaticHostEntry 5 }

sapStaticHostSlaProfile OBJECT-TYPE
    SYNTAX          ServObjName
    MAX-ACCESS      read-create
    STATUS          current
    DESCRIPTION     "The value of the object sapStaticHostSlaProfile specifies
                     the SLA profile for this static host. The specified
                     SLA profile needs to exists in the
                     TIMETRA-SUBSCRIBER-MGMT-MIB::tmnxSLAProfileTable."
    DEFVAL          { "" }
    ::= { sapStaticHostEntry 6 }

sapStaticHostShcvOperState OBJECT-TYPE
    SYNTAX          INTEGER {
                        disabled  (1),
                        undefined (2),
                        down      (3),
                        up        (4)
                    }
    MAX-ACCESS      read-only
    STATUS          current
    DESCRIPTION     "The value of the object sapStaticHostShcvOperState
                     gives the state of the subscriber host connectivity
                     check for this static host."
    ::= { sapStaticHostEntry 7 }

sapStaticHostShcvChecks OBJECT-TYPE
    SYNTAX          Unsigned32
    MAX-ACCESS      read-only
    STATUS          current
    DESCRIPTION     "The value of the object sapStaticHostShcvChecks specifies
                     the number of connectivity checks for this static host."
    ::= { sapStaticHostEntry 8 }

sapStaticHostShcvReplies OBJECT-TYPE
    SYNTAX          Unsigned32
    MAX-ACCESS      read-only
    STATUS          current
    DESCRIPTION     "The value of the object sapStaticHostShcvReplies specifies
                     the number of host replies for this static host."
    ::= { sapStaticHostEntry 9 }

sapStaticHostShcvReplyTime OBJECT-TYPE
    SYNTAX          TimeStamp
    MAX-ACCESS      read-only
    STATUS          current
    DESCRIPTION     "The value of the object sapStaticHostShcvReplyTime
                     gives the timestamp of the last successful connectivity
                     check for this static host."
    ::= { sapStaticHostEntry 10 }

sapStaticHostDynMacAddress OBJECT-TYPE
    SYNTAX          MacAddress
    MAX-ACCESS      read-only
    STATUS          current
    DESCRIPTION     "The value of the object sapStaticHostDynMacAddress gives
                     the MAC address learned via ARP in case this is an IP-only
                     static host (sapStaticHostMacAddress is set to
                     0:0:0:0:0:0).
                     The value 0:0:0:0:0:0 indicates that no MAC address is
                     learned yet."
    ::= { sapStaticHostEntry 11 }

sapStaticHostRetailerSvcId OBJECT-TYPE
    SYNTAX          TmnxServId
    MAX-ACCESS      read-only
    STATUS          current
    DESCRIPTION     "The value of the object sapStaticHostRetailerSvcId
                     indicates the service ID of the retailer VPRN service
                     to which this static host belongs. When this object is
                     non zero, the static host belongs to a retailer VPRN."
    ::= { sapStaticHostEntry 12 } 

sapStaticHostRetailerIf OBJECT-TYPE
    SYNTAX          InterfaceIndexOrZero
    MAX-ACCESS      read-only
    STATUS          current
    DESCRIPTION     "The value of the object sapStaticHostRetailerIf indicates
                     the interface index of the retailer VPRN interface to which
                     this static host belongs. When this object is non zero,
                     the static host belongs to a retailer VPRN."
    ::= { sapStaticHostEntry 13 } 

sapStaticHostFwdingState OBJECT-TYPE
    SYNTAX          TmnxOperState
    MAX-ACCESS      read-only
    STATUS          current
    DESCRIPTION     "The value of sapStaticHostFwdingState indicates the
                     forwarding state of this static host. When the value
                     is 'outOfService', host traffic is not forwarded.
                     When it is 'inService', host traffic is forwarded."
    ::= { sapStaticHostEntry 14 } 

sapStaticHostAncpString OBJECT-TYPE
    SYNTAX          TmnxAncpStringOrZero
    MAX-ACCESS      read-create
    STATUS          current
    DESCRIPTION     "The value of sapStaticHostAncpString specifies
                     the ancp-string associated to this SAP host."
    DEFVAL          { "" }
    ::= { sapStaticHostEntry 15 } 

sapStaticHostSubIdIsSapId OBJECT-TYPE
    SYNTAX          TruthValue
    MAX-ACCESS      read-create
    STATUS          current
    DESCRIPTION     "The value of the object sapStaticHostSubIdIsSapId
                     specifies whether the SAP-id is taken as subscriber
                     identification for this static host."
    DEFVAL          { false }
    ::= { sapStaticHostEntry 16 } 

sapStaticHostAppProfile OBJECT-TYPE
    SYNTAX          ServObjName
    MAX-ACCESS      read-create
    STATUS          current
    DESCRIPTION     "The value of sapStaticHostAppProfile specifies
                     the application profile for this static host. The
                     specified application profile needs to exist in the
                     TIMETRA-BSX-NG-MIB::tmnxBsxAppProfTable."
    DEFVAL          { "" }
    ::= { sapStaticHostEntry 17 }

sapStaticHostIntermediateDestId OBJECT-TYPE
    SYNTAX          DisplayString (SIZE (0..32))
    MAX-ACCESS      read-create
    STATUS          current
    DESCRIPTION     "The value of sapStaticHostIntermediateDestId specifies
                     to which intermediate destination (for example a DSLAM)
                     this host belongs."
    DEFVAL          { "" }
    ::= { sapStaticHostEntry 18 }

sapStaticHostAdminStatus OBJECT-TYPE
    SYNTAX          ServiceAdminStatus
    MAX-ACCESS      read-create
    STATUS          current
    DESCRIPTION     "The value of sapStaticHostAdminStatus specifies
                     the administrative status of this host."
    DEFVAL          { down }
    ::= { sapStaticHostEntry 19 }

sapStaticHostFilterProfile OBJECT-TYPE
    SYNTAX          TNamedItemOrEmpty
    MAX-ACCESS      read-create
    STATUS          current
    DESCRIPTION     "The value of the object sapStaticHostFilterProfile specifies
                     the filter profile for this static host. The specified
                     filter profile needs to exists in the
                     TIMETRA-SUBSCRIBER-MGMT-MIB::tmnxSubFilterProfileTable."
    DEFVAL          { "" }
    ::= { sapStaticHostEntry 20 }

sapStaticHostAdminRetailSvcId OBJECT-TYPE
    SYNTAX       TmnxServId
    MAX-ACCESS   read-create
    STATUS       current
    DESCRIPTION  "The value of sapStaticHostAdminRetailSvcId specifies the
                  forwarding service ID for an unnumbered static host in a
                  wholesale/retail context."
    DEFVAL       { 0 }
    ::= { sapStaticHostEntry 21 }
    
sapStaticHostRipPolicy OBJECT-TYPE
    SYNTAX       TNamedItemOrEmpty
    MAX-ACCESS   read-create
    STATUS       current
    DESCRIPTION  "The value of the object sapStaticHostRipPolicy specifies the  
                  RIP/RIP-NG policy for this static host."
    DEFVAL       { "" }
    ::= { sapStaticHostEntry 22 }
    
-- ----------------------------------------
-- SAP Tls DHCP Information Table
-- ----------------------------------------
sapTlsDhcpInfoTable OBJECT-TYPE
    SYNTAX          SEQUENCE OF SapTlsDhcpInfoEntry
    MAX-ACCESS      not-accessible
    STATUS          current
    DESCRIPTION     "sapTlsDhcpInfoTable  contains  DHCP information related
                     to a TLS  SAP.  This table complements sapTlsInfoTable,
                     and contains an entry for each Tls SAP. Rows in this
                     table are created and deleted automatically by the system."
    ::= { tmnxSapObjs 14 }

sapTlsDhcpInfoEntry OBJECT-TYPE
    SYNTAX          SapTlsDhcpInfoEntry
    MAX-ACCESS      not-accessible
    STATUS          current
    DESCRIPTION     " DHCP specific information for a TLS SAP."
    INDEX           { svcId, sapPortId, sapEncapValue }
    ::= { sapTlsDhcpInfoTable 1 }

SapTlsDhcpInfoEntry ::=
    SEQUENCE {
        sapTlsDhcpAdminState            TmnxEnabledDisabled,
        sapTlsDhcpDescription           ServObjDesc,
        sapTlsDhcpSnoop                 TmnxEnabledDisabled,
        sapTlsDhcpLeasePopulate         Unsigned32,
        sapTlsDhcpOperLeasePopulate     Unsigned32,
        sapTlsDhcpInfoAction            INTEGER,
        sapTlsDhcpCircuitId             INTEGER,
        sapTlsDhcpRemoteId              INTEGER,
        sapTlsDhcpRemoteIdString        DisplayString,
        sapTlsDhcpProxyAdminState       TmnxEnabledDisabled,
        sapTlsDhcpProxyServerAddr       IpAddress,
        sapTlsDhcpProxyLeaseTime        Unsigned32,
        sapTlsDhcpProxyLTRadiusOverride TruthValue,
        sapTlsDhcpVendorIncludeOptions  BITS,
        sapTlsDhcpVendorOptionString    DisplayString
        }

sapTlsDhcpAdminState OBJECT-TYPE
    SYNTAX          TmnxEnabledDisabled
    MAX-ACCESS      read-write
    STATUS          current
    DESCRIPTION     "The value of the object sapTlsDhcpAdminState specifies
                     the overall enable/disable state of all DHCP related
                     actions  on  this  Sap. The value 'disabled' allows
                     the user to configure  individual DHCP commands but
                     administratively disable them."
    DEFVAL          { disabled }
    ::= { sapTlsDhcpInfoEntry 1 }

sapTlsDhcpDescription OBJECT-TYPE
    SYNTAX          ServObjDesc
    MAX-ACCESS      read-write
    STATUS          current
    DESCRIPTION     "The value of the object sapTlsDhcpDescription specifies
                     a user provided description for DHCP on this Sap.
                     It consists of any printable, seven-bit ASCII characters
                     up to 80 characters in length."
    DEFVAL          { ''H }
    ::= { sapTlsDhcpInfoEntry 2 }

sapTlsDhcpSnoop OBJECT-TYPE
    SYNTAX          TmnxEnabledDisabled
    MAX-ACCESS      read-write
    STATUS          current
    DESCRIPTION     "The value of the object sapTlsDhcpSnoop specifies
                     the enable/disable state for DHCP snooping on this Sap.
                     Note that in order for snooping to be enabled
                     the object sapTlsDhcpAdminState must also have the
                     value enabled."
    DEFVAL          { disabled }
    ::= { sapTlsDhcpInfoEntry 3 }

sapTlsDhcpLeasePopulate OBJECT-TYPE
    SYNTAX          Unsigned32 (0..131071)
    MAX-ACCESS      read-write
    STATUS          current
    DESCRIPTION     "The value of the object sapTlsDhcpLeasePopulate specifies
                     the maximum number of DHCP lease states allowed on this
                     SAP."
    DEFVAL { 0 }
    ::= { sapTlsDhcpInfoEntry 4 }

sapTlsDhcpOperLeasePopulate OBJECT-TYPE
    SYNTAX          Unsigned32 (0..131071)
    MAX-ACCESS      read-only
    STATUS          current
    DESCRIPTION     "The value of the object sapTlsDhcpOperLeasePopulate
                     indicates the number of DHCP lease states currently
                     allocated on this SAP."
    ::= { sapTlsDhcpInfoEntry 5 }

sapTlsDhcpInfoAction OBJECT-TYPE
    SYNTAX          INTEGER {
                        replace (1),
                        drop    (2),
                        keep    (3)
                    }
    MAX-ACCESS      read-write
    STATUS          current
    DESCRIPTION     "The value of the object sapTlsDhcpInfoAction specifies
                     the DHCP option reforwarding policy:
                     'replace' - replace existing information with
                                 configured information
                     'drop'    - discard messages with existing relay
                                 information if the option-82 information
                                 is also present.
                     'keep'    - retain the existing relay information."
    DEFVAL { keep }
    ::= { sapTlsDhcpInfoEntry 6 }

sapTlsDhcpCircuitId OBJECT-TYPE
    SYNTAX          INTEGER {
                        none           (0),
                        asciiTuple     (1),
                        vlanAsciiTuple (2)
                    }
    MAX-ACCESS      read-write
    STATUS          current
    DESCRIPTION     "The value of the object sapTlsDhcpCircuitId specifies
                     whether or not the circuit-id suboption is present, and if
                     it is present what information goes in it:
                     - 'none'          the circuit-id suboption will not be part
                                       of the information option (Option 82).
                     - 'asciiTuple'    the ASCII-encoded  concatenated tuple
                                       consisting of the
                                          - access-node-identifier
                                          - service-id
                                          - interface-name
                                       is used.
                    - 'vlanAsciiTuple' the format will include VLAN-id and dot1p
                                       bits in addition to what is included in 
                                       ascii-tuple already.  The format is 
                                       supported on dot1q and qinq encapsulated 
                                       ports only.  Thus, when the option 82 
                                       bits are stripped, dot1p bits will be 
                                       copied to the Ethernet header of an 
                                       outgoing packet."
    DEFVAL { asciiTuple }
    ::= { sapTlsDhcpInfoEntry 7 }

sapTlsDhcpRemoteId OBJECT-TYPE
    SYNTAX          INTEGER {
                        none           (1),
                        mac            (2),
                        remoteIdString (3)
                    }
    MAX-ACCESS      read-write
    STATUS          current
    DESCRIPTION     "The value of the object sapTlsDhcpRemoteId specifies
                     what information goes into the remote-id suboption in
                     the DHCP Relay packet.
                     If the value of this object is set to 'none',
                     the remote-id suboption will not be part of the
                     information option (Option 82).
                     If the value of this object is set to 'mac',
                     the MAC address of the remote end is encoded in the
                     suboption.
                     If the value of this object is set to 'remoteIdString',
                     sapTlsDhcpRemoteIdString will represent the remote-id.
                     By default, the remote-id value is none."
    DEFVAL { none }
    ::= { sapTlsDhcpInfoEntry 8 }

sapTlsDhcpRemoteIdString OBJECT-TYPE
    SYNTAX          DisplayString (SIZE (0..32))
    MAX-ACCESS      read-write
    STATUS          current
    DESCRIPTION     "The value of the object sapTlsDhcpRemoteIdString specifies
                     a remote-id string.
                     a non-empty value is only supported while
                     the value of sapTlsDhcpRemoteId is equal to 'remoteIdString'."

    DEFVAL { "" }
    ::= { sapTlsDhcpInfoEntry 9 }

sapTlsDhcpProxyAdminState   OBJECT-TYPE
    SYNTAX          TmnxEnabledDisabled
    MAX-ACCESS      read-write
    STATUS          current
    DESCRIPTION     "The value of sapTlsDhcpProxyAdminState specifies the 
                     desired administrative state of the proxy server on this
                     interface.
                     
                     Note that in order for the proxy server to be enabled,
                     the value of sapTlsDhcpAdminState must also be 'enabled'."
    DEFVAL { disabled }
    ::= { sapTlsDhcpInfoEntry 10 }

sapTlsDhcpProxyServerAddr   OBJECT-TYPE
    SYNTAX          IpAddress
    MAX-ACCESS      read-write
    STATUS          current
    DESCRIPTION     "The value of sapTlsDhcpProxyServerAddr specifies 
                     the IP address which will be used as the source address
                     of the emulated DHCP server in the context of 
                     this VPLS SAP.
                     
                     This address is mandatory for the proxy server capability
                     and it should be in the context of the subnet represented
                     by this VPLS."
    DEFVAL { '00000000'H }
    ::= { sapTlsDhcpInfoEntry 11 }

sapTlsDhcpProxyLeaseTime    OBJECT-TYPE
    SYNTAX          Unsigned32 (0|300..315446399)
    UNITS           "seconds"
    MAX-ACCESS      read-write
    STATUS          current
    DESCRIPTION     "The value of sapTlsDhcpProxyLeaseTime specifies in seconds
                     how long a DHCP client is allowed to use the offered IP 
                     address.
                    
                     Value 0 means the lease time provided by a RADIUS or
                     an upstream DHCP server will not be overridden. A lease
                     time of 7 days is used when RADIUS does not provide 
                     a lease time."
    DEFVAL { 0 }
    ::= { sapTlsDhcpInfoEntry 12 }

sapTlsDhcpProxyLTRadiusOverride OBJECT-TYPE
    SYNTAX          TruthValue
    MAX-ACCESS      read-write
    STATUS          current
    DESCRIPTION     "The value of sapTlsDhcpProxyLTRadiusOverride specifies
                     whether or not the lease time provided by the RADIUS 
                     server is presented to the DHCP client.

                     By default the proxy-server will always make use of 
                     sapTlsDhcpProxyLeaseTime, regardless of what lease time 
                     information is provided from the RADIUS server. 
                     When sapTlsDhcpProxyLTRadiusOverride is set to 'true', the
                     proxy-server will use the lease time information provided
                     by the RADIUS server, regardless of the configured one."
    DEFVAL { false }
    ::= { sapTlsDhcpInfoEntry 13 }

sapTlsDhcpVendorIncludeOptions OBJECT-TYPE
    SYNTAX          BITS {
                        systemId  (0),
                        clientMac (1),
                        serviceId (2),
                        sapId     (3)
                    }
    MAX-ACCESS      read-write
    STATUS          current
    DESCRIPTION     "The value of sapTlsDhcpVendorIncludeOptions specifies
                     what is encoded in the Nokia vendor specific
                     sub-option of option 82.

                     The value of this object is only used when
                     sapTlsDhcpInfoAction is 'replace'."
    DEFVAL { { } }
    ::= { sapTlsDhcpInfoEntry 14 }

sapTlsDhcpVendorOptionString OBJECT-TYPE
    SYNTAX          DisplayString (SIZE (0..32))
    MAX-ACCESS      read-write
    STATUS          current
    DESCRIPTION     "The value of sapTlsDhcpVendorOptionString specifies the
                     string that goes into the Nokia vendor specific
                     sub-option of option 82.

                     This string is only used when sapTlsDhcpInfoAction is set 
                     to 'replace'."
    DEFVAL { "" }
    ::= { sapTlsDhcpInfoEntry 15 }

-- --------------------------------------
-- SAP Tls Dhcp Stats Table
-- --------------------------------------
sapTlsDhcpStatsTable OBJECT-TYPE
    SYNTAX          SEQUENCE OF SapTlsDhcpStatsEntry
    MAX-ACCESS      not-accessible
    STATUS          current
    DESCRIPTION     "sapTlsDhcpStatsTable contains DHCP statistics related
                     to  a TLS SAP. This table complements sapTlsInfoTable,
                     and  contains  an entry for each Tls SAP. Rows in this
                     table  are  created  and  deleted automatically by the
                     system."
    ::= { tmnxSapObjs 15 }

sapTlsDhcpStatsEntry OBJECT-TYPE
    SYNTAX          SapTlsDhcpStatsEntry
    MAX-ACCESS      not-accessible
    STATUS          current
    DESCRIPTION     " DHCP statistics for a TLS SAP."
    INDEX           { svcId, sapPortId, sapEncapValue }
    ::= { sapTlsDhcpStatsTable 1 }

SapTlsDhcpStatsEntry ::=
    SEQUENCE {
        sapTlsDhcpStatsClntSnoopdPckts      Counter32,
        sapTlsDhcpStatsSrvrSnoopdPckts      Counter32,
        sapTlsDhcpStatsClntForwdPckts       Counter32,
        sapTlsDhcpStatsSrvrForwdPckts       Counter32,
        sapTlsDhcpStatsClntDropdPckts       Counter32,
        sapTlsDhcpStatsSrvrDropdPckts       Counter32,
        sapTlsDhcpStatsClntProxRadPckts     Counter32,
        sapTlsDhcpStatsClntProxLSPckts      Counter32,
        sapTlsDhcpStatsGenReleasePckts      Counter32,
        sapTlsDhcpStatsGenForceRenPckts     Counter32,
        sapTlsDhcpStatsClntProxUDBPckts     Counter32,
        sapTlsDhcpStatsClntProxNqPckts    Counter32
    }

sapTlsDhcpStatsClntSnoopdPckts OBJECT-TYPE
    SYNTAX          Counter32
    MAX-ACCESS      read-only
    STATUS          current
    DESCRIPTION     "The value of the object sapTlsDhcpStatsClntSnoopdPckts
                     indicates the number of  DHCP client packets that have
                     been snooped on this SAP."
    ::= { sapTlsDhcpStatsEntry 1 }

sapTlsDhcpStatsSrvrSnoopdPckts OBJECT-TYPE
    SYNTAX          Counter32
    MAX-ACCESS      read-only
    STATUS          current
    DESCRIPTION     "The value of the object sapTlsDhcpStatsSrvrSnoopdPckts
                     indicates the number of  DHCP server packets that have
                     been snooped on this SAP."
    ::= { sapTlsDhcpStatsEntry 2 }

sapTlsDhcpStatsClntForwdPckts OBJECT-TYPE
    SYNTAX          Counter32
    MAX-ACCESS      read-only
    STATUS          current
    DESCRIPTION     "The value of the object sapTlsDhcpStatsClntForwdPckts
                     indicates the number  of  DHCP  client  packets  that
                     have been forwarded on this SAP."
    ::= { sapTlsDhcpStatsEntry 3 }

sapTlsDhcpStatsSrvrForwdPckts OBJECT-TYPE
    SYNTAX          Counter32
    MAX-ACCESS      read-only
    STATUS          current
    DESCRIPTION     "The value of the object sapTlsDhcpStatsSrvrForwdPckts
                     indicates the number of  DHCP  server  packets  that have
                     been forwarded on this SAP."
    ::= { sapTlsDhcpStatsEntry 4 }

sapTlsDhcpStatsClntDropdPckts OBJECT-TYPE
    SYNTAX          Counter32
    MAX-ACCESS      read-only
    STATUS          current
    DESCRIPTION     "The value of the object sapTlsDhcpStatsClntDropdPckts
                     indicates the number of  DHCP client packets that have
                     been dropped on this SAP."
    ::= { sapTlsDhcpStatsEntry 5 }

sapTlsDhcpStatsSrvrDropdPckts OBJECT-TYPE
    SYNTAX          Counter32
    MAX-ACCESS      read-only
    STATUS          current
    DESCRIPTION     "The value of the object sapTlsDhcpStatsSrvrDropdPckts
                     indicates the number of  DHCP server packets that have
                     been dropped on this SAP."
    ::= { sapTlsDhcpStatsEntry 6 }

sapTlsDhcpStatsClntProxRadPckts OBJECT-TYPE
    SYNTAX          Counter32
    MAX-ACCESS      read-only
    STATUS          current
    DESCRIPTION     "The value of the object sapTlsDhcpStatsClntProxRadPckts
                     indicates the number of DHCP client packets that have
                     been proxied on this SAP based on data received from a
                     RADIUS server."
    ::= { sapTlsDhcpStatsEntry 7 }

sapTlsDhcpStatsClntProxLSPckts OBJECT-TYPE
    SYNTAX          Counter32
    MAX-ACCESS      read-only
    STATUS          current
    DESCRIPTION     "The value of the object sapTlsDhcpStatsClntProxLSPckts
                     indicates the number of DHCP client packets that have
                     been proxied on this SAP based on a lease state. The
                     lease itself can have been obtained from a DHCP or RADIUS
                     server. This is the so called lease split functionality."
    ::= { sapTlsDhcpStatsEntry 8 }

sapTlsDhcpStatsGenReleasePckts OBJECT-TYPE
    SYNTAX          Counter32
    MAX-ACCESS      read-only
    STATUS          current
    DESCRIPTION     "The value of the object sapTlsDhcpStatsGenReleasePckts
                     indicates the number of DHCP RELEASE messages spoofed on
                     this SAP to the DHCP server."
    ::= { sapTlsDhcpStatsEntry 9 }

sapTlsDhcpStatsGenForceRenPckts OBJECT-TYPE
    SYNTAX          Counter32
    MAX-ACCESS      read-only
    STATUS          current
    DESCRIPTION     "The value of the object sapTlsDhcpStatsGenForceRenPckts
                     indicates the number of DHCP FORCERENEW messages spoofed
                     on this SAP to the DHCP clients."
    ::= { sapTlsDhcpStatsEntry 10 }
    
sapTlsDhcpStatsClntProxUDBPckts OBJECT-TYPE
    SYNTAX          Counter32
    MAX-ACCESS      read-only
    STATUS          current
    DESCRIPTION     "The value of the object sapTlsDhcpStatsClntProxUDBPckts
                     indicates the number of DHCP client packets that have
                     been proxied on this SAP based on the local user database."
    ::= { sapTlsDhcpStatsEntry 11 }
    
sapTlsDhcpStatsClntProxNqPckts OBJECT-TYPE
    SYNTAX          Counter32
    MAX-ACCESS      read-only
    STATUS          current
    DESCRIPTION     "The value of the object sapTlsDhcpStatsClntProxNqPckts
                     indicates the number of DHCP client packets that have
                     been proxied on this SAP based on data received from a
                     Diameter NASREQ server."
    ::= { sapTlsDhcpStatsEntry 12 }


-- ----------------------------------------
-- SAP Tls Dhcp Lease State Table
-- ----------------------------------------
sapTlsDhcpLeaseStateTable OBJECT-TYPE
    SYNTAX          SEQUENCE OF SapTlsDhcpLeaseStateEntry
    MAX-ACCESS      not-accessible
    STATUS          obsolete
    DESCRIPTION     "sapTlsDhcpLeaseStateTable contains DHCP lease state info
                     for a TLS SAP. This table complements sapTlsInfoTable,
                     and contains an entry for each Tls SAP. Rows in this table
                     are created and deleted automatically by the system.
                     The content of this table is moved to the
                     svcDhcpLeaseStateTable."
    ::= { tmnxSapObjs 16 }

sapTlsDhcpLeaseStateEntry OBJECT-TYPE
    SYNTAX          SapTlsDhcpLeaseStateEntry
    MAX-ACCESS      not-accessible
    STATUS          obsolete
    DESCRIPTION     "DHCP Lease State information on a TLS SAP."
    INDEX           { svcId,
                      sapPortId,
                      sapEncapValue,
                      sapTlsDhcpLseStateCiAddr,
                      sapTlsDhcpLseStateChAddr }
    ::= { sapTlsDhcpLeaseStateTable 1 }

SapTlsDhcpLeaseStateEntry ::=
    SEQUENCE {
        sapTlsDhcpLseStateCiAddr        IpAddress,
        sapTlsDhcpLseStateChAddr        MacAddress,
        sapTlsDhcpLseStateRemainLseTime Unsigned32,
        sapTlsDhcpLseStateOption82      OCTET STRING,
        sapTlsDhcpLseStatePersistKey    Unsigned32
    }

sapTlsDhcpLseStateCiAddr OBJECT-TYPE
    SYNTAX          IpAddress
    MAX-ACCESS      not-accessible
    STATUS          obsolete
    DESCRIPTION     "The value of the object sapTlsDhcpLseStateCiAddr indicates
                     the IP address of the DHCP lease state."
    ::= { sapTlsDhcpLeaseStateEntry 1 }

sapTlsDhcpLseStateChAddr OBJECT-TYPE
    SYNTAX          MacAddress
    MAX-ACCESS      not-accessible
    STATUS          obsolete
    DESCRIPTION     "The value of the object sapTlsDhcpLseStateChAddr indicates
                     the MAC address of the DHCP lease state."
    ::= { sapTlsDhcpLeaseStateEntry 2 }

sapTlsDhcpLseStateRemainLseTime OBJECT-TYPE
    SYNTAX          Unsigned32
    MAX-ACCESS      read-only
    STATUS          obsolete
    DESCRIPTION     "The value of the object sapTlsDhcpLseStateRemainLseTime
                     indicates the remaining lease time of the Ip address of
                     the DHCP lease state.
                     This object was made obsolete in the 4.0 release."
    ::= { sapTlsDhcpLeaseStateEntry 3 }

sapTlsDhcpLseStateOption82 OBJECT-TYPE
    SYNTAX          OCTET STRING
    MAX-ACCESS      read-only
    STATUS          obsolete
    DESCRIPTION     "The value of the object sapTlsDhcpLseStateOption82
                     indicates the content of the Option82 for this DHCP
                     lease state.
                     This object was made obsolete in the 4.0 release."
    ::= { sapTlsDhcpLeaseStateEntry 4 }

sapTlsDhcpLseStatePersistKey OBJECT-TYPE
    SYNTAX          Unsigned32
    MAX-ACCESS      read-only
    STATUS          obsolete
    DESCRIPTION     "The value of the object sapTlsDhcpLseStatePersistKey
                     indicates a key value that can be used to track this lease
                     state in the persistence file.
                     This object was made obsolete in the 4.0 release."
    ::= { sapTlsDhcpLeaseStateEntry 5 }

-- --------------------------------------------
-- Ingress QoS Scheduler SAP Statistics Table
-- --------------------------------------------
sapPortIdIngQosSchedStatsTable OBJECT-TYPE
    SYNTAX          SEQUENCE OF SapPortIdIngQosSchedStatsEntry
    MAX-ACCESS      not-accessible
    STATUS          current
    DESCRIPTION
        "The sapPortIdIngQosSchedStatsTable contains ingress QoS
         queue SAP statistics. This table is used when the SAP
         is  a CCAG or LAG in 'link' mode, or an APS."
    ::= { tmnxSapObjs 17 }

sapPortIdIngQosSchedStatsEntry OBJECT-TYPE
    SYNTAX          SapPortIdIngQosSchedStatsEntry
    MAX-ACCESS      not-accessible
    STATUS          current
    DESCRIPTION     "Each entry represents the ingress statistics about a
                     specific SAP's QoS queue. Entries are created when
                     a scheduler policy is applied to a SAP."
    INDEX           { svcId, sapPortId, sapEncapValue,
                      sapPortIdIngQosSchedName, sapPortIdIngPortId }
    ::= { sapPortIdIngQosSchedStatsTable 1 }

SapPortIdIngQosSchedStatsEntry ::=
    SEQUENCE {
        sapPortIdIngQosSchedName      TNamedItem,
        sapPortIdIngPortId            TmnxPortID,
        sapPortIdIngQosSchedFwdPkts   Counter64,
        sapPortIdIngQosSchedFwdOctets Counter64,
        sapPortIdIngQosSchedCustId    TmnxCustId
    }

sapPortIdIngQosSchedName OBJECT-TYPE
    SYNTAX          TNamedItem
    MAX-ACCESS      not-accessible
    STATUS          current
    DESCRIPTION     "The value of sapPortIdIngQosSchedName is used as an index
                     of the ingress QoS scheduler of this SAP."
    ::= { sapPortIdIngQosSchedStatsEntry 1 }

sapPortIdIngPortId OBJECT-TYPE
    SYNTAX          TmnxPortID
    MAX-ACCESS      not-accessible
    STATUS          current
    DESCRIPTION     "The value of sapPortIdIngPortId is used
                     as an index of the ingress QoS scheduler of this SAP. When
                     the SAP is an aps/ccag/lag in 'link' mode, this object is
                     the TmnxPortID of the member-port on which the scheduler is
                     applied."
    ::= {sapPortIdIngQosSchedStatsEntry 2 }

sapPortIdIngQosSchedFwdPkts OBJECT-TYPE
    SYNTAX          Counter64
    MAX-ACCESS      read-only
    STATUS          current
    DESCRIPTION     "The value of sapPortIdIngQosSchedFwdPkts indicates
                     the number of forwarded packets, as determined by the SAP
                     ingress scheduler policy, offered by the Pchip to the
                     Qchip."
    ::= { sapPortIdIngQosSchedStatsEntry 3 }

sapPortIdIngQosSchedFwdOctets OBJECT-TYPE
    SYNTAX          Counter64
    MAX-ACCESS      read-only
    STATUS          current
    DESCRIPTION     "The value of sapPortIdIngQosSchedFwdOctets indicates
                     the number of forwarded octets,as determined by the SAP
                     ingress scheduler policy, offered by the Pchip to the
                     Qchip."
    ::= { sapPortIdIngQosSchedStatsEntry 4 }

sapPortIdIngQosSchedCustId OBJECT-TYPE
    SYNTAX          TmnxCustId
    MAX-ACCESS      read-only
    STATUS          current
    DESCRIPTION     "The value of sapPortIdIngQosSchedCustId indicates the
                     Customer ID for the associated service."
    ::= { sapPortIdIngQosSchedStatsEntry 5 }

-- ------------------------------------------------------------
-- Egress QoS Scheduler SAP Statistics Table for Link mode SAPs
-- ------------------------------------------------------------
sapPortIdEgrQosSchedStatsTable OBJECT-TYPE
    SYNTAX          SEQUENCE OF SapPortIdEgrQosSchedStatsEntry
    MAX-ACCESS      not-accessible
    STATUS          current
    DESCRIPTION     "The sapPortIdEgrQosSchedStatsTable contains egress QoS
                     queue SAP statistics. This table is used when the SAP
                     is  a CCAG or LAG in 'link' mode, or an APS."
    ::= { tmnxSapObjs 18 }

sapPortIdEgrQosSchedStatsEntry OBJECT-TYPE
    SYNTAX          SapPortIdEgrQosSchedStatsEntry
    MAX-ACCESS      not-accessible
    STATUS          current
    DESCRIPTION     "Each entry represents the egress statistics about a
                     specific SAP's QoS queue. Entries are created when
                     a scheduler policy is applied to a SAP."
    INDEX           { svcId, sapPortId, sapEncapValue,
                      sapPortIdEgrQosSchedName, sapPortIdEgrPortId }
    ::= { sapPortIdEgrQosSchedStatsTable 1 }

SapPortIdEgrQosSchedStatsEntry ::=
    SEQUENCE {
        sapPortIdEgrQosSchedName        TNamedItem,
        sapPortIdEgrPortId              TmnxPortID,
        sapPortIdEgrQosSchedFwdPkts     Counter64,
        sapPortIdEgrQosSchedFwdOctets   Counter64,
        sapPortIdEgrQosSchedCustId      TmnxCustId
    }

sapPortIdEgrQosSchedName OBJECT-TYPE
    SYNTAX          TNamedItem
    MAX-ACCESS      not-accessible
    STATUS          current
    DESCRIPTION     "The value of sapPortIdEgrQosSchedName is used as an index
                     of the egress QoS scheduler of this SAP."
    ::= { sapPortIdEgrQosSchedStatsEntry 1 }

sapPortIdEgrPortId OBJECT-TYPE
    SYNTAX          TmnxPortID
    MAX-ACCESS      not-accessible
    STATUS          current
    DESCRIPTION     "The value of sapPortIdEgrPortId is used
                     as an index of the egress QoS scheduler of this SAP. When
                     the SAP is an aps/ccag/lag in 'link' mode, this object is
                     the TmnxPortID of the member-port on which the scheduler is
                     applied."
    ::= {sapPortIdEgrQosSchedStatsEntry 2 }

sapPortIdEgrQosSchedFwdPkts OBJECT-TYPE
    SYNTAX          Counter64
    MAX-ACCESS      read-only
    STATUS          current
    DESCRIPTION     "The value of sapPortIdEgrQosSchedFwdPkts indicates
                     the number of forwarded packets, as determined by the SAP
                     egress scheduler policy, offered by the Pchip to the
                     Qchip."
    ::= { sapPortIdEgrQosSchedStatsEntry 3 }

sapPortIdEgrQosSchedFwdOctets OBJECT-TYPE
    SYNTAX          Counter64
    MAX-ACCESS      read-only
    STATUS          current
    DESCRIPTION     "The value of sapPortIdEgrQosSchedFwdOctets indicates
                     the number of forwarded octets,as determined by the SAP
                     egress scheduler policy, offered by the Pchip to the
                     Qchip."
    ::= { sapPortIdEgrQosSchedStatsEntry 4 }

sapPortIdEgrQosSchedCustId OBJECT-TYPE
    SYNTAX          TmnxCustId
    MAX-ACCESS      read-only
    STATUS          current
    DESCRIPTION     "The value of sapPortIdEgrQosSchedCustId indicates the
                     Customer ID for the associated service."
    ::= { sapPortIdEgrQosSchedStatsEntry 5 }


-- ------------------------------------------
-- SAP Ingress QoS Queue Table
-- ------------------------------------------
sapIngQosQueueInfoTable OBJECT-TYPE
    SYNTAX          SEQUENCE OF SapIngQosQueueInfoEntry
    MAX-ACCESS      not-accessible
    STATUS          current
    DESCRIPTION     "This table is used to override the base parameters
                     of a queue, as defined in the associated SAP
                     ingress QoS policy."
    ::= { tmnxSapObjs 19 }

sapIngQosQueueInfoEntry OBJECT-TYPE
    SYNTAX          SapIngQosQueueInfoEntry
    MAX-ACCESS      not-accessible
    STATUS          current
    DESCRIPTION     "Override values for the specified SAP ingress QoS
                     queue. These values override the corresponding ones
                     specified in the associated SAP ingress QoS policy."
    INDEX           { svcId,
                      sapPortId,
                      sapEncapValue,
                      sapIngQosQId }
    ::= { sapIngQosQueueInfoTable 1 }

SapIngQosQueueInfoEntry ::=
    SEQUENCE {
        sapIngQosQId                TIngressQueueId,
        sapIngQosQRowStatus         RowStatus,
        sapIngQosQLastMgmtChange    TimeStamp,
        sapIngQosQOverrideFlags     TQosQueueAttribute,
        sapIngQosQCBS               TBurstSize,
        sapIngQosQMBS               TBurstSize,
        sapIngQosQHiPrioOnly        TBurstPercentOrDefault,
        sapIngQosQCIRAdaptation     TAdaptationRule,
        sapIngQosQPIRAdaptation     TAdaptationRule,
        sapIngQosQAdminPIR          TQosQueuePIRRate,
        sapIngQosQAdminCIR          TQosQueueCIRRate,
        sapIngQosQMBSBytes          TBurstSizeBytes,
        sapIngQosQWeight            TWeight,
        sapIngQosQCIRWeight         TWeight,
        sapIngQosQAdminPIRPercent   Unsigned32,
        sapIngQosQAdminCIRPercent   Unsigned32,
        sapIngQosQMonitorDepth      TruthValue
    }

sapIngQosQId OBJECT-TYPE
    SYNTAX          TIngressQueueId
    MAX-ACCESS      not-accessible
    STATUS          current
    DESCRIPTION     "The value of sapIngQosQId indicates the ID of the
                     queue whose parameters are to be overridden."
    ::= { sapIngQosQueueInfoEntry 1 }

sapIngQosQRowStatus OBJECT-TYPE
    SYNTAX          RowStatus
    MAX-ACCESS      read-create
    STATUS          current
    DESCRIPTION     "The value of sapIngQosQRowStatus controls the creation
                     and deletion of rows in this table."
    ::= { sapIngQosQueueInfoEntry 2 }

sapIngQosQLastMgmtChange OBJECT-TYPE
    SYNTAX          TimeStamp
    MAX-ACCESS      read-only
    STATUS          current
    DESCRIPTION     "The value of sapIngQosQLastMgmtChange indicates the
                     value of sysUpTime at the time of the last management
                     change of any writable object of this row."
    ::= { sapIngQosQueueInfoEntry 3 }

sapIngQosQOverrideFlags OBJECT-TYPE
    SYNTAX          TQosQueueAttribute
    MAX-ACCESS      read-create
    STATUS          current
    DESCRIPTION     "The value of sapIngQosQOverrideFlags specifies the
                     set of attributes whose values have been overridden
                     via management on this queue. Clearing a given flag
                     will return the corresponding overridden attribute
                     to the value defined on the SAP's ingress QoS policy."
    ::= { sapIngQosQueueInfoEntry 4 }

sapIngQosQCBS OBJECT-TYPE
    SYNTAX          TBurstSize
    UNITS           "kilo bytes"
    MAX-ACCESS      read-create
    STATUS          current
    DESCRIPTION     "The value of sapIngQosQCBS specifies the amount of
                     reserved buffer space (in kilo bytes) for this queue."
    DEFVAL { -1 }
    ::= { sapIngQosQueueInfoEntry 5 }

sapIngQosQMBS OBJECT-TYPE
    SYNTAX          TBurstSize
    UNITS           "kilo bytes"
    MAX-ACCESS      read-create
    STATUS          obsolete
    DESCRIPTION     "The value of sapIngQosQMBS specifies the maximum
                     amount of buffer space (in kilo bytes) allowed for
                     this queue."
    DEFVAL { -1 }
    ::= { sapIngQosQueueInfoEntry 6 }

sapIngQosQHiPrioOnly OBJECT-TYPE
    SYNTAX          TBurstPercentOrDefault
    UNITS           "percent"
    MAX-ACCESS      read-create
    STATUS          current
    DESCRIPTION     "The value of sapIngQosQHiPrioOnly specifies the
                     percentage of buffer space for this queue, used
                     exclusively by high priority packets."
    DEFVAL { -1 }
    ::= { sapIngQosQueueInfoEntry 7 }

sapIngQosQCIRAdaptation OBJECT-TYPE
    SYNTAX          TAdaptationRule
    MAX-ACCESS      read-create
    STATUS          current
    DESCRIPTION     "The value of sapIngQosQCIRAdaptation specifies the
                     criteria to use to compute the operational CIR value
                     for this queue, while maintaining a minimum offset."
    DEFVAL { closest }
    ::= { sapIngQosQueueInfoEntry 8 }

sapIngQosQPIRAdaptation OBJECT-TYPE
    SYNTAX          TAdaptationRule
    MAX-ACCESS      read-create
    STATUS          current
    DESCRIPTION     "The value of sapIngQosQPIRAdaptation specifies the
                     criteria to use to compute the operational PIR value
                     for this queue, while maintaining a minimum offset."
    DEFVAL { closest }
    ::= { sapIngQosQueueInfoEntry 9 }

sapIngQosQAdminPIR OBJECT-TYPE
    SYNTAX          TQosQueuePIRRate
    UNITS           "kilo bits per second"
    MAX-ACCESS      read-create
    STATUS          current
    DESCRIPTION     "The value of sapIngQosQAdminPIR specifies the desired
                     PIR value for this queue."
    DEFVAL { -1 }
    ::= { sapIngQosQueueInfoEntry 10 }

sapIngQosQAdminCIR OBJECT-TYPE
    SYNTAX          TQosQueueCIRRate
    UNITS           "kilo bits per second"
    MAX-ACCESS      read-create
    STATUS          current
    DESCRIPTION     "The value of sapIngQosQAdminCIR specifies the desired
                     CIR value for this queue."
    DEFVAL { -1 }
    ::= { sapIngQosQueueInfoEntry 11 }

sapIngQosQMBSBytes OBJECT-TYPE
    SYNTAX          TBurstSizeBytes
    UNITS           "bytes"
    MAX-ACCESS      read-create
    STATUS          current
    DESCRIPTION     "The value of sapIngQosQMBSBytes specifies the maximum
                     amount of buffer space (in bytes) allowed for
                     this queue."
    DEFVAL { -1 }
    ::= { sapIngQosQueueInfoEntry 12 }

sapIngQosQWeight OBJECT-TYPE
    SYNTAX       TWeight
    MAX-ACCESS   read-create
    STATUS       current
    DESCRIPTION
        "The value of sapIngQosQWeight specifies the weight that needs to be
         used by the scheduler to which this queue would be feeding."
    DEFVAL { 1 }
    ::= { sapIngQosQueueInfoEntry 13 }

sapIngQosQCIRWeight OBJECT-TYPE
    SYNTAX       TWeight
    MAX-ACCESS   read-create
    STATUS       current
    DESCRIPTION
        "The value of sapIngQosQCIRWeight specifies the weight that should be 
         assigned to this queue by the parent scheduler among all the entities 
         feeding into the parent, when the traffic is conforming to the 
         committed rate.

         A value of '0' specifies that the queue will not receive bandwidth for
         the 'within-cir' pass on its parent scheduler."
    DEFVAL { 1 }
    ::= { sapIngQosQueueInfoEntry 14 }

sapIngQosQAdminPIRPercent OBJECT-TYPE
    SYNTAX          Unsigned32 (1..10000)
    UNITS           "hundredths of a percent"
    MAX-ACCESS      read-create
    STATUS          current
    DESCRIPTION     "The value of sapIngQosQAdminPIRPercent specifies the 
                     desired PIR value for this queue as a percentage."
    DEFVAL { 10000 }
    ::= { sapIngQosQueueInfoEntry 15 }

sapIngQosQAdminCIRPercent OBJECT-TYPE
    SYNTAX          Unsigned32 (0..10000)
    UNITS           "hundredths of a percent"
    MAX-ACCESS      read-create
    STATUS          current
    DESCRIPTION     "The value of sapIngQosQAdminCIRPercent specifies the 
                     desired CIR value for this queue as a percentage."
    DEFVAL { 0 }
    ::= { sapIngQosQueueInfoEntry 16 }

sapIngQosQMonitorDepth              OBJECT-TYPE
    SYNTAX       TruthValue
    MAX-ACCESS   read-create
    STATUS       current
    DESCRIPTION
        "The value of sapIngQosQMonitorDepth specifies whether to enable
         queue-depth monitoring for this specified queue."
    DEFVAL { false }
    ::= { sapIngQosQueueInfoEntry 17 }

-- ----------------------------
-- SAP Egress QoS Queue Table
-- ----------------------------
sapEgrQosQueueInfoTable OBJECT-TYPE
    SYNTAX          SEQUENCE OF SapEgrQosQueueInfoEntry
    MAX-ACCESS      not-accessible
    STATUS          current
    DESCRIPTION     "This table is used to override the base parameters
                     of a queue, as defined in the associated SAP
                     egress QoS policy."
    ::= { tmnxSapObjs 20 }

sapEgrQosQueueInfoEntry OBJECT-TYPE
    SYNTAX          SapEgrQosQueueInfoEntry
    MAX-ACCESS      not-accessible
    STATUS          current
    DESCRIPTION     "Override values for the specified SAP egress QoS
                     queue. These values override the corresponding ones
                     specified in the associated SAP egress QoS policy."
    INDEX           { svcId,
                      sapPortId,
                      sapEncapValue,
                      sapEgrQosQId }
    ::= { sapEgrQosQueueInfoTable 1 }

SapEgrQosQueueInfoEntry ::=
    SEQUENCE {
        sapEgrQosQId                TEgressQueueId,
        sapEgrQosQRowStatus         RowStatus,
        sapEgrQosQLastMgmtChange    TimeStamp,
        sapEgrQosQOverrideFlags     TQosQueueAttribute,
        sapEgrQosQCBS               TBurstSize,
        sapEgrQosQMBS               TBurstSize,
        sapEgrQosQHiPrioOnly        TBurstPercentOrDefault,
        sapEgrQosQCIRAdaptation     TAdaptationRule,
        sapEgrQosQPIRAdaptation     TAdaptationRule,
        sapEgrQosQAdminPIR          TQosQueuePIRRate,
        sapEgrQosQAdminCIR          TQosQueueCIRRate,
        sapEgrQosQAvgOverhead       Unsigned32,
        sapEgrQosQMBSBytes          TBurstSizeBytes,
        sapEgrQosQWeight            TWeight,
        sapEgrQosQCIRWeight         TWeight,
        sapEgrQosQAdminPIRPercent   Unsigned32,
        sapEgrQosQAdminCIRPercent   Unsigned32,
        sapEgrQosQMonitorDepth      TruthValue
    }

sapEgrQosQId OBJECT-TYPE
    SYNTAX          TEgressQueueId
    MAX-ACCESS      not-accessible
    STATUS          current
    DESCRIPTION     "The value of sapEgrQosQId indicates the ID of the
                     queue whose parameters are to be overridden."
    ::= { sapEgrQosQueueInfoEntry 1 }

sapEgrQosQRowStatus OBJECT-TYPE
    SYNTAX          RowStatus
    MAX-ACCESS      read-create
    STATUS          current
    DESCRIPTION     "The value of sapEgrQosQRowStatus controls the creation
                     and deletion of rows in this table."
    ::= { sapEgrQosQueueInfoEntry 2 }

sapEgrQosQLastMgmtChange OBJECT-TYPE
    SYNTAX          TimeStamp
    MAX-ACCESS      read-only
    STATUS          current
    DESCRIPTION     "The value of sapEgrQosQLastMgmtChange indicates the
                     value of sysUpTime at the time of the last management
                     change of any writable object of this row."
    ::= { sapEgrQosQueueInfoEntry 3 }

sapEgrQosQOverrideFlags OBJECT-TYPE
    SYNTAX          TQosQueueAttribute
    MAX-ACCESS      read-create
    STATUS          current
    DESCRIPTION     "The value of sapEgrQosQOverrideFlags specifies the
                     set of attributes whose values have been overridden
                     via management on this queue. Clearing a given flag
                     will return the corresponding overridden attribute
                     to the value defined on the SAP's ingress QoS policy."
    ::= { sapEgrQosQueueInfoEntry 4 }

sapEgrQosQCBS OBJECT-TYPE
    SYNTAX          TBurstSize
    UNITS           "kilo bytes"
    MAX-ACCESS      read-create
    STATUS          current
    DESCRIPTION     "The value of sapEgrQosQCBS specifies the amount of
                     reserved buffer space (in kilo bytes) for this queue."
    DEFVAL { -1 }
    ::= { sapEgrQosQueueInfoEntry 5 }

sapEgrQosQMBS OBJECT-TYPE
    SYNTAX          TBurstSize
    UNITS           "kilo bytes"
    MAX-ACCESS      read-create
    STATUS          obsolete
    DESCRIPTION     "The value of sapEgrQosQMBS specifies the maximum
                     amount of buffer space (in kilo bytes) allowed for
                     this queue."
    DEFVAL { -1 }
    ::= { sapEgrQosQueueInfoEntry 6 }

sapEgrQosQHiPrioOnly OBJECT-TYPE
    SYNTAX          TBurstPercentOrDefault
    UNITS           "percent"
    MAX-ACCESS      read-create
    STATUS          current
    DESCRIPTION     "The value of sapEgrQosQHiPrioOnly specifies the
                     percentage of buffer space for this queue, used
                     exclusively by high priority packets."
    DEFVAL { -1 }
    ::= { sapEgrQosQueueInfoEntry 7 }

sapEgrQosQCIRAdaptation OBJECT-TYPE
    SYNTAX          TAdaptationRule
    MAX-ACCESS      read-create
    STATUS          current
    DESCRIPTION     "The value of sapEgrQosQCIRAdaptation specifies the
                     criteria to use to compute the operational CIR value
                     for this queue, while maintaining a minimum offset."
    DEFVAL { closest }
    ::= { sapEgrQosQueueInfoEntry 8 }

sapEgrQosQPIRAdaptation OBJECT-TYPE
    SYNTAX          TAdaptationRule
    MAX-ACCESS      read-create
    STATUS          current
    DESCRIPTION     "The value of sapEgrQosQPIRAdaptation specifies the
                     criteria to use to compute the operational PIR value
                     for this queue, while maintaining a minimum offset."
    DEFVAL { closest }
    ::= { sapEgrQosQueueInfoEntry 9 }

sapEgrQosQAdminPIR OBJECT-TYPE
    SYNTAX          TQosQueuePIRRate
    UNITS           "kilo bits per second"
    MAX-ACCESS      read-create
    STATUS          current
    DESCRIPTION     "The value of sapEgrQosQAdminPIR specifies the desired
                     PIR value for this queue."
    DEFVAL { -1 }
    ::= { sapEgrQosQueueInfoEntry 10 }

sapEgrQosQAdminCIR OBJECT-TYPE
    SYNTAX          TQosQueueCIRRate
    UNITS           "kilo bits per second"
    MAX-ACCESS      read-create
    STATUS          current
    DESCRIPTION     "The value of sapEgrQosQAdminCIR specifies the desired
                     CIR value for this queue."
    DEFVAL { -1 }
    ::= { sapEgrQosQueueInfoEntry 11 }

sapEgrQosQAvgOverhead   OBJECT-TYPE
    SYNTAX          Unsigned32 (0..10000)
    MAX-ACCESS      read-create
    STATUS          current
    DESCRIPTION     "The value of sapEgrQosQAvgOverhead specifies the 
                     encapsulation overhead, in hundredths of a percent,  
                     used to translate packet-based rate to frame-based 
                     rate and vice versa."
    DEFVAL      { 0 }
    ::= { sapEgrQosQueueInfoEntry 12 }

sapEgrQosQMBSBytes OBJECT-TYPE
    SYNTAX          TBurstSizeBytes
    UNITS           "bytes"
    MAX-ACCESS      read-create
    STATUS          current
    DESCRIPTION     "The value of sapEgrQosQMBSBytes specifies the maximum
                     amount of buffer space (in bytes) allowed for
                     this queue."
    DEFVAL { -1 }
    ::= { sapEgrQosQueueInfoEntry 13 }

sapEgrQosQWeight OBJECT-TYPE
    SYNTAX       TWeight
    MAX-ACCESS   read-create
    STATUS       current
    DESCRIPTION
        "The value of sapEgrQosQWeight specifies the weight that needs to be
         used by the scheduler to which this queue would be feeding."
    DEFVAL { 1 }
    ::= { sapEgrQosQueueInfoEntry 14 }

sapEgrQosQCIRWeight OBJECT-TYPE
    SYNTAX       TWeight
    MAX-ACCESS   read-create
    STATUS       current
    DESCRIPTION
        "The value of sapEgrQosQCIRWeight specifies the weight that should be 
         assigned to this queue by the parent scheduler among all the entities 
         feeding into the parent, when the traffic is conforming to the 
         committed rate.
        
         A value of '0' specifies that the queue will not receive bandwidth for
         the 'within-cir' pass on its parent scheduler."
    DEFVAL { 1 }
    ::= { sapEgrQosQueueInfoEntry 15 }

sapEgrQosQAdminPIRPercent OBJECT-TYPE
    SYNTAX          Unsigned32 (1..10000)
    UNITS           "hundredths of a percent"
    MAX-ACCESS      read-create
    STATUS          current
    DESCRIPTION     "The value of sapEgrQosQAdminPIRPercent specifies the
                     desired PIR value for this queue as a percentage."
    DEFVAL { 10000 }
    ::= { sapEgrQosQueueInfoEntry 16 }

sapEgrQosQAdminCIRPercent OBJECT-TYPE
    SYNTAX          Unsigned32 (0..10000)
    UNITS           "hundredths of a percent"
    MAX-ACCESS      read-create
    STATUS          current
    DESCRIPTION     "The value of sapEgrQosQAdminCIRPercent specifies the
                     desired CIR value for this queue as a percentage."
    DEFVAL { 0 }
    ::= { sapEgrQosQueueInfoEntry 17 }

sapEgrQosQMonitorDepth              OBJECT-TYPE
    SYNTAX       TruthValue
    MAX-ACCESS   read-create
    STATUS       current
    DESCRIPTION
        "The value of sapEgrQosQMonitorDepth specifies whether to enable
         queue-depth monitoring for this specified queue."
    DEFVAL { false }
    ::= { sapEgrQosQueueInfoEntry 18 }

-- ------------------------------------
-- SAP Ingress QoS Scheduler Table
-- ------------------------------------
sapIngQosSchedInfoTable OBJECT-TYPE
    SYNTAX          SEQUENCE OF SapIngQosSchedInfoEntry
    MAX-ACCESS      not-accessible
    STATUS          current
    DESCRIPTION     "This table is used to override the base parameters
                     of a virtual scheduler, as defined in the associated
                     SAP ingress scheduler policy."
    ::= { tmnxSapObjs 21 }

sapIngQosSchedInfoEntry OBJECT-TYPE
    SYNTAX          SapIngQosSchedInfoEntry
    MAX-ACCESS      not-accessible
    STATUS          current
    DESCRIPTION     "Override values for the specified SAP ingress virtual
                     scheduler. These values override the corresponding
                     ones specified in the associated SAP ingress scheduler
                     policy."
    INDEX           { svcId,
                      sapPortId,
                      sapEncapValue,
                      IMPLIED sapIngQosSName }
    ::= { sapIngQosSchedInfoTable 1 }

SapIngQosSchedInfoEntry ::=
    SEQUENCE {
        sapIngQosSName              TNamedItem,
        sapIngQosSRowStatus         RowStatus,
        sapIngQosSLastMgmtChange    TimeStamp,
        sapIngQosSOverrideFlags     TVirtSchedAttribute,
        sapIngQosSPIR               THPolVirtualSchePIRRate,
        sapIngQosSCIR               THPolVirtualScheCIRRate,
        sapIngQosSSummedCIR         TruthValue,
        sapIngQosSPIRHi             Unsigned32,
        sapIngQosSPIRLo             Unsigned32,
        sapIngQosSCIRHi             Unsigned32,
        sapIngQosSCIRLo             Unsigned32,
        sapIngQosSParentWeight      TWeight,
        sapIngQosSParentCIRWeight   TWeight
    }

sapIngQosSName OBJECT-TYPE
    SYNTAX          TNamedItem
    MAX-ACCESS      not-accessible
    STATUS          current
    DESCRIPTION     "The value of sapIngQosSName indicates the name of
                     the virtual scheduler whose parameters are to be
                     overridden."
    ::= { sapIngQosSchedInfoEntry 1 }

sapIngQosSRowStatus OBJECT-TYPE
    SYNTAX          RowStatus
    MAX-ACCESS      read-create
    STATUS          current
    DESCRIPTION     "The value of sapIngQosSRowStatus controls the creation
                     and deletion of rows in this table."
    ::= { sapIngQosSchedInfoEntry 2 }

sapIngQosSLastMgmtChange OBJECT-TYPE
    SYNTAX          TimeStamp
    MAX-ACCESS      read-only
    STATUS          current
    DESCRIPTION     "The value of sapIngQosSLastMgmtChange indicates the
                     value of sysUpTime at the time of the last management
                     change of any writable object of this row."
    ::= { sapIngQosSchedInfoEntry 3 }

sapIngQosSOverrideFlags OBJECT-TYPE
    SYNTAX          TVirtSchedAttribute
    MAX-ACCESS      read-create
    STATUS          current
    DESCRIPTION     "The value of sapIngQosSOverrideFlags specifies the
                     set of attributes whose values have been overridden
                     via management on this virtual scheduler. Clearing a
                     given flag will return the corresponding overridden
                     attribute to the value defined on the SAP's ingress
                     scheduler policy."
    ::= { sapIngQosSchedInfoEntry 4 }

sapIngQosSPIR OBJECT-TYPE
    SYNTAX          THPolVirtualSchePIRRate
    UNITS           "kilo bits per second"
    MAX-ACCESS      read-create
    STATUS          obsolete
    DESCRIPTION     "The value of sapIngQosSPIR specifies the desired
                     PIR value for this virtual scheduler.

                     This object is obsoleted in 11.0 Release. It is replaced by 
                     sapIngQosSPIRHi and sapIngQosSPIRLo."
    DEFVAL { -1 }
    ::= { sapIngQosSchedInfoEntry 5 }

sapIngQosSCIR OBJECT-TYPE
    SYNTAX          THPolVirtualScheCIRRate
    UNITS           "kilo bits per second"
    MAX-ACCESS      read-create
    STATUS          obsolete
    DESCRIPTION     "The value of sapIngQosSCIR specifies the desired
                     CIR value for this virtual scheduler.

                     This object is obsoleted in 11.0 Release. It is replaced by 
                     sapIngQosSCIRHi and sapIngQosSCIRLo."
    DEFVAL { -1 }
    ::= { sapIngQosSchedInfoEntry 6 }

sapIngQosSSummedCIR     OBJECT-TYPE
    SYNTAX          TruthValue
    MAX-ACCESS      read-create
    STATUS          current
    DESCRIPTION     "The value of sapIngQosSSummedCIR specifies if the CIR
                     should be used as the summed CIR values of the children
                     schedulers or queues. If set to 'true', the applicable
                     scheduler CIR (sapIngQosSCIR) loses its meaning."
    DEFVAL { true }
    ::= { sapIngQosSchedInfoEntry 7 }

sapIngQosSPIRHi OBJECT-TYPE
    SYNTAX       Unsigned32 (0 | 4294967295)
    UNITS        "kbps"
    MAX-ACCESS   read-create
    STATUS       current
    DESCRIPTION  "The value of sapIngQosSPIRHi indicates upper 32 bits of the
                  pir-rate allowed for this virtual scheduler.    

                  This value should always be set along with sapIngQosSPIRLo,
                  otherwise an 'inconsistentValue' error is returned.

                  When the value of sapIngQosSPIRHi along with the value of
                  sapIngQosSPIRLo is set to 4294967295 (0xFFFFFFFF), rate
                  for this virtual scheduler indicates maximum rate."
    DEFVAL { 4294967295 }
    ::= { sapIngQosSchedInfoEntry 8 }

sapIngQosSPIRLo OBJECT-TYPE
    SYNTAX       Unsigned32 (1..3200000000 | 4294967295)
    UNITS        "kbps"
    MAX-ACCESS   read-create
    STATUS       current
    DESCRIPTION  "The value of sapIngQosSPIRLo indicates lower 32 bits of the
                  pir-rate allowed for this virtual scheduler.    

                  This value should always be set along with sapIngQosSPIRHi,
                  otherwise an 'inconsistentValue' error is returned.

                  When the value of sapIngQosSPIRHi along with the value of
                  sapIngQosSPIRLo is set to 4294967295 (0xFFFFFFFF), rate
                  for this virtual scheduler indicates maximum rate."
    DEFVAL { 4294967295 }
    ::= { sapIngQosSchedInfoEntry 9 }

sapIngQosSCIRHi OBJECT-TYPE
    SYNTAX       Unsigned32 (0 | 4294967295)
    UNITS        "kbps"
    MAX-ACCESS   read-create
    STATUS       current
    DESCRIPTION  "The value of sapIngQosSCIRHi indicates upper 32 bits of the
                  cir-rate allowed for this virtual scheduler.    

                  This value should always be set along with sapIngQosSCIRLo,
                  otherwise an 'inconsistentValue' error is returned.

                  When the value of sapIngQosSCIRHi along with the value of
                  sapIngQosSCIRLo is set to 4294967295 (0xFFFFFFFF), rate
                  for this virtual scheduler indicates maximum rate."
    DEFVAL { 4294967295 }
    ::= { sapIngQosSchedInfoEntry 10 }

sapIngQosSCIRLo OBJECT-TYPE
    SYNTAX       Unsigned32 (0..3200000000 | 4294967295)
    UNITS        "kbps"
    MAX-ACCESS   read-create
    STATUS       current
    DESCRIPTION  "The value of sapIngQosSCIRLo indicates lower 32 bits of the
                  cir-rate allowed for this virtual scheduler.    

                  This value should always be set along with sapIngQosSCIRHi,
                  otherwise an 'inconsistentValue' error is returned.

                  When the value of sapIngQosSCIRHi along with the value of
                  sapIngQosSCIRLo is set to 4294967295 (0xFFFFFFFF), rate
                  for this virtual scheduler indicates maximum rate."
    DEFVAL { 4294967295 }
    ::= { sapIngQosSchedInfoEntry 11 }

sapIngQosSParentWeight              OBJECT-TYPE
    SYNTAX       TWeight
    MAX-ACCESS   read-create
    STATUS       current
    DESCRIPTION
        "The value of sapIngQosSParentWeight specifies the weight that needs
         to be used by this virtual scheduler to which this queue would be
         feeding."
    DEFVAL { 1 }
    ::= { sapIngQosSchedInfoEntry 12 }


sapIngQosSParentCIRWeight           OBJECT-TYPE
    SYNTAX       TWeight
    MAX-ACCESS   read-create
    STATUS       current
    DESCRIPTION
        "The value of sapIngQosSParentCIRWeight specifies the weight that needs
         to be used until the committed rate by this virtual scheduler to which
         this queue would be feeding."
    DEFVAL { 1 }
    ::= { sapIngQosSchedInfoEntry 13 }

-- ------------------------------------
-- SAP Egress QoS Scheduler Table
-- ------------------------------------
sapEgrQosSchedInfoTable OBJECT-TYPE
    SYNTAX          SEQUENCE OF SapEgrQosSchedInfoEntry
    MAX-ACCESS      not-accessible
    STATUS          current
    DESCRIPTION     "This table is used to override the base parameters
                     of a virtual scheduler, as defined in the associated
                     SAP egress scheduler policy."
    ::= { tmnxSapObjs 22 }

sapEgrQosSchedInfoEntry OBJECT-TYPE
    SYNTAX          SapEgrQosSchedInfoEntry
    MAX-ACCESS      not-accessible
    STATUS          current
    DESCRIPTION     "Override values for the specified SAP egress virtual
                     scheduler. These values override the corresponding
                     ones specified in the associated SAP egress scheduler
                     policy."
    INDEX           { svcId,
                      sapPortId,
                      sapEncapValue,
                      IMPLIED sapEgrQosSName }
    ::= { sapEgrQosSchedInfoTable 1 }

SapEgrQosSchedInfoEntry ::=
    SEQUENCE {
        sapEgrQosSName              TNamedItem,
        sapEgrQosSRowStatus         RowStatus,
        sapEgrQosSLastMgmtChange    TimeStamp,
        sapEgrQosSOverrideFlags     TVirtSchedAttribute,
        sapEgrQosSPIR               THPolVirtualSchePIRRate,
        sapEgrQosSCIR               THPolVirtualScheCIRRate,
        sapEgrQosSSummedCIR         TruthValue,
        sapEgrQosSPIRHi             Unsigned32,
        sapEgrQosSPIRLo             Unsigned32,
        sapEgrQosSCIRHi             Unsigned32,
        sapEgrQosSCIRLo             Unsigned32,
        sapEgrQosSParentWeight      TWeight,
        sapEgrQosSParentCIRWeight   TWeight
    }

sapEgrQosSName OBJECT-TYPE
    SYNTAX          TNamedItem
    MAX-ACCESS      not-accessible
    STATUS          current
    DESCRIPTION     "The value of sapEgrQosSName indicates the name of
                     the virtual scheduler whose parameters are to be
                     overridden."
    ::= { sapEgrQosSchedInfoEntry 1 }

sapEgrQosSRowStatus OBJECT-TYPE
    SYNTAX          RowStatus
    MAX-ACCESS      read-create
    STATUS          current
    DESCRIPTION     "The value of sapEgrQosSRowStatus controls the creation
                     and deletion of rows in this table."
    ::= { sapEgrQosSchedInfoEntry 2 }

sapEgrQosSLastMgmtChange OBJECT-TYPE
    SYNTAX          TimeStamp
    MAX-ACCESS      read-only
    STATUS          current
    DESCRIPTION     "The value of sapEgrQosSLastMgmtChange indicates the
                     value of sysUpTime at the time of the last management
                     change of any writable object of this row."
    ::= { sapEgrQosSchedInfoEntry 3 }

sapEgrQosSOverrideFlags OBJECT-TYPE
    SYNTAX          TVirtSchedAttribute
    MAX-ACCESS      read-create
    STATUS          current
    DESCRIPTION     "The value of sapEgrQosSOverrideFlags specifies the
                     set of attributes whose values have been overridden
                     via management on this virtual scheduler. Clearing a
                     given flag will return the corresponding overridden
                     attribute to the value defined on the SAP's egress
                     scheduler policy."
    ::= { sapEgrQosSchedInfoEntry 4 }

sapEgrQosSPIR OBJECT-TYPE
    SYNTAX          THPolVirtualSchePIRRate
    UNITS           "kilo bits per second"
    MAX-ACCESS      read-create
    STATUS          obsolete
    DESCRIPTION     "The value of sapEgrQosSPIR specifies the desired
                     PIR value for this virtual scheduler.
       
                     This object is obsoleted in 11.0 Release. It is replaced by 
                     sapEgrQosSPIRHi and sapEgrQosSPIRLo."
    DEFVAL { -1 }
    ::= { sapEgrQosSchedInfoEntry 5 }

sapEgrQosSCIR OBJECT-TYPE
    SYNTAX          THPolVirtualScheCIRRate
    UNITS           "kilo bits per second"
    MAX-ACCESS      read-create
    STATUS          obsolete
    DESCRIPTION     "The value of sapEgrQosSCIR specifies the desired
                     CIR value for this virtual scheduler.
            
                     This object is obsoleted in 11.0 Release. It is replaced by 
                     sapEgrQosSCIRHi and sapEgrQosSCIRLo."
    DEFVAL { -1 }
    ::= { sapEgrQosSchedInfoEntry 6 }

sapEgrQosSSummedCIR     OBJECT-TYPE
    SYNTAX          TruthValue
    MAX-ACCESS      read-create
    STATUS          current
    DESCRIPTION     "The value of sapEgrQosSSummedCIR specifies if the CIR
                     should be used as the summed CIR values of the children
                     schedulers or queues. If set to 'true', the applicable
                     scheduler CIR (sapEgrQosSCIR) loses its meaning."
    DEFVAL { true }
    ::= { sapEgrQosSchedInfoEntry 7 }

sapEgrQosSPIRHi OBJECT-TYPE
    SYNTAX       Unsigned32 (0 | 4294967295)
    UNITS        "kbps"
    MAX-ACCESS   read-create
    STATUS       current
    DESCRIPTION  "The value of sapEgrQosSPIRHi indicates upper 32 bits of the
                  pir-rate allowed for this virtual scheduler.    

                  This value should always be set along with sapEgrQosSPIRLo,
                  otherwise an 'inconsistentValue' error is returned.

                  When the value of sapEgrQosSPIRHi along with the value of
                  sapEgrQosSPIRLo is set to 4294967295 (0xFFFFFFFF), rate
                  for this virtual scheduler indicates maximum rate."
    DEFVAL { 4294967295 }
    ::= { sapEgrQosSchedInfoEntry 8 }

sapEgrQosSPIRLo OBJECT-TYPE
    SYNTAX       Unsigned32 (1..3200000000 | 4294967295)
    UNITS        "kbps"
    MAX-ACCESS   read-create
    STATUS       current
    DESCRIPTION  "The value of sapEgrQosSPIRLo indicates lower 32 bits of the
                  pir-rate allowed for this virtual scheduler.    

                  This value should always be set along with sapEgrQosSPIRHi,
                  otherwise an 'inconsistentValue' error is returned.

                  When the value of sapEgrQosSPIRHi along with the value of
                  sapEgrQosSPIRLo is set to 4294967295 (0xFFFFFFFF), rate
                  for this virtual scheduler indicates maximum rate."
    DEFVAL { 4294967295 }
    ::= { sapEgrQosSchedInfoEntry 9 }

sapEgrQosSCIRHi OBJECT-TYPE
    SYNTAX       Unsigned32 (0 | 4294967295)
    UNITS        "kbps"
    MAX-ACCESS   read-create
    STATUS       current
    DESCRIPTION  "The value of sapEgrQosSCIRHi indicates upper 32 bits of the
                  cir-rate allowed for this virtual scheduler.    

                  This value should always be set along with sapEgrQosSCIRLo,
                  otherwise an 'inconsistentValue' error is returned.

                  When the value of sapEgrQosSCIRHi along with the value of
                  sapEgrQosSCIRLo is set to 4294967295 (0xFFFFFFFF), rate
                  for this virtual scheduler indicates maximum rate."
    DEFVAL { 4294967295 }
    ::= { sapEgrQosSchedInfoEntry 10 }

sapEgrQosSCIRLo OBJECT-TYPE
    SYNTAX       Unsigned32 (0..3200000000 | 4294967295)
    UNITS        "kbps"
    MAX-ACCESS   read-create
    STATUS       current
    DESCRIPTION  "The value of sapEgrQosSCIRLo indicates lower 32 bits of the
                  cir-rate allowed for this virtual scheduler.    

                  This value should always be set along with sapEgrQosSCIRHi,
                  otherwise an 'inconsistentValue' error is returned.

                  When the value of sapEgrQosSCIRHi along with the value of
                  sapEgrQosSCIRLo is set to 4294967295 (0xFFFFFFFF), rate
                  for this virtual scheduler indicates maximum rate."
    DEFVAL { 4294967295 }
    ::= { sapEgrQosSchedInfoEntry 11 }

sapEgrQosSParentWeight              OBJECT-TYPE
    SYNTAX       TWeight
    MAX-ACCESS   read-create
    STATUS       current
    DESCRIPTION
        "The value of sapEgrQosSParentWeight specifies the weight that needs
         to be used by this virtual scheduler to which this queue would be
         feeding."
    DEFVAL { 1 }
    ::= { sapEgrQosSchedInfoEntry 12 }


sapEgrQosSParentCIRWeight           OBJECT-TYPE
    SYNTAX       TWeight
    MAX-ACCESS   read-create
    STATUS       current
    DESCRIPTION
        "The value of sapEgrQosSParentCIRWeight specifies the weight that needs
         to be used until the committed rate by this virtual scheduler to which
         this queue would be feeding."
    DEFVAL { 1 }
    ::= { sapEgrQosSchedInfoEntry 13 }

-- --------------------------------------
-- SAP Subscriber Management Table
-- --------------------------------------
sapSubMgmtInfoTable OBJECT-TYPE
    SYNTAX          SEQUENCE OF SapSubMgmtInfoEntry
    MAX-ACCESS      not-accessible
    STATUS          current
    DESCRIPTION     "A table that contains SAP subscriber management
                     information."
    ::= { tmnxSapObjs 23 }

sapSubMgmtInfoEntry OBJECT-TYPE
    SYNTAX          SapSubMgmtInfoEntry
    MAX-ACCESS      not-accessible
    STATUS          current
    DESCRIPTION     "Subscriber management specific information about a SAP."
    INDEX           { svcId, sapPortId, sapEncapValue }
    ::= { sapSubMgmtInfoTable 1 }

SapSubMgmtInfoEntry ::=
    SEQUENCE {
        sapSubMgmtAdminStatus           TmnxEnabledDisabled,
        sapSubMgmtDefSubProfile         ServObjName,
        sapSubMgmtDefSlaProfile         ServObjName,
        sapSubMgmtSubIdentPolicy        ServObjName,
        sapSubMgmtSubscriberLimit       TmnxSapSubscriberLimit,
        sapSubMgmtProfiledTrafficOnly   TruthValue,
        sapSubMgmtNonSubTrafficSubIdent DisplayString,
        sapSubMgmtNonSubTrafficSubProf  ServObjName,
        sapSubMgmtNonSubTrafficSlaProf  ServObjName,
        sapSubMgmtMacDaHashing          TruthValue,
        sapSubMgmtDefSubIdent           TmnxDefSubIdSource,
        sapSubMgmtDefSubIdentString     DisplayString,
        sapSubMgmtDefAppProfile         ServObjName,
        sapSubMgmtNonSubTrafficAppProf  ServObjName,
        sapSubMgmtDefInterDestId        TmnxDefInterDestIdSource,
        sapSubMgmtDefInterDestIdString  DisplayString,
        sapSubMgmtDefFilterProfile      TNamedItemOrEmpty
    }

sapSubMgmtAdminStatus OBJECT-TYPE
    SYNTAX          TmnxEnabledDisabled
    MAX-ACCESS      read-create
    STATUS          current
    DESCRIPTION     "The value of sapSubMgmtAdminStatus specifies whether
                     enhanced subscriber management is enabled on this SAP."
    DEFVAL { disabled }
    ::= { sapSubMgmtInfoEntry 1 }

sapSubMgmtDefSubProfile OBJECT-TYPE
    SYNTAX          ServObjName
    MAX-ACCESS      read-create
    STATUS          current
    DESCRIPTION     "The value of sapSubMgmtDefSubProfile specifies the default
                     subscriber profile applicable on this SAP. The
                     corresponding profile is defined in
                     TIMETRA-SUBSCRIBER-MGMT-MIB::tmnxSubProfileTable.

                     A value of 'default' is not allowed for this object."
    DEFVAL { "" }
    ::= { sapSubMgmtInfoEntry 2 }

sapSubMgmtDefSlaProfile OBJECT-TYPE
    SYNTAX          ServObjName
    MAX-ACCESS      read-create
    STATUS          current
    DESCRIPTION     "The value of sapSubMgmtDefSlaProfile specifies the default
                     SLA profile applicable on this SAP. The corresponding
                     profile is defined in
                     TIMETRA-SUBSCRIBER-MGMT-MIB::tmnxSLAProfileTable."
    DEFVAL { "" }
    ::= { sapSubMgmtInfoEntry 3 }

sapSubMgmtSubIdentPolicy OBJECT-TYPE
    SYNTAX          ServObjName
    MAX-ACCESS      read-create
    STATUS          current
    DESCRIPTION     "The value of sapSubMgmtSubIdentPolicy specifies the
                     subscriber identification policy applicable on this SAP.
                     The corresponding policy is defined in
                     TIMETRA-SUBSCRIBER-MGMT-MIB::tmnxSubIdentPolicyTable."
    DEFVAL { "" }
    ::= { sapSubMgmtInfoEntry 4 }

sapSubMgmtSubscriberLimit OBJECT-TYPE
    SYNTAX          TmnxSapSubscriberLimit
    MAX-ACCESS      read-create
    STATUS          current
    DESCRIPTION     "The value of sapSubMgmtSubscriberLimit specifies the
                     maximum number of subscribers allowed for this SAP.

                     If the value is 0, there is no limit. Only if the value is
                     1, the 'single-sub-parameters' defined with objects
                     sapSubMgmtProfiledTrafficOnly,
                     sapSubMgmtNonSubTrafficSubProf and
                     sapSubMgmtNonSubTrafficSlaProf are meaningful."
    DEFVAL { 1 }
    ::= { sapSubMgmtInfoEntry 5 }

sapSubMgmtProfiledTrafficOnly OBJECT-TYPE
    SYNTAX          TruthValue
    MAX-ACCESS      read-create
    STATUS          current
    DESCRIPTION     "The value of sapSubMgmtProfiledTrafficOnly specifies
                     whether only profiled traffic is applicable for this SAP.
                     If set to 'true', all SAP queues will be deleted.

                     The value of this object is only meaningful if
                     sapSubMgmtSubscriberLimit is set to 1."
    DEFVAL { false }
    ::= { sapSubMgmtInfoEntry 6 }

sapSubMgmtNonSubTrafficSubIdent OBJECT-TYPE
    SYNTAX          DisplayString (SIZE (0..32))
    MAX-ACCESS      read-create
    STATUS          current
    DESCRIPTION     "The value of sapSubMgmtNonSubTrafficSubIdent specifies the
                     subscriber identification applicable on this SAP for all
                     non-subscriber traffic.

                     The value of this object is only meaningful if
                     sapSubMgmtSubscriberLimit is set to 1."
    DEFVAL { "" }
    ::= { sapSubMgmtInfoEntry 7 }

sapSubMgmtNonSubTrafficSubProf OBJECT-TYPE
    SYNTAX          ServObjName
    MAX-ACCESS      read-create
    STATUS          current
    DESCRIPTION     "The value of sapSubMgmtNonSubTrafficSubProf specifies the
                     subscriber profile applicable on this SAP for all
                     non-subscriber traffic.

                     The value of this object is only meaningful if
                     sapSubMgmtSubscriberLimit is set to 1."
    DEFVAL { "" }
    ::= { sapSubMgmtInfoEntry 8 }

sapSubMgmtNonSubTrafficSlaProf OBJECT-TYPE
    SYNTAX          ServObjName
    MAX-ACCESS      read-create
    STATUS          current
    DESCRIPTION     "The value of sapSubMgmtNonSubTrafficSlaProf specifies the
                     SLA profile applicable on this SAP for all non-subscriber
                     traffic.

                     The value of this object is only meaningful if
                     sapSubMgmtSubscriberLimit is set to 1."
    DEFVAL { "" }
    ::= { sapSubMgmtInfoEntry 9 }

sapSubMgmtMacDaHashing OBJECT-TYPE
    SYNTAX          TruthValue
    MAX-ACCESS      read-create
    STATUS          current
    DESCRIPTION     "The value of sapSubMgmtMacDaHashing specifies whether
                     subscriber traffic egressing a LAG SAP has its egress LAG
                     link selected by a function of the MAC destination address
                     instead of subscriber id.

                     The value of this object is only meaningful if
                     sapSubMgmtAdminStatus is set to 'enabled' and can only
                     be configured for TLS services."
    DEFVAL { false }
    ::= { sapSubMgmtInfoEntry 10 }

sapSubMgmtDefSubIdent OBJECT-TYPE
    SYNTAX          TmnxDefSubIdSource
    MAX-ACCESS      read-create
    STATUS          current
    DESCRIPTION     "The value of sapSubMgmtDefSubIdent specifies what is
                     used as the default subscriber identification applicable
                     on this SAP.

                     This value is used in case no other source (like Radius)
                     provides a subscriber identification string.

                     If the value of this objects is set to 'useSapId',
                     the SAP-id is used as the default subscriber identification
                     string. In this case, sapSubMgmtDefSubIdentString must
                     contain the empty string.

                     If the value of this objects is set to 'useAutoId',
                     the auto-generated subscriber identification string,
                     as defined in tmnxSubMgmtAutoSubIdObjs, is used as the
                     default subscriber identification string. In this case,
                     sapSubMgmtDefSubIdentString must contain the empty string.

                     If the value of this object is set to 'useString',
                     the value of sapSubMgmtDefSubIdentString is used as the
                     default subscriber identification string. In this case,
                     an empty sapSubMgmtDefSubIdentString means that there is no
                     default subscriber identification configured."
    DEFVAL { useString }
    ::= { sapSubMgmtInfoEntry 11 }

sapSubMgmtDefSubIdentString OBJECT-TYPE
    SYNTAX          DisplayString (SIZE (0..32))
    MAX-ACCESS      read-create
    STATUS          current
    DESCRIPTION     "The value of sapSubMgmtDefSubIdentString specifies the
                     default subscriber identification string applicable on
                     this SAP."
    DEFVAL { "" }
    ::= { sapSubMgmtInfoEntry 12 }

sapSubMgmtDefAppProfile OBJECT-TYPE
    SYNTAX          ServObjName
    MAX-ACCESS      read-create
    STATUS          current
    DESCRIPTION     "The value of sapSubMgmtDefAppProfile specifies the default
                     application profile applicable on this SAP. The
                     corresponding profile is defined in
                     TIMETRA-BSX-NG-MIB::tmnxBsxAppProfTable."
    DEFVAL { "" }
    ::= { sapSubMgmtInfoEntry 13 }

sapSubMgmtNonSubTrafficAppProf OBJECT-TYPE
    SYNTAX          ServObjName
    MAX-ACCESS      read-create
    STATUS          current
    DESCRIPTION     "The value of sapSubMgmtNonSubTrafficAppProf specifies the
                     application profile applicable on this SAP for all
                     non-subscriber traffic.

                     The value of this object is only meaningful if
                     sapSubMgmtSubscriberLimit is set to 1."
    DEFVAL { "" }
    ::= { sapSubMgmtInfoEntry 14 }

sapSubMgmtDefInterDestId OBJECT-TYPE
    SYNTAX          TmnxDefInterDestIdSource
    MAX-ACCESS      read-create
    STATUS          current
    DESCRIPTION     "The value of sapSubMgmtDefInterDestId specifies what is
                     used as the default intermediate destination identifier
                     applicable on this SAP.

                     This value is used in case no other source (like Radius)
                     provides an intermediate destination identifier.

                     If the value of this object is set to 'useString',
                     the value of sapSubMgmtDefInterDestIdString is used as
                     the default intermediate destination identifier. In this
                     case, an empty sapSubMgmtDefInterDestIdString means that
                     there is no default intermediate destination identifier
                     configured.

                     If the value of this object is set to 'useTopQTag', the
                     top q-tag of this SAP is used as the default intermediate
                     destination identifier. In this case,
                     sapSubMgmtDefInterDestIdString must contain the empty
                     string.

                     If the value of this object is set to 'useVpi', the
                     ATM VPI of this SAP is used as the default intermediate
                     destination identifier. In this case,
                     sapSubMgmtDefInterDestIdString must contain the empty
                     string."
    DEFVAL { useString }
    ::= { sapSubMgmtInfoEntry 15 }

sapSubMgmtDefInterDestIdString OBJECT-TYPE
    SYNTAX          DisplayString (SIZE (0..32))
    MAX-ACCESS      read-create
    STATUS          current
    DESCRIPTION     "The value of sapSubMgmtDefInterDestIdString specifies the
                     default intermediate destination identifier applicable on
                     this SAP."
    DEFVAL { "" }
    ::= { sapSubMgmtInfoEntry 16 }

sapSubMgmtDefFilterProfile OBJECT-TYPE
    SYNTAX          TNamedItemOrEmpty
    MAX-ACCESS      read-create
    STATUS          current
    DESCRIPTION     "The value of the object sapSubMgmtDefFilterProfile specifies
                     the default filter profile for this SAP. The specified
                     filter profile needs to exists in the
                     TIMETRA-SUBSCRIBER-MGMT-MIB::tmnxSubFilterProfileTable."
    DEFVAL          { "" }
    ::= { sapSubMgmtInfoEntry 17 }

-- -----------------------------------------
-- SAP TLS MSTI Table
-- -----------------------------------------
sapTlsMstiTable OBJECT-TYPE
    SYNTAX          SEQUENCE OF SapTlsMstiEntry
    MAX-ACCESS      not-accessible
    STATUS          current
    DESCRIPTION     "This table contains Multiple Spanning Tree Instance
                     information for the SAP. Each management VPLS running
                     MSTP can have upto 15 MSTI. An entry in this table is
                     automatically created when a tlsMstiEntry is created."
    ::= { tmnxSapObjs 24 }

sapTlsMstiEntry OBJECT-TYPE
    SYNTAX          SapTlsMstiEntry
    MAX-ACCESS      not-accessible
    STATUS          current
    DESCRIPTION     "Information about a specific MSTI for a SAP."
    INDEX           { svcId, sapPortId, sapEncapValue, tlsMstiInstanceId}
    ::= { sapTlsMstiTable 1 }

SapTlsMstiEntry ::=
    SEQUENCE {
        sapTlsMstiPriority          Integer32,
        sapTlsMstiPathCost          INTEGER,
        sapTlsMstiLastMgmtChange    TimeStamp,
        sapTlsMstiPortRole          StpPortRole,
        sapTlsMstiPortState         TStpPortState,
        sapTlsMstiDesignatedBridge  BridgeId,
        sapTlsMstiDesignatedPort    Integer32
    }

sapTlsMstiPriority OBJECT-TYPE
    SYNTAX          Integer32 (0..255)
    MAX-ACCESS      read-write
    STATUS          current
    DESCRIPTION     "The value of the object sapTlsMstiPriority specifies
                     the value of the port priority field which is contained in
                     the most significant 4 bits of the 16-bit Port ID
                     associated with this SAP and MSTI. As only the most
                     significant 4 bits of the value are used, the actual value
                     of this object is limited to multiples of 16: e.g. the
                     agent rounds down the value to one of: 0, 16, 32, .. ,
                     224, 240."
    DEFVAL          { 128 }
    ::= { sapTlsMstiEntry 1 }

sapTlsMstiPathCost OBJECT-TYPE
    SYNTAX          INTEGER (1..200000000)
    MAX-ACCESS      read-write
    STATUS          current
    DESCRIPTION     "The value of the object sapTlsMstiPathCost specifies the
                     contribution of this port to the MSTI path cost of paths
                     towards the spanning tree regional root which include this
                     port."
    DEFVAL          { 10 }
    ::= { sapTlsMstiEntry 2 }

sapTlsMstiLastMgmtChange OBJECT-TYPE
    SYNTAX          TimeStamp
    MAX-ACCESS      read-only
    STATUS          current
    DESCRIPTION     "The value of the object sapTlsMstiLastMgmtChange indicates
                     the value of sysUpTime at the time of the most recent
                     management-initiated change to this SAP MSTI information."
    ::= { sapTlsMstiEntry 3 }

sapTlsMstiPortRole OBJECT-TYPE
    SYNTAX          StpPortRole
    MAX-ACCESS      read-only
    STATUS          current
    DESCRIPTION     "sapTlsMstiPortRole indicates the current role of the
                     sap in the MSTI as defined by the Spanning Tree Protocol."
    ::= { sapTlsMstiEntry 4 }

sapTlsMstiPortState OBJECT-TYPE
    SYNTAX          TStpPortState
    MAX-ACCESS      read-only
    STATUS          current
    DESCRIPTION     "The value of the object sapTlsMstiPortState indicates the
                     port's current state as defined by application of the
                     Spanning Tree Protocol. This state controls what action a
                     port takes on reception of a frame. If the bridge has
                     detected a port that is malfunctioning it will
                     place that port into the 'broken' state."
    ::= { sapTlsMstiEntry 5 }

sapTlsMstiDesignatedBridge OBJECT-TYPE
    SYNTAX          BridgeId
    MAX-ACCESS      read-only
    STATUS          current
    DESCRIPTION     "The value of the object sapTlsMstiDesignatedBridge
                     indicates  the Bridge Identifier of the bridge which this
                     port considers to be the Designated Bridge for this port's
                     segment for this MSTI."
    ::= { sapTlsMstiEntry 6 }

sapTlsMstiDesignatedPort OBJECT-TYPE
    SYNTAX          Integer32
    MAX-ACCESS      read-only
    STATUS          current
    DESCRIPTION     "The value of the object sapTlsMstiDesignatedPort indicates
                     the Port Identifier of the port on the Designated Bridge
                     for this port's segment for this MSTI."
    ::= { sapTlsMstiEntry 7 }

-- -------------------------------------
-- IPIPE SAP Table
-- -------------------------------------
sapIpipeInfoTable OBJECT-TYPE
    SYNTAX          SEQUENCE OF SapIpipeInfoEntry
    MAX-ACCESS      not-accessible
    STATUS          current
    DESCRIPTION     "A table that contains IPIPE specific SAP information."
    ::= { tmnxSapObjs 25 }

sapIpipeInfoEntry OBJECT-TYPE
    SYNTAX          SapIpipeInfoEntry
    MAX-ACCESS      not-accessible
    STATUS          current
    DESCRIPTION     "IPIPE specific information about a SAP."
    INDEX           { svcId, sapPortId, sapEncapValue }
    ::= { sapIpipeInfoTable 1 }

SapIpipeInfoEntry ::=
    SEQUENCE {
        sapIpipeCeInetAddressType           InetAddressType,
        sapIpipeCeInetAddress               InetAddress,
        sapIpipeMacRefreshInterval          Unsigned32,
        sapIpipeMacAddress                  MacAddress,
        sapIpipeArpedMacAddress             MacAddress,
        sapIpipeArpedMacAddressTimeout      Unsigned32,
        sapIpipeDiscoveredCeInetAddrType    InetAddressType,
        sapIpipeDiscoveredCeInetAddr        InetAddress,
        sapIpipeUseBroadcastMac             TruthValue,
        sapIpipeUsingBroadcastMac           TruthValue,
        sapIpipeIpv6LinkLocalCeInetAddr     InetAddress,
        sapIpipeIpv6GlobalCeInetAddr        InetAddress,
        sapIpipeIpv6DiscoveredMacAddress    MacAddress,
        sapIpipeLegacyFaultNotification     TruthValue,
        sapIpipeRemainRecoveryTimer         Unsigned32
    }

sapIpipeCeInetAddressType OBJECT-TYPE
    SYNTAX          InetAddressType
    MAX-ACCESS      read-write
    STATUS          current
    DESCRIPTION     "The value of the object sapIpipeCeInetAddressType
                     specifies the addresstype of the local end host IP
                     of an IPIPE.

                     This object is only configurable if the value of
                     'svcIpipeCeAddressDiscovery' is 'disabled."
    ::= { sapIpipeInfoEntry 1}

sapIpipeCeInetAddress OBJECT-TYPE
    SYNTAX          InetAddress (SIZE(0|4))
    MAX-ACCESS      read-write
    STATUS          current
    DESCRIPTION     "The type of this address is determined by the value of
                     the sapIpipeCeInetAddressType object.

                     This object specifies the IPv4 address of the
                     local end host of an IPIPE.

                     This object is only configurable if the value of
                     'svcIpipeCeAddressDiscovery' is 'disabled."
    ::= { sapIpipeInfoEntry 2 }

sapIpipeMacRefreshInterval OBJECT-TYPE
    SYNTAX      Unsigned32 (0..65535)
    UNITS       "seconds"
    MAX-ACCESS  read-write
    STATUS      current
    DESCRIPTION
        "The value of sapIpipeMacRefreshInterval specifies the interval
         between successive attempts to refresh the MAC address of the CE
         device associated with an Ethernet ipipe SAP. If no other event
         (such as reception of an ARP request from the CE) occurs that
         would refresh the MAC address before the end of the interval,
         an ARP request will be originated from the IPIPE SAP."
    DEFVAL { 14400 }
    ::= { sapIpipeInfoEntry 3 }

sapIpipeMacAddress  OBJECT-TYPE
    SYNTAX         MacAddress
    MAX-ACCESS     read-write
    STATUS         current
    DESCRIPTION    "The value of the object sapIpipeMacAddress specifies
                    the MAC address of an IPIPE Ethernet SAP."
    DEFVAL { '000000000000'h }
    ::= { sapIpipeInfoEntry 4 }

sapIpipeArpedMacAddress  OBJECT-TYPE
    SYNTAX         MacAddress
    MAX-ACCESS     read-only
    STATUS         current
    DESCRIPTION    "The value of the object sapIpipeArpedMacAddress indicates
                    the MAC address of the local end host."
    ::= { sapIpipeInfoEntry 5 }

sapIpipeArpedMacAddressTimeout  OBJECT-TYPE
    SYNTAX      Unsigned32 (0..65535)
    MAX-ACCESS     read-only
    STATUS         current
    DESCRIPTION    "The value of the object sapIpipeArpedMacAddressTimeout
                    indicates the number of seconds to wait for the
                    sapIpipeArpedMacAddress to be re-refreshed."
    ::= { sapIpipeInfoEntry 6 }

sapIpipeDiscoveredCeInetAddrType OBJECT-TYPE
    SYNTAX          InetAddressType
    MAX-ACCESS      read-only
    STATUS          current
    DESCRIPTION     "The value of the object sapIpipeDiscoveredCeInetAddrType
                     indicates the addresstype of the local end discovered
                     host IP of an IPIPE SAP."
    ::= { sapIpipeInfoEntry 7}

sapIpipeDiscoveredCeInetAddr OBJECT-TYPE
    SYNTAX          InetAddress (SIZE(0|4))
    MAX-ACCESS      read-only
    STATUS          current
    DESCRIPTION     "The type of this address is determined by the value of
                     the sapIpipeDiscoveredCeInetAddrType object.

                     This object indicates the IPv4 address of the discovered
                     local end host of an IPIPE SAP."
    ::= { sapIpipeInfoEntry 8 }

sapIpipeUseBroadcastMac OBJECT-TYPE
    SYNTAX          TruthValue
    MAX-ACCESS      read-write
    STATUS          current
    DESCRIPTION     "The value of sapIpipeUseBroadcastMac specifies whether
                     to use a broadcast MAC address to forward traffic from
                     the Ethernet Ipipe SAP when sapIpipeArpedMacAddress is
                     not a valid MAC address (no ARPed MAC address).

                     If svcIpipeCeAddressDiscovery is set to 'disabled (2)',
                     this value cannot be changed from the default value.

                     For non-Ethernet SAPs this value cannot be changed
                     from the default value."
    DEFVAL { false }
    ::= { sapIpipeInfoEntry 9 }

sapIpipeUsingBroadcastMac OBJECT-TYPE
    SYNTAX          TruthValue
    MAX-ACCESS      read-only
    STATUS          current
    DESCRIPTION     "The value of sapIpipeUsingBroadcastMac indicates whether
                     a broadcast MAC address is currently being used to
                     forward traffic from the Ethernet Ipipe SAP."
    ::= { sapIpipeInfoEntry 10 }

sapIpipeIpv6LinkLocalCeInetAddr OBJECT-TYPE
    SYNTAX          InetAddress (SIZE(0|16))
    MAX-ACCESS      read-only
    STATUS          current
    DESCRIPTION     "This object indicates the discovered link local IPv6
                     address of the local end host of an IPIPE SAP."
    ::= { sapIpipeInfoEntry 11 }

sapIpipeIpv6GlobalCeInetAddr OBJECT-TYPE
    SYNTAX          InetAddress (SIZE(0|16))
    MAX-ACCESS      read-only
    STATUS          current
    DESCRIPTION     "This object indicates the discovered global IPv6
                     address of the local end host of an IPIPE SAP."
    ::= { sapIpipeInfoEntry 12 }

sapIpipeIpv6DiscoveredMacAddress  OBJECT-TYPE
    SYNTAX         MacAddress
    MAX-ACCESS     read-only
    STATUS         current
    DESCRIPTION    "The value of the object sapIpipeIpv6DiscoveredMacAddress
                    indicates the MAC address of the IPv6 local end host."
    ::= { sapIpipeInfoEntry 13 }

sapIpipeLegacyFaultNotification OBJECT-TYPE
    SYNTAX          TruthValue
    MAX-ACCESS      read-only
    STATUS          current
    DESCRIPTION     "The value of sapIpipeLegacyFaultNotification indicates
                     whethe SAP will propagate fault towards the legacy side."
    ::= { sapIpipeInfoEntry 14 }

sapIpipeRemainRecoveryTimer OBJECT-TYPE
    SYNTAX          Unsigned32
    UNITS           "deci-seconds"
    MAX-ACCESS      read-only
    STATUS          current
    DESCRIPTION     "The value of sapIpipeRemainRecoveryTimer indicates
                     remaining value for the recovery timer.

                     A value of zero indicates that the timer is not ongoing."
    ::= { sapIpipeInfoEntry 15 }

-- -----------------------------------------
-- SAP Base ToD Monitoring Table
-- -----------------------------------------
sapTodMonitorTable OBJECT-TYPE
    SYNTAX          SEQUENCE OF SapTodMonitorEntry
    MAX-ACCESS      not-accessible
    STATUS          current
    DESCRIPTION     "This table contains information on configurable objects
                     on SAP level, that can be modified by a scheduled policy."
    ::= { tmnxSapObjs 26 }

sapTodMonitorEntry OBJECT-TYPE
    SYNTAX          SapTodMonitorEntry
    MAX-ACCESS      not-accessible
    STATUS          current
    DESCRIPTION     "Information about ToD policy modifiable config data
                     for a SAP."
    INDEX           { svcId, sapPortId, sapEncapValue }
    ::= { sapTodMonitorTable 1 }

SapTodMonitorEntry ::=
    SEQUENCE {
        sapCurrentIngressIpFilterId      TFilterID,
        sapCurrentIngressIpv6FilterId    TFilterID,
        sapCurrentIngressMacFilterId     TFilterID,
        sapCurrentIngressQosPolicyId     TSapIngressPolicyID,
        sapCurrentIngressQosSchedPlcy    ServObjName,
        sapCurrentEgressIpFilterId       TFilterID,
        sapCurrentEgressIpv6FilterId     TFilterID,
        sapCurrentEgressMacFilterId      TFilterID,
        sapCurrentEgressQosPolicyId      TSapEgressPolicyID,
        sapCurrentEgressQosSchedPlcy     ServObjName,
        sapIntendedIngressIpFilterId     TFilterID,
        sapIntendedIngressIpv6FilterId   TFilterID,
        sapIntendedIngressMacFilterId    TFilterID,
        sapIntendedIngressQosPolicyId    TSapIngressPolicyID,
        sapIntendedIngressQosSchedPlcy   ServObjName,
        sapIntendedEgressIpFilterId      TFilterID,
        sapIntendedEgressIpv6FilterId    TFilterID,
        sapIntendedEgressMacFilterId     TFilterID,
        sapIntendedEgressQosPolicyId     TSapEgressPolicyID,
        sapIntendedEgressQosSchedPlcy    ServObjName
    }

sapCurrentIngressIpFilterId OBJECT-TYPE
    SYNTAX          TFilterID
    MAX-ACCESS      read-only
    STATUS          current
    DESCRIPTION     "The value of the object sapCurrentIngressIpFilterId
                     indicates the index in the tIPFilterTable corresponding to
                     the ingress filter applied on this SAP, or zero if no
                     filter is currently active.
                     The active filter may deviate from sapIngressIpFilterId in
                     case it is overruled by a ToD Suite policy."
    ::= { sapTodMonitorEntry 1 }

sapCurrentIngressIpv6FilterId OBJECT-TYPE
    SYNTAX          TFilterID
    MAX-ACCESS      read-only
    STATUS          current
    DESCRIPTION     "The value of the object sapCurrentIngressIpv6FilterId
                     indicates the index in the tIPv6FilterTable corresponding
                     to the ingress Ipv6 filter applied on this SAP, or zero if
                     no filter is currently active.
                     The active filter may deviate from sapIngressIpv6FilterId
                     in case it is overruled by a ToD Suite policy."
    ::= { sapTodMonitorEntry 2 }

sapCurrentIngressMacFilterId OBJECT-TYPE
    SYNTAX          TFilterID
    MAX-ACCESS      read-only
    STATUS          current
    DESCRIPTION     "The value of the object sapCurrentIngressMacFilterId
                     indicates the index in the tMacFilterTable corresponding
                     to the ingress Mac filter applied on this SAP, or zero if
                     no filter is currently active.
                     The active filter may deviate from sapIngressMacFilterId
                     in case it is overruled by a ToD Suite policy."
    ::= { sapTodMonitorEntry 3 }

sapCurrentIngressQosPolicyId OBJECT-TYPE
    SYNTAX          TSapIngressPolicyID
    MAX-ACCESS      read-only
    STATUS          current
    DESCRIPTION     "The value of the object sapCurrentIngressQosPolicyId
                     indicates the index in the tSapIngressTable corresponding
                     to the ingress Qos Policy applied on this SAP, or zero if
                     no filter is currently active.
                     The active filter may deviate from sapIngressQosPolicyId
                     in case it is overruled by a ToD Suite policy."
    ::= { sapTodMonitorEntry 4 }

sapCurrentIngressQosSchedPlcy OBJECT-TYPE
    SYNTAX          ServObjName
    MAX-ACCESS      read-only
    STATUS          current
    DESCRIPTION     "The value of the object sapCurrentIngressQosSchedPlcy
                     indicates the ingress QoS scheduler on this SAP, or zero
                     if none is currently active.
                     The active policy may deviate from
                     sapIngressQosSchedulerPolicy in case it is overruled by a
                     ToD Suite policy defined on this SAP, or on the
                     multi-service this SAP belongs to. "
    ::= { sapTodMonitorEntry 5 }

sapCurrentEgressIpFilterId OBJECT-TYPE
    SYNTAX          TFilterID
    MAX-ACCESS      read-only
    STATUS          current
    DESCRIPTION     "The value of the object sapCurrentEgressIpFilterId
                     indicates the index in the tIPFilterTable corresponding to
                     the Egress filter applied on this SAP, or zero if no
                     filter is currently active.
                     The active filter may deviate from sapEgressIpFilterId in
                     case it is overruled by a ToD Suite policy."
    ::= { sapTodMonitorEntry 6 }

sapCurrentEgressIpv6FilterId OBJECT-TYPE
    SYNTAX          TFilterID
    MAX-ACCESS      read-only
    STATUS          current
    DESCRIPTION     "The value of the object sapCurrentEgressIpv6FilterId
                     indicates the index in the tIPv6FilterTable corresponding
                     to the Egress Ipv6 filter applied on this SAP, or zero if
                     no filter is currently active.
                     The active filter may deviate from sapEgressIpv6FilterId
                     in case it is overruled by a ToD Suite policy."
    ::= { sapTodMonitorEntry 7 }

sapCurrentEgressMacFilterId OBJECT-TYPE
    SYNTAX          TFilterID
    MAX-ACCESS      read-only
    STATUS          current
    DESCRIPTION     "The value of the object sapCurrentEgressMacFilterId
                     indicates the index in the tMacFilterTable corresponding
                     to the Egress Mac filter applied on this SAP, or zero if
                     no filter is currently active.
                     The active filter may deviate from sapEgressMacFilterId in
                     case it is overruled by a ToD Suite policy."
    ::= { sapTodMonitorEntry 8 }

sapCurrentEgressQosPolicyId OBJECT-TYPE
    SYNTAX          TSapEgressPolicyID
    MAX-ACCESS      read-only
    STATUS          current
    DESCRIPTION     "The value of the object sapCurrentEgressQosPolicyId
                     indicates the index in the tSapEgressTable corresponding
                     to the Egress Qos Policy applied on this SAP, or zero if
                     no filter is currently active.
                     The active filter may deviate from sapEgressQosPolicyId in
                     case it is overruled by a ToD Suite policy."
    ::= { sapTodMonitorEntry 9 }

sapCurrentEgressQosSchedPlcy OBJECT-TYPE
    SYNTAX          ServObjName
    MAX-ACCESS      read-only
    STATUS          current
    DESCRIPTION     "The value of the object sapCurrentEgressQosSchedPlcy
                     indicates the Egress QoS scheduler on this SAP, or zero if
                     none is currently active.
                     The active policy may deviate from
                     sapEgressQosSchedulerPolicy in case it is overruled by a
                     ToD Suite policy defined on this SAP, or on the
                     multi-customer this SAP belongs to."
    ::= { sapTodMonitorEntry 10 }

sapIntendedIngressIpFilterId OBJECT-TYPE
    SYNTAX          TFilterID
    MAX-ACCESS      read-only
    STATUS          current
    DESCRIPTION     "The value of the object sapIntendedIngressIpFilterId
                     indicates the index in the tIPFilterTable corresponding
                     to the ingress IP filter that should be applied on
                     this SAP.
                     If it deviates from sapCurrentIngressIpFilterId, this 
                     means that there was a problem when trying to activate
                     this filter. It can only deviate when using ToD Suites
                     for the SAP. When the ToD Suites decides that a new
                     filter must be applied, it will try to do this. If it
                     fails, the current and intended field are not equal."
    ::= { sapTodMonitorEntry 11 }

sapIntendedIngressIpv6FilterId OBJECT-TYPE
    SYNTAX          TFilterID
    MAX-ACCESS      read-only
    STATUS          current
    DESCRIPTION     "The value of the object sapIntendedIngressIpv6FilterId
                     indicates the index in the tIPv6FilterTable corresponding
                     to the ingress Ipv6 filter that should be applied on this
                     SAP. 
                     If it deviates from sapCurrentIngressIpv6FilterId, this
                     means that there was a problem when trying to activate
                     this filter. It can only deviate when using ToD Suites
                     for the SAP. When the ToD Suites decides that a new
                     filter must be applied, it will try to do this. If it
                     fails, the current and intended field are not equal."
    ::= { sapTodMonitorEntry 12 }

sapIntendedIngressMacFilterId OBJECT-TYPE
    SYNTAX          TFilterID
    MAX-ACCESS      read-only
    STATUS          current
    DESCRIPTION     "The value of the object sapIntendedIngressMacFilterId
                     indicates the index in the tMacFilterTable corresponding
                     to the ingress Mac filter that should be applied
                     on this SAP. 
                     If it deviates from sapCurrentIngressMacFilterId, this
                     means that there was a problem when trying to activate
                     this filter. It can only deviate when using ToD Suites for
                     the SAP. When the ToD Suites decides that a new filter
                     must be applied, it will try to do this. If it fails,
                     the current and intended field are not equal."
    ::= { sapTodMonitorEntry 13 }

sapIntendedIngressQosPolicyId OBJECT-TYPE
    SYNTAX          TSapIngressPolicyID
    MAX-ACCESS      read-only
    STATUS          current
    DESCRIPTION     "The value of the object sapIntendedIngressQosPolicyId
                     indicates the index in the tSapIngressTable corresponding
                     to the ingress Qos policy that should be applied
                     on this SAP. 
                     If it deviates from sapCurrentIngressQosPolicyId, this
                     means that there was a problem when trying to activate
                     this filter. It can only deviate when using ToD Suites for
                     the SAP. When the ToD Suites decides that a new filter
                     must be applied, it will try to do this. If it fails, the 
                     current and intended field are not equal."
    ::= { sapTodMonitorEntry 14 }

sapIntendedIngressQosSchedPlcy OBJECT-TYPE
    SYNTAX          ServObjName
    MAX-ACCESS      read-only
    STATUS          current
    DESCRIPTION     "The value of the object sapIntendedIngressQosSchedPlcy
                     indicates the ingress QoS scheduler that should be applied
                     on this SAP. 
                     If it deviates from sapCurrentIngressQosSchedPlcy, this
                     means that there was a problem when trying to activate
                     this filter. It can only deviate when using ToD Suites for
                     the SAP. When the ToD Suites decides that a new filter 
                     must be applied, it will try to do this. If it fails,
                     the current and intended field are not equal."
    ::= { sapTodMonitorEntry 15 }

sapIntendedEgressIpFilterId OBJECT-TYPE
    SYNTAX          TFilterID
    MAX-ACCESS      read-only
    STATUS          current
    DESCRIPTION     "The value of the object sapIntendedEgressIpFilterId
                     indicates the index in the tIPFilterTable corresponding to
                     the Egress IP filter scheduler that should be applied on
                     this SAP. 
                     If it deviates from sapCurrentEgressIpFilterId, this
                     means that there was a problem when trying to activate
                     this filter. It can only deviate when using ToD Suites for
                     the SAP. When the ToD Suites decides that a new filter
                     must be applied, it will try to do this. If it fails, 
                     the current and intended field are not equal."
    ::= { sapTodMonitorEntry 16 }

sapIntendedEgressIpv6FilterId OBJECT-TYPE
    SYNTAX          TFilterID
    MAX-ACCESS      read-only
    STATUS          current
    DESCRIPTION     "The value of the object sapIntendedEgressIpv6FilterId
                     indicates the index in the tIPv6FilterTable corresponding
                     to the Egress IPv6 filter scheduler that should be applied
                     on this SAP. 
                     If it deviates from sapCurrentEgressIpv6FilterId, this
                     means that there was a problem when trying to activate
                     this filter. It can only deviate when using ToD Suites for
                     the SAP. When the ToD Suites decides that a new filter 
                     must be applied, it will try to do this. If it fails, 
                     the current and intended field are not equal."
    ::= { sapTodMonitorEntry 17 }

sapIntendedEgressMacFilterId OBJECT-TYPE
    SYNTAX          TFilterID
    MAX-ACCESS      read-only
    STATUS          current
    DESCRIPTION     "The value of the object sapIntendedEgressMacFilterId
                     indicates the index in the tMacFilterTable corresponding 
                     to the Egress mac filter scheduler that should be applied
                     on this SAP. 
                     If it deviates from sapCurrentEgressMacFilterId, this
                     means that there was a problem when trying to activate
                     this filter. It can only deviate when using ToD Suites for
                     the SAP. When the ToD Suites decides that a new filter 
                     must be applied, it will try to do this. If it fails, 
                     the current and intended field are not equal."
    ::= { sapTodMonitorEntry 18 }

sapIntendedEgressQosPolicyId OBJECT-TYPE
    SYNTAX          TSapEgressPolicyID
    MAX-ACCESS      read-only
    STATUS          current
    DESCRIPTION     "The value of the object sapIntendedEgressQosPolicyId
                     indicates the index in the tSapEgressTable corresponding
                     to the Egress Qos Policy that should be applied
                     on this SAP. 
                     If it deviates from sapCurrentEgressQosPolicyId, this
                     means that there was a problem when trying to activate
                     this filter. It can only deviate when using ToD Suites for
                     the SAP. When the ToD Suites decides that a new filter 
                     must be applied, it will try to do this. If it fails, 
                     the current and intended field are not equal."
    ::= { sapTodMonitorEntry 19 }

sapIntendedEgressQosSchedPlcy OBJECT-TYPE
    SYNTAX          ServObjName
    MAX-ACCESS      read-only
    STATUS          current
    DESCRIPTION     "The value of the object sapIntendedEgressQosSchedPlcy
                     indicates the index in the tSapEgressTable corresponding
                     to the Egress Qos Scheduler policy that should be applied 
                     on this SAP. 
                     If it deviates from sapCurrentEgressQosSchedPlcy, this
                     means that there was a problem when trying to activate
                     this filter. It can only deviate when using ToD Suites for
                     the SAP. When the ToD Suites decides that a new filter 
                     must be applied, it will try to do this. If it fails, 
                     the current and intended field are not equal."
    ::= { sapTodMonitorEntry 20 }

-- -------------------------------------------------
-- SAP Ingress Qos queue stats per Qos policy
-- -------------------------------------------------
sapIngrQosPlcyStatsTable OBJECT-TYPE
    SYNTAX          SEQUENCE OF SapIngrQosPlcyStatsEntry
    MAX-ACCESS      not-accessible
    STATUS          current
    DESCRIPTION     "A table that contains Ingress Qos policy related
                     statistics for a SAP.
                     
                     Conceptual rows in this table are automatically created by
                     the system.
                     
                     No row will be created for a SAP if the value of the object 
                     sapTodSuite is equal to the empty string."
    ::= { tmnxSapObjs 27 }

sapIngrQosPlcyStatsEntry OBJECT-TYPE
    SYNTAX          SapIngrQosPlcyStatsEntry
    MAX-ACCESS      not-accessible
    STATUS          current
    DESCRIPTION     "Statistics about a specific Ingress Qos Policy applied
                     on a specific SAP."
    INDEX           { svcId, sapPortId, sapEncapValue, sapIgQosPlcyId }
    ::= { sapIngrQosPlcyStatsTable 1 }

SapIngrQosPlcyStatsEntry ::=
    SEQUENCE {
        sapIgQosPlcyId                      TSapIngressPolicyID,
        sapIgQosPlcyDroppedHiPrioPackets    Counter64,
        sapIgQosPlcyDroppedHiPrioOctets     Counter64,
        sapIgQosPlcyDroppedLoPrioPackets    Counter64,
        sapIgQosPlcyDroppedLoPrioOctets     Counter64,
        sapIgQosPlcyForwardedInProfPackets  Counter64,
        sapIgQosPlcyForwardedInProfOctets   Counter64,
        sapIgQosPlcyForwardedOutProfPackets Counter64,
        sapIgQosPlcyForwardedOutProfOctets  Counter64
    }

sapIgQosPlcyId OBJECT-TYPE
    SYNTAX          TSapIngressPolicyID
    MAX-ACCESS      not-accessible
    STATUS          current
    DESCRIPTION     "The value of the object sapIgQosPlcyId indicates
                     the row index in the tSapIngressTable corresponding to this
                     ingress QoS policy, or one if no policy is specified."
    ::= { sapIngrQosPlcyStatsEntry 1 }

sapIgQosPlcyDroppedHiPrioPackets OBJECT-TYPE
    SYNTAX          Counter64
    MAX-ACCESS      read-only
    STATUS          current
    DESCRIPTION     "The value of the object sapIgQosPlcyDroppedHiPrioPackets
                     indicates the number of high priority packets,
                     as determined by the SAP ingress QoS
                     policy, dropped by the Qchip due to:
                     MBS exceeded, buffer pool limit exceeded, etc."
    ::= { sapIngrQosPlcyStatsEntry 2 }

sapIgQosPlcyDroppedHiPrioOctets OBJECT-TYPE
    SYNTAX          Counter64
    MAX-ACCESS      read-only
    STATUS          current
    DESCRIPTION     "The value of the object sapIgQosPlcyDroppedHiPrioOctets
                     indicates the number of high priority octets,
                     as determined by the SAP ingress QoS
                     policy, dropped by the Qchip due to:
                     MBS exceeded, buffer pool limit exceeded, etc."
    ::= { sapIngrQosPlcyStatsEntry 3 }

sapIgQosPlcyDroppedLoPrioPackets OBJECT-TYPE
    SYNTAX          Counter64
    MAX-ACCESS      read-only
    STATUS          current
    DESCRIPTION     "The value of the object sapIgQosPlcyDroppedLoPrioPackets
                     indicates the number of low priority packets,
                     as determined by the SAP ingress QoS
                     policy, dropped by the Qchip due to:
                     MBS exceeded, buffer pool limit exceeded, etc."
    ::= { sapIngrQosPlcyStatsEntry 4 }

sapIgQosPlcyDroppedLoPrioOctets OBJECT-TYPE
    SYNTAX          Counter64
    MAX-ACCESS      read-only
    STATUS          current
    DESCRIPTION     "The value of the object sapIgQosPlcyDroppedLoPrioOctets
                     indicates the number of low priority octets,
                     as determined by the SAP ingress QoS
                     policy, dropped by the Qchip due to:
                     MBS exceeded, buffer pool limit exceeded, etc."
    ::= { sapIngrQosPlcyStatsEntry 5 }

sapIgQosPlcyForwardedInProfPackets OBJECT-TYPE
    SYNTAX          Counter64
    MAX-ACCESS      read-only
    STATUS          current
    DESCRIPTION     "The value of the object sapIgQosPlcyForwardedInProfPackets
                     indicates the number of in-profile packets
                     (rate below CIR) forwarded by the ingress Qchip."
    ::= { sapIngrQosPlcyStatsEntry 6 }

sapIgQosPlcyForwardedInProfOctets OBJECT-TYPE
    SYNTAX          Counter64
    MAX-ACCESS      read-only
    STATUS          current
    DESCRIPTION     "The value of the object sapIgQosPlcyForwardedInProfOctets
                     indicates the number of in-profile octets
                     (rate below CIR) forwarded by the ingress Qchip."
    ::= { sapIngrQosPlcyStatsEntry 7 }

sapIgQosPlcyForwardedOutProfPackets OBJECT-TYPE
    SYNTAX          Counter64
    MAX-ACCESS      read-only
    STATUS          current
    DESCRIPTION     "The value of the object sapIgQosPlcyForwardedOutProfPackets
                     indicates the number of out-of-profile packets
                     (rate above CIR) forwarded by the ingress Qchip."
    ::= { sapIngrQosPlcyStatsEntry 8 }

sapIgQosPlcyForwardedOutProfOctets OBJECT-TYPE
    SYNTAX          Counter64
    MAX-ACCESS      read-only
    STATUS          current
    DESCRIPTION     "The value of the object sapIgQosPlcyForwardedOutProfOctets
                     indicates the number of out-of-profile octets
                     (rate above CIR) forwarded by the ingress Qchip."
    ::= { sapIngrQosPlcyStatsEntry 9 }

-- -------------------------------------------------
-- SAP Egress Qos queue stats per Qos policy
-- -------------------------------------------------
sapEgrQosPlcyStatsTable OBJECT-TYPE
    SYNTAX          SEQUENCE OF SapEgrQosPlcyStatsEntry
    MAX-ACCESS      not-accessible
    STATUS          current
    DESCRIPTION     "A table that contains Egress Qos policy related
                     statistics for a SAP.
                     
                     Conceptual rows in this table are automatically created by
                     the system.
                     
                     No row will be created for a SAP if the value of the object 
                     sapTodSuite is equal to the empty string."
    ::= { tmnxSapObjs 28 }

sapEgrQosPlcyStatsEntry OBJECT-TYPE
    SYNTAX          SapEgrQosPlcyStatsEntry
    MAX-ACCESS      not-accessible
    STATUS          current
    DESCRIPTION     "Statistics about a specific Egress Qos Policy applied
                     on a specific SAP."
    INDEX           { svcId, sapPortId, sapEncapValue, sapEgQosPlcyId }
    ::= { sapEgrQosPlcyStatsTable 1 }

SapEgrQosPlcyStatsEntry ::=
    SEQUENCE {
        sapEgQosPlcyId                      TSapEgressPolicyID,
        sapEgQosPlcyDroppedInProfPackets    Counter64,
        sapEgQosPlcyDroppedInProfOctets     Counter64,
        sapEgQosPlcyDroppedOutProfPackets   Counter64,
        sapEgQosPlcyDroppedOutProfOctets    Counter64,
        sapEgQosPlcyForwardedInProfPackets  Counter64,
        sapEgQosPlcyForwardedInProfOctets   Counter64,
        sapEgQosPlcyForwardedOutProfPackets Counter64,
        sapEgQosPlcyForwardedOutProfOctets  Counter64
    }

sapEgQosPlcyId OBJECT-TYPE
    SYNTAX          TSapEgressPolicyID
    MAX-ACCESS      not-accessible
    STATUS          current
    DESCRIPTION     "The value of the object sapEgQosPlcyId indicates
                     the row index in the tSapEgressTable corresponding to this
                     egress QoS policy, or one if no policy is specified."
    ::= { sapEgrQosPlcyStatsEntry 1 }

sapEgQosPlcyDroppedInProfPackets OBJECT-TYPE
    SYNTAX          Counter64
    MAX-ACCESS      read-only
    STATUS          current
    DESCRIPTION     "The value of the object sapEgQosPlcyDroppedInProfPackets
                     indicates the number of in-profile packets,
                     as determined by the SAP egress QoS
                     policy, dropped by the Qchip due to:
                     MBS exceeded, buffer pool limit exceeded, etc."
    ::= { sapEgrQosPlcyStatsEntry 2 }

sapEgQosPlcyDroppedInProfOctets OBJECT-TYPE
    SYNTAX          Counter64
    MAX-ACCESS      read-only
    STATUS          current
    DESCRIPTION     "The value of the object sapEgQosPlcyDroppedInProfOctets
                     indicates the number of in-profile octets,
                     as determined by the SAP egress QoS
                     policy, dropped by the Qchip due to:
                     MBS exceeded, buffer pool limit exceeded, etc."
    ::= { sapEgrQosPlcyStatsEntry 3 }

sapEgQosPlcyDroppedOutProfPackets OBJECT-TYPE
    SYNTAX          Counter64
    MAX-ACCESS      read-only
    STATUS          current
    DESCRIPTION     "The value of the object sapEgQosPlcyDroppedOutProfPackets
                     indicates the number of out-profile packets,
                     as determined by the SAP egress QoS
                     policy, dropped by the Qchip due to:
                     MBS exceeded, buffer pool limit exceeded, etc."
    ::= { sapEgrQosPlcyStatsEntry 4 }

sapEgQosPlcyDroppedOutProfOctets OBJECT-TYPE
    SYNTAX          Counter64
    MAX-ACCESS      read-only
    STATUS          current
    DESCRIPTION     "The value of the object sapEgQosPlcyDroppedOutProfOctets
                     indicates the number of out-profile octets,
                     as determined by the SAP egress QoS
                     policy, dropped by the Qchip due to:
                     MBS exceeded, buffer pool limit exceeded, etc."
    ::= { sapEgrQosPlcyStatsEntry 5 }

sapEgQosPlcyForwardedInProfPackets OBJECT-TYPE
    SYNTAX          Counter64
    MAX-ACCESS      read-only
    STATUS          current
    DESCRIPTION     "The value of the object sapEgQosPlcyForwardedInProfPackets
                     indicates the number of in-profile packets
                     (rate below CIR) forwarded by the egress Qchip."
    ::= { sapEgrQosPlcyStatsEntry 6 }

sapEgQosPlcyForwardedInProfOctets OBJECT-TYPE
    SYNTAX          Counter64
    MAX-ACCESS      read-only
    STATUS          current
    DESCRIPTION     "The value of the object sapEgQosPlcyForwardedInProfOctets
                     indicates the number of in-profile octets
                     (rate below CIR) forwarded by the egress Qchip."
    ::= { sapEgrQosPlcyStatsEntry 7 }

sapEgQosPlcyForwardedOutProfPackets OBJECT-TYPE
    SYNTAX          Counter64
    MAX-ACCESS      read-only
    STATUS          current
    DESCRIPTION     "The value of the object sapEgQosPlcyForwardedOutProfPackets
                     indicates the number of out-of-profile packets
                     (rate above CIR) forwarded by the egress Qchip."
    ::= { sapEgrQosPlcyStatsEntry 8 }

sapEgQosPlcyForwardedOutProfOctets OBJECT-TYPE
    SYNTAX          Counter64
    MAX-ACCESS      read-only
    STATUS          current
    DESCRIPTION     "The value of the object sapEgQosPlcyForwardedOutProfOctets
                     indicates the number of out-of-profile octets
                     (rate above CIR) forwarded by the egress Qchip."
    ::= { sapEgrQosPlcyStatsEntry 9 }

-- ------------------------------------------
-- Ingress QoS Plcy Queue SAP Statistics Table
-- ------------------------------------------
sapIngQosPlcyQueueStatsTable OBJECT-TYPE
    SYNTAX          SEQUENCE OF SapIngQosPlcyQueueStatsEntry
    MAX-ACCESS      not-accessible
    STATUS          current
    DESCRIPTION     "A table that contains ingress QoS queue SAP
                     statistics, per Ingress QoS Policy the queue
                     was used by.
                     
                     Conceptual rows in this table are automatically created by
                     the system.
                     
                     No row will be created for a SAP if the value of the object 
                     sapTodSuite is equal to the empty string."
    ::= { tmnxSapObjs 29 }

sapIngQosPlcyQueueStatsEntry OBJECT-TYPE
    SYNTAX          SapIngQosPlcyQueueStatsEntry
    MAX-ACCESS      not-accessible
    STATUS          current
    DESCRIPTION     "Ingress statistics about a specific SAP's
                     QoS queue for a given Qos policy."
    INDEX           { svcId,
                      sapPortId,
                      sapEncapValue,
                      sapIgQosPlcyQueuePlcyId,
                      sapIgQosPlcyQueueId }
    ::= { sapIngQosPlcyQueueStatsTable 1 }

SapIngQosPlcyQueueStatsEntry ::=
    SEQUENCE {
        sapIgQosPlcyQueuePlcyId                       TSapIngressPolicyID,
        sapIgQosPlcyQueueId                           TSapIngQueueId,
        sapIgQosPlcyQueueStatsOfferedHiPrioPackets    Counter64,
        sapIgQosPlcyQueueStatsDroppedHiPrioPackets    Counter64,
        sapIgQosPlcyQueueStatsOfferedLoPrioPackets    Counter64,
        sapIgQosPlcyQueueStatsDroppedLoPrioPackets    Counter64,
        sapIgQosPlcyQueueStatsOfferedHiPrioOctets     Counter64,
        sapIgQosPlcyQueueStatsDroppedHiPrioOctets     Counter64,
        sapIgQosPlcyQueueStatsOfferedLoPrioOctets     Counter64,
        sapIgQosPlcyQueueStatsDroppedLoPrioOctets     Counter64,
        sapIgQosPlcyQueueStatsForwardedInProfPackets  Counter64,
        sapIgQosPlcyQueueStatsForwardedOutProfPackets Counter64,
        sapIgQosPlcyQueueStatsForwardedInProfOctets   Counter64,
        sapIgQosPlcyQueueStatsForwardedOutProfOctets  Counter64,
        sapIgQosPlcyQueueCustId                       TmnxCustId,
        sapIgQosPlcyQueueStatsUncoloredPacketsOffered Counter64,
        sapIgQosPlcyQueueStatsUncoloredOctetsOffered  Counter64
    }

sapIgQosPlcyQueuePlcyId OBJECT-TYPE
    SYNTAX          TSapIngressPolicyID
    MAX-ACCESS      not-accessible
    STATUS          current
    DESCRIPTION     "The value of the object sapIgQosPlcyQueuePlcyId indicates
                     the row index in the tSapIngressTable corresponding to
                     this ingress QoS policy."
    ::= { sapIngQosPlcyQueueStatsEntry 1 }

sapIgQosPlcyQueueId OBJECT-TYPE
    SYNTAX          TSapIngQueueId
    MAX-ACCESS      not-accessible
    STATUS          current
    DESCRIPTION     "The index of the ingress QoS queue of this SAP used by the
                     policy indicated by sapIgQosPlcyQueuePlcyId."
    ::= { sapIngQosPlcyQueueStatsEntry 2 }

sapIgQosPlcyQueueStatsOfferedHiPrioPackets OBJECT-TYPE
    SYNTAX          Counter64
    MAX-ACCESS      read-only
    STATUS          current
    DESCRIPTION     "The value of sapIgQosPlcyQueueStatsOfferedHiPrioPackets
                     indicates the number of high priority packets,
                     as determined by the SAP ingress QoS policy, offered by
                     the Pchip to the Qchip."
    ::= { sapIngQosPlcyQueueStatsEntry 3 }

sapIgQosPlcyQueueStatsDroppedHiPrioPackets OBJECT-TYPE
    SYNTAX          Counter64
    MAX-ACCESS      read-only
    STATUS          current
    DESCRIPTION     "The value of sapIgQosPlcyQueueStatsDroppedHiPrioPackets
                     indicates the number of high priority packets,
                     as determined by the SAP ingress QoS policy, dropped by
                     the Qchip due to: MBS exceeded, buffer pool limit
                     exceeded, etc."
    ::= { sapIngQosPlcyQueueStatsEntry 4 }

sapIgQosPlcyQueueStatsOfferedLoPrioPackets OBJECT-TYPE
    SYNTAX          Counter64
    MAX-ACCESS      read-only
    STATUS          current
    DESCRIPTION     "The value of sapIgQosPlcyQueueStatsOfferedLoPrioPackets
                     indicates the number of  low priority packets,
                     as determined by the SAP ingress QoS policy, offered by
                     the Pchip to the Qchip."
    ::= { sapIngQosPlcyQueueStatsEntry 5 }

sapIgQosPlcyQueueStatsDroppedLoPrioPackets OBJECT-TYPE
    SYNTAX          Counter64
    MAX-ACCESS      read-only
    STATUS          current
    DESCRIPTION     "The value of sapIgQosPlcyQueueStatsDroppedLoPrioPackets
                     indicates the number of low priority packets,
                     as determined by the SAP ingress QoS policy, dropped by
                     the Qchip due to: MBS exceeded, buffer pool limit
                     exceeded, etc."
    ::= { sapIngQosPlcyQueueStatsEntry 6 }

sapIgQosPlcyQueueStatsOfferedHiPrioOctets OBJECT-TYPE
    SYNTAX          Counter64
    MAX-ACCESS      read-only
    STATUS          current
    DESCRIPTION     "The value of sapIgQosPlcyQueueStatsOfferedHiPrioOctets
                     indicates the number of high priority octets,
                     as determined by the SAP ingress QoS policy, offered by
                     the Pchip to the Qchip."
    ::= { sapIngQosPlcyQueueStatsEntry 7 }

sapIgQosPlcyQueueStatsDroppedHiPrioOctets OBJECT-TYPE
    SYNTAX          Counter64
    MAX-ACCESS      read-only
    STATUS          current
    DESCRIPTION     "The value of sapIgQosPlcyQueueStatsDroppedHiPrioOctets
                     indicates the number ofhigh priority octets,
                     as determined by the SAP ingress QoS policy, dropped by
                     the Qchip due to: MBS exceeded, buffer pool limit
                     exceeded, etc."
    ::= { sapIngQosPlcyQueueStatsEntry 8 }

sapIgQosPlcyQueueStatsOfferedLoPrioOctets OBJECT-TYPE
    SYNTAX          Counter64
    MAX-ACCESS      read-only
    STATUS          current
    DESCRIPTION     "The value of sapIgQosPlcyQueueStatsOfferedLoPrioOctets
                     indicates the number of low priority octets,
                     as determined by the SAP ingress QoS policy, offered by
                     the Pchip to the Qchip."
    ::= { sapIngQosPlcyQueueStatsEntry 9 }

sapIgQosPlcyQueueStatsDroppedLoPrioOctets OBJECT-TYPE
    SYNTAX          Counter64
    MAX-ACCESS      read-only
    STATUS          current
    DESCRIPTION     "The value of sapIgQosPlcyQueueStatsDroppedLoPrioOctets
                     indicates the number of low priority octets,
                     as determined by the SAP ingress QoS policy, dropped by
                     the Qchip due to: MBS exceeded, buffer pool limit
                     exceeded, etc."
    ::= { sapIngQosPlcyQueueStatsEntry 10 }

sapIgQosPlcyQueueStatsForwardedInProfPackets OBJECT-TYPE
    SYNTAX          Counter64
    MAX-ACCESS      read-only
    STATUS          current
    DESCRIPTION     "The value of sapIgQosPlcyQueueStatsForwardedInProfPackets
                     indicates the number of in-profile packets
                     (rate below CIR) forwarded by the ingress Qchip."
    ::= { sapIngQosPlcyQueueStatsEntry 11 }

sapIgQosPlcyQueueStatsForwardedOutProfPackets OBJECT-TYPE
    SYNTAX          Counter64
    MAX-ACCESS      read-only
    STATUS          current
    DESCRIPTION     "The value of sapIgQosPlcyQueueStatsForwardedOutProfPackets
                     indicates the number of out-of-profile packets
                     (rate above CIR) forwarded by the ingress Qchip."
    ::= { sapIngQosPlcyQueueStatsEntry 12 }

sapIgQosPlcyQueueStatsForwardedInProfOctets OBJECT-TYPE
    SYNTAX          Counter64
    MAX-ACCESS      read-only
    STATUS          current
    DESCRIPTION     "The value of sapIgQosPlcyQueueStatsForwardedInProfOctets
                     indicates the number of in-profile octets
                     (rate below CIR) forwarded by the ingress Qchip."
    ::= { sapIngQosPlcyQueueStatsEntry 13 }

sapIgQosPlcyQueueStatsForwardedOutProfOctets OBJECT-TYPE
    SYNTAX          Counter64
    MAX-ACCESS      read-only
    STATUS          current
    DESCRIPTION     "The value of sapIgQosPlcyQueueStatsForwardedOutProfOctets
                     indicates the number of  out-of-profile octets
                     (rate above CIR) forwarded by the ingress Qchip."
    ::= { sapIngQosPlcyQueueStatsEntry 14 }

sapIgQosPlcyQueueCustId OBJECT-TYPE
    SYNTAX          TmnxCustId
    MAX-ACCESS      read-only
    STATUS          current
    DESCRIPTION     "The value of the object sapIgQosPlcyQueueCustId
                     indicates the Customer ID for the associated service."
    ::= { sapIngQosPlcyQueueStatsEntry 15 }

sapIgQosPlcyQueueStatsUncoloredPacketsOffered OBJECT-TYPE
    SYNTAX          Counter64
    MAX-ACCESS      read-only
    STATUS          current
    DESCRIPTION     "The value of sapIgQosPlcyQueueStatsUncoloredPacketsOffered
                     indicates the number of uncolored packets offered to
                     the ingress Qchip."
    ::= { sapIngQosPlcyQueueStatsEntry 16 }

sapIgQosPlcyQueueStatsUncoloredOctetsOffered OBJECT-TYPE
    SYNTAX          Counter64
    MAX-ACCESS      read-only
    STATUS          current
    DESCRIPTION     "The value of sapIgQosPlcyQueueStatsUncoloredOctetsOffered
                     indicates the number of uncolored octets offered to
                     the ingress Qchip."
    ::= { sapIngQosPlcyQueueStatsEntry 17 }

-- ------------------------------------------
-- Egress QoS Plcy Queue SAP Statistics Table
-- ------------------------------------------
sapEgrQosPlcyQueueStatsTable OBJECT-TYPE
    SYNTAX          SEQUENCE OF SapEgrQosPlcyQueueStatsEntry
    MAX-ACCESS      not-accessible
    STATUS          current
    DESCRIPTION     "A table that contains egress QoS queue SAP
                     statistics per Egress QoS Policy the queue
                     was used by.
                     
                     Conceptual rows in this table are automatically created by
                     the system.
                     
                     No row will be created for a SAP if the value of the object 
                     sapTodSuite is equal to the empty string."
    ::= { tmnxSapObjs 30 }

sapEgrQosPlcyQueueStatsEntry OBJECT-TYPE
    SYNTAX          SapEgrQosPlcyQueueStatsEntry
    MAX-ACCESS      not-accessible
    STATUS          current
    DESCRIPTION     "Egress statistics about a specific SAP's
                     QoS queue for a given Qos policy."
    INDEX           { svcId,
                      sapPortId,
                      sapEncapValue,
                      sapEgQosPlcyQueuePlcyId,
                      sapEgQosPlcyQueueId }
    ::= { sapEgrQosPlcyQueueStatsTable 1 }

SapEgrQosPlcyQueueStatsEntry ::=
    SEQUENCE {
        sapEgQosPlcyQueuePlcyId                       TSapEgressPolicyID,
        sapEgQosPlcyQueueId                           TSapEgrQueueId,
        sapEgQosPlcyQueueStatsForwardedInProfPackets  Counter64,
        sapEgQosPlcyQueueStatsDroppedInProfPackets    Counter64,
        sapEgQosPlcyQueueStatsForwardedOutProfPackets Counter64,
        sapEgQosPlcyQueueStatsDroppedOutProfPackets   Counter64,
        sapEgQosPlcyQueueStatsForwardedInProfOctets   Counter64,
        sapEgQosPlcyQueueStatsDroppedInProfOctets     Counter64,
        sapEgQosPlcyQueueStatsForwardedOutProfOctets  Counter64,
        sapEgQosPlcyQueueStatsDroppedOutProfOctets    Counter64,
        sapEgQosPlcyQueueCustId                       TmnxCustId
    }

sapEgQosPlcyQueuePlcyId OBJECT-TYPE
    SYNTAX          TSapEgressPolicyID
    MAX-ACCESS      not-accessible
    STATUS          current
    DESCRIPTION     "The row index in the tSapEgressTable
                     corresponding to this egress QoS policy."
    ::= { sapEgrQosPlcyQueueStatsEntry 1 }

sapEgQosPlcyQueueId OBJECT-TYPE
    SYNTAX          TSapEgrQueueId
    MAX-ACCESS      not-accessible
    STATUS          current
    DESCRIPTION     "The value of sapEgQosPlcyQueueId indicates
                     index of the egress QoS queue of this SAP."
    ::= { sapEgrQosPlcyQueueStatsEntry 2 }

sapEgQosPlcyQueueStatsForwardedInProfPackets OBJECT-TYPE
    SYNTAX          Counter64
    MAX-ACCESS      read-only
    STATUS          current
    DESCRIPTION     "The value of sapEgQosPlcyQueueStatsForwardedInProfPackets
                     indicates the number of in-profile packets (rate below
                     CIR) forwarded by the egress Qchip."
    ::= { sapEgrQosPlcyQueueStatsEntry 3 }

sapEgQosPlcyQueueStatsDroppedInProfPackets OBJECT-TYPE
    SYNTAX          Counter64
    MAX-ACCESS      read-only
    STATUS          current
    DESCRIPTION     "The value of sapEgQosPlcyQueueStatsDroppedInProfPackets
                     indicates the number of in-profile packets discarded by
                     the egress Qchip due to: MBS exceeded, buffer pool limit
                     exceeded, etc."
    ::= { sapEgrQosPlcyQueueStatsEntry 4 }

sapEgQosPlcyQueueStatsForwardedOutProfPackets OBJECT-TYPE
    SYNTAX          Counter64
    MAX-ACCESS      read-only
    STATUS          current
    DESCRIPTION     "The value of sapEgQosPlcyQueueStatsForwardedOutProfPackets
                     indicates the number of out-of-profile packets (rate
                     above CIR) forwarded by the egress Qchip."
    ::= { sapEgrQosPlcyQueueStatsEntry 5 }

sapEgQosPlcyQueueStatsDroppedOutProfPackets OBJECT-TYPE
    SYNTAX          Counter64
    MAX-ACCESS      read-only
    STATUS          current
    DESCRIPTION     "The value of sapEgQosPlcyQueueStatsDroppedOutProfPackets
                     indicates the number out-of-profile packets discarded by
                     the egress Qchip due to: MBS exceeded, buffer pool limit
                     exceeded, etc."
    ::= { sapEgrQosPlcyQueueStatsEntry 6 }

sapEgQosPlcyQueueStatsForwardedInProfOctets OBJECT-TYPE
    SYNTAX          Counter64
    MAX-ACCESS      read-only
    STATUS          current
    DESCRIPTION     "The value of sapEgQosPlcyQueueStatsForwardedInProfOctets
                     indicates the number ofin-profile octets (rate below CIR)
                     forwarded by the egress Qchip."
    ::= { sapEgrQosPlcyQueueStatsEntry 7 }

sapEgQosPlcyQueueStatsDroppedInProfOctets OBJECT-TYPE
    SYNTAX          Counter64
    MAX-ACCESS      read-only
    STATUS          current
    DESCRIPTION     "The value of sapEgQosPlcyQueueStatsDroppedInProfOctets
                     indicates the number in-profile octets discarded by the
                     egress Qchip due to: MBS exceeded, buffer pool limit
                     exceeded, etc."
    ::= { sapEgrQosPlcyQueueStatsEntry 8 }

sapEgQosPlcyQueueStatsForwardedOutProfOctets OBJECT-TYPE
    SYNTAX          Counter64
    MAX-ACCESS      read-only
    STATUS          current
    DESCRIPTION     "The value of sapEgQosPlcyQueueStatsForwardedOutProfOctets
                     indicates the number of out-of-profile octets (rate
                     above CIR) forwarded by the egress Qchip."
    ::= { sapEgrQosPlcyQueueStatsEntry 9 }

sapEgQosPlcyQueueStatsDroppedOutProfOctets OBJECT-TYPE
    SYNTAX          Counter64
    MAX-ACCESS      read-only
    STATUS          current
    DESCRIPTION     "The value of sapEgQosPlcyQueueStatsDroppedOutProfOctets
                     indicates the number out-of-profile octets discarded by
                     the egress Qchip due to: MBS exceeded, buffer pool limit
                     exceeded, etc."
    ::= { sapEgrQosPlcyQueueStatsEntry 10 }

sapEgQosPlcyQueueCustId OBJECT-TYPE
    SYNTAX          TmnxCustId
    MAX-ACCESS      read-only
    STATUS          current
    DESCRIPTION     "The value of the object sapEgQosPlcyQueueCustId indicates
                     the Customer ID for the associated service."
    ::= { sapEgrQosPlcyQueueStatsEntry 11 }

-- ----------------------------------------
-- SAP DHCP Information Table
-- ----------------------------------------
sapDhcpInfoTable OBJECT-TYPE
    SYNTAX          SEQUENCE OF SapDhcpInfoEntry
    MAX-ACCESS      not-accessible
    STATUS          current
    DESCRIPTION     "sapDhcpInfoTable contains DHCP information related to a
                     routed CO subscriber SAP.  This table complements
                     sapBaseInfoTable, and contains an entry for each
                     routed CO subscriber SAP. Rows in this table
                     are created and deleted automatically by the system."
    ::= { tmnxSapObjs 31 }

sapDhcpInfoEntry OBJECT-TYPE
    SYNTAX          SapDhcpInfoEntry
    MAX-ACCESS      not-accessible
    STATUS          current
    DESCRIPTION     "DHCP specific information for a routed CO subscriber SAP."
    INDEX           { svcId, sapPortId, sapEncapValue }
    ::= { sapDhcpInfoTable 1 }

SapDhcpInfoEntry ::=
    SEQUENCE {
        sapDhcpOperLeasePopulate  Unsigned32
    }

sapDhcpOperLeasePopulate OBJECT-TYPE
    SYNTAX          Unsigned32
    MAX-ACCESS      read-only
    STATUS          current
    DESCRIPTION     "The value of the object sapDhcpOperLeasePopulate
                     indicates the number of DHCP lease states currently
                     allocated on this SAP."
    ::= { sapDhcpInfoEntry 1 }

-- -------------------------------------------------
-- SAP Ingress QoS Scheduler Per-Policy Statistics Table
-- -------------------------------------------------
sapIngSchedPlcyStatsTable OBJECT-TYPE
    SYNTAX          SEQUENCE OF SapIngSchedPlcyStatsEntry
    MAX-ACCESS      not-accessible
    STATUS          current
    DESCRIPTION     "A table that contains ingress QoS queue
                     statistics for the SAP's, organized by
                     scheduler policy.
                     
                     Conceptual rows in this table are automatically created by
                     the system.
                     
                     No row will be created for a SAP if the value of the object 
                     sapTodSuite is equal to the empty string."
    ::= { tmnxSapObjs 32 }

sapIngSchedPlcyStatsEntry OBJECT-TYPE
    SYNTAX          SapIngSchedPlcyStatsEntry
    MAX-ACCESS      not-accessible
    STATUS          current
    DESCRIPTION     "Statistics about a specific SAP's ingress Qos Scheduler. 
                     Entries are created when a scheduler policy of a SAP 
                     is replaced with another one due to Time-Of-Day policies."
    INDEX           { svcId, sapPortId, sapEncapValue, tSchedulerPolicyName,
                      IMPLIED sapIngQosSchedName }
    ::= { sapIngSchedPlcyStatsTable 1 }

SapIngSchedPlcyStatsEntry ::=
    SEQUENCE {
        sapIngSchedPlcyStatsFwdPkt    Counter64,
        sapIngSchedPlcyStatsFwdOct    Counter64
    }

sapIngSchedPlcyStatsFwdPkt OBJECT-TYPE
    SYNTAX          Counter64
    MAX-ACCESS      read-only
    STATUS          current
    DESCRIPTION     "The number of forwarded packets, as
                     determined by the SAP ingress scheduler
                     policy, offered by the Pchip to the
                     Qchip."
    ::= { sapIngSchedPlcyStatsEntry 1 }

sapIngSchedPlcyStatsFwdOct OBJECT-TYPE
    SYNTAX          Counter64
    MAX-ACCESS      read-only
    STATUS          current
    DESCRIPTION     "The number of forwarded octets, as
                     determined by the SAP ingress scheduler
                     policy, offered by the Pchip to the
                     Qchip."
    ::= { sapIngSchedPlcyStatsEntry 2 }

-- ---------------------------------------------
-- SAP Egress QoS Scheduler Per-Policy Statistics Table
-- ---------------------------------------------
sapEgrSchedPlcyStatsTable OBJECT-TYPE
    SYNTAX          SEQUENCE OF SapEgrSchedPlcyStatsEntry
    MAX-ACCESS      not-accessible
    STATUS          current
    DESCRIPTION     "A table that contains egress QoS scheduler 
                     statistics for the SAP's, organized by
                     scheduler policy.
                     
                     Conceptual rows in this table are automatically created by
                     the system.
                     
                     No row will be created for a SAP if the value of the object 
                     sapTodSuite is equal to the empty string."
    ::= { tmnxSapObjs 33 }

sapEgrSchedPlcyStatsEntry OBJECT-TYPE
    SYNTAX          SapEgrSchedPlcyStatsEntry
    MAX-ACCESS      not-accessible
    STATUS          current
    DESCRIPTION     "Statistics about a specific SAP's egress QoS scheduler.
                     Entries are created when a scheduler policy of a SAP 
                     is replaced with another one due to Time-Of-Day policies."
    INDEX           { svcId, sapPortId, sapEncapValue, tSchedulerPolicyName,
                      IMPLIED sapEgrQosSchedName }
    ::= { sapEgrSchedPlcyStatsTable 1 }

SapEgrSchedPlcyStatsEntry ::=
    SEQUENCE {
        sapEgrSchedPlcyStatsFwdPkt    Counter64,
        sapEgrSchedPlcyStatsFwdOct    Counter64
    }

sapEgrSchedPlcyStatsFwdPkt OBJECT-TYPE
    SYNTAX          Counter64
    MAX-ACCESS      read-only
    STATUS          current
    DESCRIPTION     "The number of packets forwarded by the
                     egress Qchip, as determined by the SAP
                     egress scheduler policy."
    ::= { sapEgrSchedPlcyStatsEntry 1 }

sapEgrSchedPlcyStatsFwdOct OBJECT-TYPE
    SYNTAX          Counter64
    MAX-ACCESS      read-only
    STATUS          current
    DESCRIPTION     "The number of octets forwarded by the
                     egress Qchip, as determined by the SAP
                     egress scheduler policy."
    ::= { sapEgrSchedPlcyStatsEntry 2 }
-- --------------------------------------------
-- SAP Ingress QoS Scheduler Per-Policy Statistics Table
-- with specific Port ID
-- --------------------------------------------
sapIngSchedPlcyPortStatsTable OBJECT-TYPE
    SYNTAX          SEQUENCE OF SapIngSchedPlcyPortStatsEntry
    MAX-ACCESS      not-accessible
    STATUS          current
    DESCRIPTION
        "The sapIngSchedPlcyPortStatsTable contains 
         ingress QoS scheduler statistics for the SAP's, organized per
         scheduler policy and per port. This table is used when the SAP
         is  a CCAG or LAG in 'link' mode, or an APS. 
         Entries are created when a scheduler policy of a SAP 
         is replaced with another one due to Time-Of-Day policies.
                     
         Conceptual rows in this table are automatically created by
         the system.
         
         No row will be created for a SAP if the value of the object 
         sapTodSuite is equal to the empty string."
    ::= { tmnxSapObjs 34 }

sapIngSchedPlcyPortStatsEntry OBJECT-TYPE
    SYNTAX          SapIngSchedPlcyPortStatsEntry
    MAX-ACCESS      not-accessible
    STATUS          current
    DESCRIPTION     "Statistics about a specific SAP's ingress Qos Scheduler. 
                     Entries are created when a scheduler policy of a SAP 
                     is replaced with another one due to Time-Of-Day policies."
    INDEX           { svcId, sapPortId, sapEncapValue, tSchedulerPolicyName,
                      tVirtualSchedulerName, sapPortIdIngPortId }
    ::= { sapIngSchedPlcyPortStatsTable 1 }

SapIngSchedPlcyPortStatsEntry ::=
    SEQUENCE {
        sapIngSchedPlcyPortStatsPort   TmnxPortID,
        sapIngSchedPlcyPortStatsFwdPkt Counter64,
        sapIngSchedPlcyPortStatsFwdOct Counter64
    }

sapIngSchedPlcyPortStatsPort OBJECT-TYPE
    SYNTAX          TmnxPortID
    MAX-ACCESS      not-accessible
    STATUS          current
    DESCRIPTION     "The value of sapIngSchedPlcyPortStatsPort is used
                     as an index of the ingress QoS scheduler of this SAP. When
                     the SAP is an aps/ccag/lag in 'link' mode, this object is
                     the TmnxPortID of the member-port on which the scheduler is
                     applied."
    ::= {sapIngSchedPlcyPortStatsEntry 1 }

sapIngSchedPlcyPortStatsFwdPkt OBJECT-TYPE
    SYNTAX          Counter64
    MAX-ACCESS      read-only
    STATUS          current
    DESCRIPTION     "The value of sapIngSchedPlcyPortStatsFwdPkt indicates
                     the number of forwarded packets, as determined by the SAP
                     ingress scheduler policy, offered by the Pchip to the
                     Qchip."
    ::= { sapIngSchedPlcyPortStatsEntry 2 }

sapIngSchedPlcyPortStatsFwdOct OBJECT-TYPE
    SYNTAX          Counter64
    MAX-ACCESS      read-only
    STATUS          current
    DESCRIPTION     "The value of sapIngSchedPlcyPortStatsFwdOct indicates
                     the number of forwarded octets,as determined by the SAP
                     ingress scheduler policy, offered by the Pchip to the
                     Qchip."
    ::= { sapIngSchedPlcyPortStatsEntry 3 }


-- ------------------------------------------------------------
-- SAP Egress QoS Scheduler Per-Policy Statistics Table
-- with specific Port ID
-- ------------------------------------------------------------
sapEgrSchedPlcyPortStatsTable OBJECT-TYPE
    SYNTAX          SEQUENCE OF SapEgrSchedPlcyPortStatsEntry
    MAX-ACCESS      not-accessible
    STATUS          current
    DESCRIPTION     
        "The sapEgrSchedPlcyPortStatsTable contains 
         egress QoS scheduler statistics for the SAP's, organized per
         scheduler policy and per port. This table is used when the SAP
         is  a CCAG or LAG in 'link' mode, or an APS. 
         Entries are created when a scheduler policy of a SAP 
         is replaced with another one due to Time-Of-Day policies.
                     
         Conceptual rows in this table are automatically created by
         the system.
         
         No row will be created for a SAP if the value of the object 
         sapTodSuite is equal to the empty string."
    ::= { tmnxSapObjs 35 }

sapEgrSchedPlcyPortStatsEntry OBJECT-TYPE
    SYNTAX          SapEgrSchedPlcyPortStatsEntry
    MAX-ACCESS      not-accessible
    STATUS          current
    DESCRIPTION     "Statistics about a specific SAP's egress Qos Scheduler. 
                     Entries are created when a scheduler policy of a SAP 
                     is replaced with another one due to Time-Of-Day policies."
    INDEX           { svcId, sapPortId, sapEncapValue, tSchedulerPolicyName,
                      tVirtualSchedulerName, sapPortIdEgrPortId }
    ::= { sapEgrSchedPlcyPortStatsTable 1 }

SapEgrSchedPlcyPortStatsEntry ::=
    SEQUENCE {
        sapEgrSchedPlcyPortStatsPort   TmnxPortID,
        sapEgrSchedPlcyPortStatsFwdPkt Counter64,
        sapEgrSchedPlcyPortStatsFwdOct Counter64
    }

sapEgrSchedPlcyPortStatsPort OBJECT-TYPE
    SYNTAX          TmnxPortID
    MAX-ACCESS      not-accessible
    STATUS          current
    DESCRIPTION     "The value of sapEgrSchedPlcyPortStatsPort is used
                     as an index of the egress QoS scheduler of this SAP. When
                     the SAP is an aps/ccag/lag in 'link' mode, this object is
                     the TmnxPortID of the member-port on which the scheduler is
                     applied."
    ::= {sapEgrSchedPlcyPortStatsEntry 1 }

sapEgrSchedPlcyPortStatsFwdPkt OBJECT-TYPE
    SYNTAX          Counter64
    MAX-ACCESS      read-only
    STATUS          current
    DESCRIPTION     "The value of sapEgrSchedPlcyPortStatsFwdPkt indicates
                     the number of forwarded packets, as determined by the SAP
                     egress scheduler policy, offered by the Pchip to the
                     Qchip."
    ::= { sapEgrSchedPlcyPortStatsEntry 2 }

sapEgrSchedPlcyPortStatsFwdOct OBJECT-TYPE
    SYNTAX          Counter64
    MAX-ACCESS      read-only
    STATUS          current
    DESCRIPTION     "The value of sapEgrSchedPlcyPortStatsFwdOct indicates
                     the number of forwarded octets,as determined by the SAP
                     egress scheduler policy, offered by the Pchip to the
                     Qchip."
    ::= { sapEgrSchedPlcyPortStatsEntry 3 }


-- ---------------------------------------------------------------------
--  CEM SAP Information Table
--
--  Sparse Dependent Extention of the sapBaseInfoTable.
--
--  The same indexes are used for both the base table, sapBaseInfoTable,
--  and the sparse dependent table, sapCemInfoTable.
--
--  This in effect extends the sapBaseInfoTable with additional columns.
--  Rows are created in the sapCemInfoTable only for those entries
--  in the sapBaseInfoTable that are created on a port with 'cemEncap'
--  encapsulation.
--
--  Deletion of a row in the sapBaseInfoTable results in the
--  same fate for the row in the sapCemInfoTable.
-- ---------------------------------------------------------------------
sapCemInfoTable OBJECT-TYPE
    SYNTAX          SEQUENCE OF SapCemInfoEntry
    MAX-ACCESS      not-accessible
    STATUS          current
    DESCRIPTION     "A table that contains CEM SAP information."
    ::= { tmnxSapObjs 40 }

sapCemInfoEntry OBJECT-TYPE
    SYNTAX          SapCemInfoEntry
    MAX-ACCESS      not-accessible
    STATUS          current
    DESCRIPTION     "Information about a specific CEM SAP."
    INDEX           { svcId, sapPortId, sapEncapValue }
    ::= { sapCemInfoTable 1 }

SapCemInfoEntry ::=
    SEQUENCE {
        sapCemLastMgmtChange              TimeStamp,
        sapCemEndpointType                INTEGER,
        sapCemBitrate                     Unsigned32,
        sapCemCasTrunkFraming             TdmOptionsCasTrunkFraming,
        sapCemPayloadSize                 Unsigned32,
        sapCemJitterBuffer                Unsigned32,
        sapCemUseRtpHeader                TruthValue,
        sapCemDifferential                TruthValue,
        sapCemTimestampFreq               Unsigned32,
        sapCemReportAlarm                 CemSapReportAlarm,
        sapCemReportAlarmStatus           CemSapReportAlarm,
        sapCemLocalEcid                   CemSapEcid,
        sapCemRemoteMacAddr               MacAddress,
        sapCemRemoteEcid                  CemSapEcid,
        sapCemJitterBufPackets            Unsigned32,
        sapCemPlayoutBufPacketsThreshold  Unsigned32
  }

sapCemLastMgmtChange OBJECT-TYPE
    SYNTAX          TimeStamp
    MAX-ACCESS      read-only
    STATUS          current
    DESCRIPTION     "The value of the object sapCemLastMgmtChange indicates
                     the value of sysUpTime at the time of the most recent
                     management-initiated change to this CEM SAP information."
    ::= { sapCemInfoEntry 1 }

sapCemEndpointType   OBJECT-TYPE
    SYNTAX           INTEGER {
                         unstructuredE1 (1),
                         unstructuredT1 (2),
                         unstructuredE3 (3),
                         unstructuredT3 (4),
                         nxDS0          (5),
                         nxDS0WithCas   (6)
                     }
    MAX-ACCESS       read-only
    STATUS           current
    DESCRIPTION      "This object indicates the CEM SAP endpoint type."
    ::= { sapCemInfoEntry 2 }

sapCemBitrate        OBJECT-TYPE
    SYNTAX           Unsigned32 (0..699)
    UNITS            "64 Kbits/s"
    MAX-ACCESS       read-only
    STATUS           current
    DESCRIPTION      "This object indicates the bit-rate in multiples of
                      64 Kbit/s of the CEM SAP."
    ::= { sapCemInfoEntry 3 }

sapCemCasTrunkFraming  OBJECT-TYPE
    SYNTAX           TdmOptionsCasTrunkFraming
    MAX-ACCESS       read-only
    STATUS           current
    DESCRIPTION      "This object indicates the CAS trunk framing mode of
                      the CEM SAP."
    ::= { sapCemInfoEntry 4 }

sapCemPayloadSize   OBJECT-TYPE
    SYNTAX           Unsigned32 (0|16..2048)
    UNITS            "bytes"
    MAX-ACCESS       read-write
    STATUS           current
    DESCRIPTION      "This object specifies the payload size (in bytes) of
                      packets transmitted to the Packet Service Network (PSN)
                      by the CEM SAP.  This determines the size of the data
                      that will be transmitted over the service.  As well,
                      if the size of the data received is not consistent with
                      the payload size then the packet is considered malformed.

                      The default value depends on the CEM SAP endpoint type
                      (sapCemEndpointType), and if applicable, the number of
                      timeslots (sapCemBitrate):
                      ---------------------------------------------------------
                      | Endpoint Type      | Timeslots | Default payload size |
                      ---------------------+-----------+-----------------------
                      | 'unstructuredE1'   | n/a       |    256 bytes         |
                      ---------------------+-----------+-----------------------
                      | 'unstructuredT1'   | n/a       |    192 bytes         |
                      ---------------------+-----------+-----------------------
                      | 'unstructuredE3'   | n/a       |   1024 bytes         |
                      ---------------------+-----------+-----------------------
                      | 'unstructuredT3'   | n/a       |   1024 bytes         |
                      ---------------------+-----------+-----------------------
                      | 'nxDS0' (E1/T1)    | N = 1     |     64 bytes         |
                      |                    +-----------+-----------------------
                      |                    | N = 2..4  | N x 32 bytes         |
                      |                    +-----------+-----------------------
                      |                    | N = 5..15 | N x 16 bytes         |
                      |                    +-----------+-----------------------
                      |                    | N >= 16   | N x  8 bytes         |
                      ---------------------+-----------+-----------------------
                      | 'nxDS0WithCas' (E1)| N         | N x 16 bytes         |
                      ---------------------+-----------+-----------------------
                      | 'nxDS0WithCas' (T1)| N         | N x 24 bytes         |
                      ---------------------------------------------------------

                      For 'nxDS0WithCas', the sapCemPayloadSize cannot
                      be changed away from the default value.

                      For '1xDS0', sapCemPayloadSize must be a multiple of 2.
                      
                      For 'NxDS0', where N > 1, sapCemPayloadSize must be a
                      multiple of the number of timeslots (sapCemBitrate).

                      For 'unstructuredE1', 'unstructuredT1', 'unstructuredE3'
                      and 'unstructuredT3', sapCemPayloadSize must be a
                      multiple of 32 bytes.

                      Configuring sapCemPayloadSize and sapCemJitterBuffer to
                      values that result in less than 2 packet buffers or
                      greater than 32 packet buffers is not allowed.

                      For all endpoint types except for 'nxDS0WithCas', the
                      minimum payload size is given below:
                      ---------------------------------------------------------
                      | Endpoint Type      | Timeslots | Minimum payload size |
                      ---------------------+-----------+-----------------------
                      | 'unstructuredE1'   | n/a       |    256 bytes         |
                      ---------------------+-----------+-----------------------
                      | 'unstructuredT1'   | n/a       |    192 bytes         |
                      ---------------------+-----------+-----------------------
                      | 'unstructuredE3'   | n/a       |   1024 bytes         |
                      ---------------------+-----------+-----------------------
                      | 'unstructuredT3'   | n/a       |   1024 bytes         |
                      ---------------------+-----------+-----------------------
                      | 'nxDS0' (E1)       | N = 1..4  | N x 16 bytes         |
                      ---------------------+-----------+-----------------------
                      | 'nxDS0' (T1)       | N = 1..4  | N x 24 bytes         |
                      ---------------------+-----------+-----------------------
                      | 'nxDS0' (E1/T1)    | N = 5..15 | N x 16 bytes         |
                      |                    +-----------+-----------------------
                      |                    | N >= 16   | N x  8 bytes         |
                      ---------------------+-----------+-----------------------
                      
                      For all endpoints types except for 'nxDS0WithCas', the
                      maximum payload size is 2048 bytes.

                      Setting this object to 0 sets it back to the default
                      value."
    ::= { sapCemInfoEntry 5 }

sapCemJitterBuffer   OBJECT-TYPE
    SYNTAX           Unsigned32 (0|1..250)
    UNITS            "milliseconds"
    MAX-ACCESS       read-write
    STATUS           current
    DESCRIPTION      "This object specifies the jitter buffer size in
                      milliseconds (ms).
                      
                      Default value depends on the CEM SAP endpoint type
                      (sapCemEndpointType), and if applicable, the number of
                      timeslots (sapCemBitrate):
                      ---------------------------------------------------------
                      | Endpoint Type      | Timeslots | Default jitter buf.  |
                      ---------------------+-----------+-----------------------
                      | 'unstructuredE1'   | n/a       |    5 ms              |
                      ---------------------+-----------+-----------------------
                      | 'unstructuredT1'   | n/a       |    5 ms              |
                      ---------------------+-----------+-----------------------
                      | 'unstructuredE3'   | n/a       |    5 ms              |
                      ---------------------+-----------+-----------------------
                      | 'unstructuredT3'   | n/a       |    5 ms              |
                      ---------------------+-----------+-----------------------
                      | 'nxDS0' (E1/T1)    | N = 1     |   32 ms              |
                      |                    +-----------+-----------------------
                      |                    | N = 2..4  |   16 ms              |
                      |                    +-----------+-----------------------
                      |                    | N = 5..15 |    8 ms              |
                      |                    +-----------+-----------------------
                      |                    | N >= 16   |    5 ms              |
                      ---------------------+-----------+-----------------------
                      | 'nxDS0WithCas' (E1)| N         |    8 ms              |
                      ---------------------+-----------+-----------------------
                      | 'nxDS0WithCas' (T1)| N         |   12 ms              |
                      ---------------------------------------------------------
                      
                      Configuring sapCemPayloadSize and sapCemJitterBuffer to
                      values that result in less than 2 packet buffers or
                      greater than 32 packet buffers is not allowed.

                      The valid range is 1 to 250 ms.  Setting this object
                      to 0 sets it back to the default value."
    ::= { sapCemInfoEntry 6 }
    
sapCemUseRtpHeader  OBJECT-TYPE
    SYNTAX          TruthValue
    MAX-ACCESS      read-write
    STATUS          current
    DESCRIPTION     "This object specifies whether a RTP header is used when
                     packets are transmitted to the Packet Service Network
                     (PSN) by the CEM SAP."
    DEFVAL          { false }
    ::= { sapCemInfoEntry 7 }

sapCemDifferential  OBJECT-TYPE
    SYNTAX          TruthValue
    MAX-ACCESS      read-only
    STATUS          current
    DESCRIPTION     "This object specifies whether this CEM SAP is in
                     differential mode."
    ::= { sapCemInfoEntry 8 }

sapCemTimestampFreq OBJECT-TYPE
    SYNTAX          Unsigned32
    UNITS           "8 KHz"
    MAX-ACCESS      read-only
    STATUS          current
    DESCRIPTION     "This object specifies the value of the differential 
                     timestamp frequency in multiples of 8 KHz for this CEM 
                     SAP."
    REFERENCE
                    "RFC 5287, section 3.8 'TDM Options'."
    ::= { sapCemInfoEntry 9 }

sapCemReportAlarm OBJECT-TYPE
    SYNTAX          CemSapReportAlarm
    MAX-ACCESS      read-write
    STATUS          current
    DESCRIPTION
                    "The value of sapCemReportAlarm determines when and if to
                    generate notifications for the CEM SAP."
    DEFVAL      { {strayPkts, malformedPkts, pktLoss, bfrOverrun, bfrUnderrun} }
    ::= { sapCemInfoEntry 10 }

sapCemReportAlarmStatus  OBJECT-TYPE
    SYNTAX          CemSapReportAlarm
    MAX-ACCESS      read-only
    STATUS          current
    DESCRIPTION
                    "The value of sapCemReportAlarmStatus indicates the current
                     alarms on this CEM SAP."
    ::= { sapCemInfoEntry 11 }

sapCemLocalEcid OBJECT-TYPE
    SYNTAX          CemSapEcid
    MAX-ACCESS      read-write
    STATUS          current
    DESCRIPTION     "The value of the object sapCemLocalEcid specifies
                     the local ECID.  
                     
                     Only valid if CEM SAP belongs to an EPIPE service."
    DEFVAL { 0 }
    ::= { sapCemInfoEntry 12 }
    
sapCemRemoteMacAddr OBJECT-TYPE
    SYNTAX          MacAddress
    MAX-ACCESS      read-write
    STATUS          current
    DESCRIPTION     "The value of the object sapCemRemoteMacAddr specifies
                     the remote MAC address.  
                     
                     Only valid if CEM SAP belongs to an EPIPE service."
    DEFVAL { '000000000000'h }
    ::= { sapCemInfoEntry 13 }

sapCemRemoteEcid OBJECT-TYPE
    SYNTAX          CemSapEcid
    MAX-ACCESS      read-write
    STATUS          current
    DESCRIPTION     "The value of the object sapCemRemoteEcid specifies
                     the remote ECID.  
                     
                     Only valid if CEM SAP belongs to an EPIPE service."
    DEFVAL { 0 }
    ::= { sapCemInfoEntry 14 }

sapCemJitterBufPackets OBJECT-TYPE
    SYNTAX           Unsigned32
    UNITS            "packets"
    MAX-ACCESS       read-only
    STATUS           current
    DESCRIPTION      "This value indicates the jitter buffer length in
                      number of packet buffers."
    ::= { sapCemInfoEntry 15 }

sapCemPlayoutBufPacketsThreshold OBJECT-TYPE
    SYNTAX           Unsigned32
    UNITS            "packets"
    MAX-ACCESS       read-only
    STATUS           current
    DESCRIPTION      "This value indicates the playout buffer packets threshold
                      in number of packet buffers."
    ::= { sapCemInfoEntry 16 }

-- ---------------------------------------------------------------------
-- CEM SAP Statistics Table
--
--
--  Sparse Dependent Extention of the sapBaseInfoTable.
--
--  The same indexes are used for both the base table, sapBaseInfoTable,
--  and the sparse dependent table, sapCemStatsTable.
--
--  This in effect extends the sapBaseInfoTable with additional columns.
--  Rows are created in the sapCemStatsTable only for those entries
--  in the sapBaseInfoTable that are created on a port that 'cemEncap' set
--  for port encapsulation.
--
--  Deletion of a row in the sapBaseInfoTable results in the
--  same fate for the row in the sapCemStatsTable.
-- ---------------------------------------------------------------------
sapCemStatsTable OBJECT-TYPE
    SYNTAX          SEQUENCE OF SapCemStatsEntry
    MAX-ACCESS      not-accessible
    STATUS          current
    DESCRIPTION     "A table that contains CEM SAP statistics."
    ::= { tmnxSapObjs 41 }

sapCemStatsEntry OBJECT-TYPE
    SYNTAX          SapCemStatsEntry
    MAX-ACCESS      not-accessible
    STATUS          current
    DESCRIPTION     "Statistics for a specific CEM SAP."
    INDEX           { svcId, sapPortId, sapEncapValue }
    ::= { sapCemStatsTable 1 }

SapCemStatsEntry ::=
    SEQUENCE {
        sapCemStatsIngressForwardedPkts   Counter32,
        sapCemStatsIngressDroppedPkts     Counter32,
        sapCemStatsEgressForwardedPkts    Counter32,
        sapCemStatsEgressDroppedPkts      Counter32,
        sapCemStatsEgressMissingPkts      Counter32,
        sapCemStatsEgressPktsReOrder      Counter32,
        sapCemStatsEgressJtrBfrUnderruns  Counter32,
        sapCemStatsEgressJtrBfrOverruns   Counter32,
        sapCemStatsEgressMisOrderDropped  Counter32,
        sapCemStatsEgressMalformedPkts    Counter32,
        sapCemStatsEgressLBitDropped      Counter32,
        sapCemStatsEgressMultipleDropped  Counter32,
        sapCemStatsEgressESs              Counter32,
        sapCemStatsEgressSESs             Counter32,
        sapCemStatsEgressUASs             Counter32,
        sapCemStatsEgressFailureCounts    Counter32,
        sapCemStatsEgressUnderrunCounts   Counter32,
        sapCemStatsEgressOverrunCounts    Counter32,
        sapCemStatsEgressJtrBfrDepth      Gauge32
    }

sapCemStatsIngressForwardedPkts OBJECT-TYPE
    SYNTAX          Counter32
    MAX-ACCESS      read-only
    STATUS          current
    DESCRIPTION     "The value of sapCemStatsIngressForwardedPkts indicates
                     the number of packets that were successfully forwarded."
    ::= { sapCemStatsEntry 1 }

sapCemStatsIngressDroppedPkts OBJECT-TYPE
    SYNTAX          Counter32
    MAX-ACCESS      read-only
    STATUS          current
    DESCRIPTION     "The value of sapCemStatsIngressDroppedPkts indicates
                     the total number of packets that were dropped due to
                     errors."
    ::= { sapCemStatsEntry 2 }

sapCemStatsEgressForwardedPkts OBJECT-TYPE
    SYNTAX          Counter32
    MAX-ACCESS      read-only
    STATUS          current
    DESCRIPTION     "The value of sapCemStatsEgressForwardedPkts indicates the
                     number of packets that were successfully forwarded."
    ::= { sapCemStatsEntry 3 }

sapCemStatsEgressDroppedPkts OBJECT-TYPE
    SYNTAX          Counter32
    MAX-ACCESS      read-only
    STATUS          current
    DESCRIPTION     "The value of sapCemStatsEgressDroppedPkts indicates
                     the total number of packets that were dropped due to
                     errors."
    ::= { sapCemStatsEntry 4 }

sapCemStatsEgressMissingPkts   OBJECT-TYPE
    SYNTAX          Counter32
    MAX-ACCESS      read-only
    STATUS          current
    DESCRIPTION     "The value of sapCemStatsEgressMissingPkts indicates the
                     number of missing packets (as detected via control word
                     sequence number gaps)."
    ::= { sapCemStatsEntry 5 }

sapCemStatsEgressPktsReOrder   OBJECT-TYPE
    SYNTAX          Counter32
    MAX-ACCESS      read-only
    STATUS          current
    DESCRIPTION     "The value of sapCemStatsEgressPktsReOrder indicates the
                     number of packets detected out of sequence (via control
                     word sequence number), but successfully re-ordered."
    ::= { sapCemStatsEntry 6 }

sapCemStatsEgressJtrBfrUnderruns  OBJECT-TYPE
    SYNTAX          Counter32
    MAX-ACCESS      read-only
    STATUS          current
    DESCRIPTION     "The value of sapCemStatsEgressJtrBfrUnderruns indicates
                     the number of times a packet needed to be played out and
                     the jitter buffer was empty."
    ::= { sapCemStatsEntry 7 }

sapCemStatsEgressJtrBfrOverruns  OBJECT-TYPE
    SYNTAX          Counter32
    MAX-ACCESS      read-only
    STATUS          current
    DESCRIPTION     "The value of sapCemStatsEgressJtrBfrOverruns indicates
                     the number of times a packet was dropped because it could
                     not fit in the jitter buffer."
    ::= { sapCemStatsEntry 8 }

sapCemStatsEgressMisOrderDropped  OBJECT-TYPE
    SYNTAX          Counter32
    MAX-ACCESS      read-only
    STATUS          current
    DESCRIPTION     "The value of sapCemStatsEgressMisOrderDropped indicates
                     the number of packets detected out of order (via control
                     word sequence numbers), and could not be re-ordered, or
                     could not be placed in the jitter buffer because it was
                     out of the current window."
    ::= { sapCemStatsEntry 9 }

sapCemStatsEgressMalformedPkts  OBJECT-TYPE
    SYNTAX          Counter32
    MAX-ACCESS      read-only
    STATUS          current
    DESCRIPTION     "The value of sapCemStatsEgressMalformedPkts indicates the
                     number of packets detected with unexpected size, or bad
                     headers' stack."
    ::= { sapCemStatsEntry 10 }

sapCemStatsEgressLBitDropped  OBJECT-TYPE
    SYNTAX          Counter32
    MAX-ACCESS      read-only
    STATUS          current
    DESCRIPTION     "The value of sapCemStatsEgressLBitDropped indicates the
                     number of packets dropped due to the L bit set by the far
                     end."
    ::= { sapCemStatsEntry 11 }

sapCemStatsEgressMultipleDropped  OBJECT-TYPE
    SYNTAX          Counter32
    MAX-ACCESS      read-only
    STATUS          current
    DESCRIPTION     "The value of sapCemStatsEgressMultipleDropped indicates
                     the number of packets dropped due to multiple sequence
                     numbers."
    ::= { sapCemStatsEntry 12 }
                     
sapCemStatsEgressESs  OBJECT-TYPE
    SYNTAX          Counter32
    MAX-ACCESS      read-only
    STATUS          current
    DESCRIPTION     "The value of sapCemStatsEgressESs indicates the number of
                     Error Seconds (ESs) encountered. Any malformed packet,
                     seq.  error, LOPS and similar are considered as error
                     seconds."
    ::= { sapCemStatsEntry 13 }

sapCemStatsEgressSESs  OBJECT-TYPE
    SYNTAX          Counter32
    MAX-ACCESS      read-only
    STATUS          current
    DESCRIPTION     "The value of sapCemStatsEgressSESs indicates the number
                     of Severely Error Seconds (SESs) encountered.  This is
                     when more than 30 percent of the packets within a one
                     second window are missing."
    ::= { sapCemStatsEntry 14 }

sapCemStatsEgressUASs  OBJECT-TYPE
    SYNTAX          Counter32
    MAX-ACCESS      read-only
    STATUS          current
    DESCRIPTION     "The value of sapCemStatsEgressUASs indicates the number of
                     Unavailable Seconds (UASs) encountered. Any consecutive
                     ten seconds of SESs are counted as one UAS."
    ::= { sapCemStatsEntry 15 }

sapCemStatsEgressFailureCounts  OBJECT-TYPE
    SYNTAX          Counter32
    MAX-ACCESS      read-only
    STATUS          current
    DESCRIPTION     "The value of sapCemStatsEgressFailureCounts indicates
                     the number failure events.  A failure event begins when
                     the LOPS failure is declared, and ends when the failure
                     is cleared."
    ::= { sapCemStatsEntry 16 }

sapCemStatsEgressUnderrunCounts  OBJECT-TYPE
    SYNTAX          Counter32
    MAX-ACCESS      read-only
    STATUS          current
    DESCRIPTION     "The value of sapCemStatsEgressUnderrunCounts indicates
                     the number of times the jitter buffer went into an
                     underrun state."
    ::= { sapCemStatsEntry 17 }

sapCemStatsEgressOverrunCounts  OBJECT-TYPE
    SYNTAX          Counter32
    MAX-ACCESS      read-only
    STATUS          current
    DESCRIPTION     "The value of sapCemStatsEgressOverrunCounts indicates
                     the number of times the jitter buffer went into an
                     overrun state."
    ::= { sapCemStatsEntry 18 }

sapCemStatsEgressJtrBfrDepth  OBJECT-TYPE
    SYNTAX          Gauge32
    MAX-ACCESS      read-only
    STATUS          current
    DESCRIPTION     "The value of sapCemStatsEgressJtrBfrDepth indicates
                     the current packet depth of the jitter buffer."
    ::= { sapCemStatsEntry 19 }
    
-- ------------------------------------------------------------
-- SAP TLS L2PT Statistics Table
-- ------------------------------------------------------------
sapTlsL2ptStatsTable OBJECT-TYPE
    SYNTAX          SEQUENCE OF SapTlsL2ptStatsEntry
    MAX-ACCESS      not-accessible
    STATUS          current
    DESCRIPTION     "A table that contains SAP Layer 2 Protocol Tunneling 
                     Statistics.
                     This table complements sapTlsInfoTable. Rows in this
                     table are created and deleted automatically by the
                     system."
    ::= { tmnxSapObjs 42 }

sapTlsL2ptStatsEntry OBJECT-TYPE
    SYNTAX          SapTlsL2ptStatsEntry
    MAX-ACCESS      not-accessible
    STATUS          current
    DESCRIPTION     "Layer 2 Protocol Tunneling Statistics for a specific SAP.
                     The statistics are provided for each combination of 
                     Destination Address and LLC SNAP type."
    INDEX           { svcId, sapPortId, sapEncapValue }
    ::= { sapTlsL2ptStatsTable 1 }

SapTlsL2ptStatsEntry ::=
    SEQUENCE {
        sapTlsL2ptStatsLastClearedTime              TimeStamp,
        sapTlsL2ptStatsL2ptEncapStpConfigBpdusRx    Counter32,
        sapTlsL2ptStatsL2ptEncapStpConfigBpdusTx    Counter32,
        sapTlsL2ptStatsL2ptEncapStpRstBpdusRx       Counter32,
        sapTlsL2ptStatsL2ptEncapStpRstBpdusTx       Counter32,
        sapTlsL2ptStatsL2ptEncapStpTcnBpdusRx       Counter32,
        sapTlsL2ptStatsL2ptEncapStpTcnBpdusTx       Counter32,
        sapTlsL2ptStatsL2ptEncapPvstConfigBpdusRx   Counter32,
        sapTlsL2ptStatsL2ptEncapPvstConfigBpdusTx   Counter32,
        sapTlsL2ptStatsL2ptEncapPvstRstBpdusRx      Counter32,
        sapTlsL2ptStatsL2ptEncapPvstRstBpdusTx      Counter32,
        sapTlsL2ptStatsL2ptEncapPvstTcnBpdusRx      Counter32,
        sapTlsL2ptStatsL2ptEncapPvstTcnBpdusTx      Counter32,
        sapTlsL2ptStatsStpConfigBpdusRx             Counter32,
        sapTlsL2ptStatsStpConfigBpdusTx             Counter32,
        sapTlsL2ptStatsStpRstBpdusRx                Counter32,
        sapTlsL2ptStatsStpRstBpdusTx                Counter32,
        sapTlsL2ptStatsStpTcnBpdusRx                Counter32,
        sapTlsL2ptStatsStpTcnBpdusTx                Counter32,
        sapTlsL2ptStatsPvstConfigBpdusRx            Counter32,
        sapTlsL2ptStatsPvstConfigBpdusTx            Counter32,
        sapTlsL2ptStatsPvstRstBpdusRx               Counter32,
        sapTlsL2ptStatsPvstRstBpdusTx               Counter32,
        sapTlsL2ptStatsPvstTcnBpdusRx               Counter32,
        sapTlsL2ptStatsPvstTcnBpdusTx               Counter32,
        sapTlsL2ptStatsOtherBpdusRx                 Counter32,
        sapTlsL2ptStatsOtherBpdusTx                 Counter32,
        sapTlsL2ptStatsOtherL2ptBpdusRx             Counter32,
        sapTlsL2ptStatsOtherL2ptBpdusTx             Counter32,
        sapTlsL2ptStatsOtherInvalidBpdusRx          Counter32,
        sapTlsL2ptStatsOtherInvalidBpdusTx          Counter32,
        sapTlsL2ptStatsL2ptEncapCdpBpdusRx          Counter32,
        sapTlsL2ptStatsL2ptEncapCdpBpdusTx          Counter32,
        sapTlsL2ptStatsL2ptEncapVtpBpdusRx          Counter32,
        sapTlsL2ptStatsL2ptEncapVtpBpdusTx          Counter32,
        sapTlsL2ptStatsL2ptEncapDtpBpdusRx          Counter32,
        sapTlsL2ptStatsL2ptEncapDtpBpdusTx          Counter32,
        sapTlsL2ptStatsL2ptEncapPagpBpdusRx         Counter32,
        sapTlsL2ptStatsL2ptEncapPagpBpdusTx         Counter32,
        sapTlsL2ptStatsL2ptEncapUdldBpdusRx         Counter32,
        sapTlsL2ptStatsL2ptEncapUdldBpdusTx         Counter32,
        sapTlsL2ptStatsCdpBpdusRx                   Counter32,
        sapTlsL2ptStatsCdpBpdusTx                   Counter32,
        sapTlsL2ptStatsVtpBpdusRx                   Counter32,
        sapTlsL2ptStatsVtpBpdusTx                   Counter32,
        sapTlsL2ptStatsDtpBpdusRx                   Counter32,
        sapTlsL2ptStatsDtpBpdusTx                   Counter32,
        sapTlsL2ptStatsPagpBpdusRx                  Counter32,
        sapTlsL2ptStatsPagpBpdusTx                  Counter32,
        sapTlsL2ptStatsUdldBpdusRx                  Counter32,
        sapTlsL2ptStatsUdldBpdusTx                  Counter32
    }

sapTlsL2ptStatsLastClearedTime OBJECT-TYPE
    SYNTAX          TimeStamp
    MAX-ACCESS      read-only
    STATUS          current
    DESCRIPTION     "The value of sapTlsL2ptStatsLastClearedTime indicates 
                     the last time that these stats were cleared. The value
                     zero indicates that they have not been cleared yet."
    ::= { sapTlsL2ptStatsEntry 1 }                                                                                                                                                  

sapTlsL2ptStatsL2ptEncapStpConfigBpdusRx OBJECT-TYPE
    SYNTAX          Counter32
    MAX-ACCESS      read-only
    STATUS          current
    DESCRIPTION     "The value of sapTlsL2ptStatsL2ptEncapStpConfigBpdusRx indicates the
                     number of L2PT encapsulated STP config bpdus received on this SAP."
    ::= { sapTlsL2ptStatsEntry 2 }

sapTlsL2ptStatsL2ptEncapStpConfigBpdusTx OBJECT-TYPE
    SYNTAX          Counter32
    MAX-ACCESS      read-only
    STATUS          current
    DESCRIPTION     "The value of sapTlsL2ptStatsL2ptEncapStpConfigBpdusTx indicates the
                     number of L2PT encapsulated STP config bpdus transmitted on this SAP."
    ::= { sapTlsL2ptStatsEntry 3 }

sapTlsL2ptStatsL2ptEncapStpRstBpdusRx OBJECT-TYPE
    SYNTAX          Counter32
    MAX-ACCESS      read-only
    STATUS          current
    DESCRIPTION     "The value of sapTlsL2ptStatsL2ptEncapStpRstBpdusRx indicates the
                     number of L2PT encapsulated STP rst bpdus received on this SAP."
    ::= { sapTlsL2ptStatsEntry 4 }

sapTlsL2ptStatsL2ptEncapStpRstBpdusTx OBJECT-TYPE
    SYNTAX          Counter32
    MAX-ACCESS      read-only
    STATUS          current
    DESCRIPTION     "The value of sapTlsL2ptStatsL2ptEncapStpRstBpdusTx indicates the
                     number of L2PT encapsulated STP rst bpdus transmitted on this SAP."
    ::= { sapTlsL2ptStatsEntry 5 }

sapTlsL2ptStatsL2ptEncapStpTcnBpdusRx OBJECT-TYPE
    SYNTAX          Counter32
    MAX-ACCESS      read-only
    STATUS          current
    DESCRIPTION     "The value of sapTlsL2ptStatsL2ptEncapStpTcnBpdusRx indicates the
                     number of L2PT encapsulated STP tcn bpdus received on this SAP."
    ::= { sapTlsL2ptStatsEntry 6 }

sapTlsL2ptStatsL2ptEncapStpTcnBpdusTx OBJECT-TYPE
    SYNTAX          Counter32
    MAX-ACCESS      read-only
    STATUS          current
    DESCRIPTION     "The value of sapTlsL2ptStatsL2ptEncapStpTcnBpdusTx indicates the
                     number of L2PT encapsulated STP tcn bpdus transmitted on this SAP."
    ::= { sapTlsL2ptStatsEntry 7 }

sapTlsL2ptStatsL2ptEncapPvstConfigBpdusRx OBJECT-TYPE
    SYNTAX          Counter32
    MAX-ACCESS      read-only
    STATUS          current
    DESCRIPTION     "The value of sapTlsL2ptStatsL2ptEncapPvstConfigBpdusRx indicates the
                     number of L2PT encapsulated PVST config bpdus received on this SAP."
    ::= { sapTlsL2ptStatsEntry 8 }

sapTlsL2ptStatsL2ptEncapPvstConfigBpdusTx OBJECT-TYPE
    SYNTAX          Counter32
    MAX-ACCESS      read-only
    STATUS          current
    DESCRIPTION     "The value of sapTlsL2ptStatsL2ptEncapPvstConfigBpdusTx indicates the
                     number of L2PT encapsulated PVST config bpdus transmitted on this SAP."
    ::= { sapTlsL2ptStatsEntry 9 }

sapTlsL2ptStatsL2ptEncapPvstRstBpdusRx OBJECT-TYPE
    SYNTAX          Counter32
    MAX-ACCESS      read-only
    STATUS          current
    DESCRIPTION     "The value of sapTlsL2ptStatsL2ptEncapPvstRstBpdusRx indicates the
                     number of L2PT encapsulated PVST rst bpdus received on this SAP."
    ::= { sapTlsL2ptStatsEntry 10 }

sapTlsL2ptStatsL2ptEncapPvstRstBpdusTx OBJECT-TYPE
    SYNTAX          Counter32
    MAX-ACCESS      read-only
    STATUS          current
    DESCRIPTION     "The value of sapTlsL2ptStatsL2ptEncapPvstRstBpdusTx indicates the
                     number of L2PT encapsulated PVST rst bpdus transmitted on this SAP."
    ::= { sapTlsL2ptStatsEntry 11 }

sapTlsL2ptStatsL2ptEncapPvstTcnBpdusRx OBJECT-TYPE
    SYNTAX          Counter32
    MAX-ACCESS      read-only
    STATUS          current
    DESCRIPTION     "The value of sapTlsL2ptStatsL2ptEncapPvstTcnBpdusRx indicates the
                     number of L2PT encapsulated PVST tcn bpdus received on this SAP."
    ::= { sapTlsL2ptStatsEntry 12 }

sapTlsL2ptStatsL2ptEncapPvstTcnBpdusTx OBJECT-TYPE
    SYNTAX          Counter32
    MAX-ACCESS      read-only
    STATUS          current
    DESCRIPTION     "The value of sapTlsL2ptStatsL2ptEncapPvstTcnBpdusTx indicates the
                     number of L2PT encapsulated PVST tcn bpdus transmitted on this SAP."
    ::= { sapTlsL2ptStatsEntry 13 }

sapTlsL2ptStatsStpConfigBpdusRx OBJECT-TYPE
    SYNTAX          Counter32
    MAX-ACCESS      read-only
    STATUS          current
    DESCRIPTION     "The value of sapTlsL2ptStatsStpConfigBpdusRx indicates the
                     number of STP config bpdus received on this SAP."
    ::= { sapTlsL2ptStatsEntry 14 }

sapTlsL2ptStatsStpConfigBpdusTx OBJECT-TYPE
    SYNTAX          Counter32
    MAX-ACCESS      read-only
    STATUS          current
    DESCRIPTION     "The value of sapTlsL2ptStatsStpConfigBpdusTx indicates the
                     number of STP config bpdus transmitted on this SAP."
    ::= { sapTlsL2ptStatsEntry 15 }

sapTlsL2ptStatsStpRstBpdusRx OBJECT-TYPE
    SYNTAX          Counter32
    MAX-ACCESS      read-only
    STATUS          current
    DESCRIPTION     "The value of sapTlsL2ptStatsStpRstBpdusRx indicates the
                     number of STP rst bpdus received on this SAP."
    ::= { sapTlsL2ptStatsEntry 16 }

sapTlsL2ptStatsStpRstBpdusTx OBJECT-TYPE
    SYNTAX          Counter32
    MAX-ACCESS      read-only
    STATUS          current
    DESCRIPTION     "The value of sapTlsL2ptStatsStpRstBpdusTx indicates the
                     number of STP rst bpdus transmitted on this SAP."
    ::= { sapTlsL2ptStatsEntry 17 }

sapTlsL2ptStatsStpTcnBpdusRx OBJECT-TYPE
    SYNTAX          Counter32
    MAX-ACCESS      read-only
    STATUS          current
    DESCRIPTION     "The value of sapTlsL2ptStatsStpTcnBpdusRx indicates the
                     number of STP tcn bpdus received on this SAP."
    ::= { sapTlsL2ptStatsEntry 18 }

sapTlsL2ptStatsStpTcnBpdusTx OBJECT-TYPE
    SYNTAX          Counter32
    MAX-ACCESS      read-only
    STATUS          current
    DESCRIPTION     "The value of sapTlsL2ptStatsStpTcnBpdusTx indicates the
                     number of STP tcn bpdus transmitted on this SAP."
    ::= { sapTlsL2ptStatsEntry 19 }

sapTlsL2ptStatsPvstConfigBpdusRx OBJECT-TYPE
    SYNTAX          Counter32
    MAX-ACCESS      read-only
    STATUS          current
    DESCRIPTION     "The value of sapTlsL2ptStatsPvstConfigBpdusRx indicates the
                     number of PVST config bpdus received on this SAP."
    ::= { sapTlsL2ptStatsEntry 20 }

sapTlsL2ptStatsPvstConfigBpdusTx OBJECT-TYPE
    SYNTAX          Counter32
    MAX-ACCESS      read-only
    STATUS          current
    DESCRIPTION     "The value of sapTlsL2ptStatsPvstConfigBpdusTx indicates the
                     number of PVST config bpdus transmitted on this SAP."
    ::= { sapTlsL2ptStatsEntry 21 }

sapTlsL2ptStatsPvstRstBpdusRx OBJECT-TYPE
    SYNTAX          Counter32
    MAX-ACCESS      read-only
    STATUS          current
    DESCRIPTION     "The value of sapTlsL2ptStatsPvstRstBpdusRx indicates the
                     number of PVST rst bpdus received on this SAP."
    ::= { sapTlsL2ptStatsEntry 22 }

sapTlsL2ptStatsPvstRstBpdusTx OBJECT-TYPE
    SYNTAX          Counter32
    MAX-ACCESS      read-only
    STATUS          current
    DESCRIPTION     "The value of sapTlsL2ptStatsPvstRstBpdusTx indicates the
                     number of PVST rst bpdus transmitted on this SAP."
    ::= { sapTlsL2ptStatsEntry 23 }

sapTlsL2ptStatsPvstTcnBpdusRx OBJECT-TYPE
    SYNTAX          Counter32
    MAX-ACCESS      read-only
    STATUS          current
    DESCRIPTION     "The value of sapTlsL2ptStatsPvstTcnBpdusRx indicates the
                     number of PVST tcn bpdus received on this SAP."
    ::= { sapTlsL2ptStatsEntry 24 }

sapTlsL2ptStatsPvstTcnBpdusTx OBJECT-TYPE
    SYNTAX          Counter32
    MAX-ACCESS      read-only
    STATUS          current
    DESCRIPTION     "The value of sapTlsL2ptStatsPvstTcnBpdusTx indicates the
                     number of PVST tcn bpdus transmitted on this SAP."
    ::= { sapTlsL2ptStatsEntry 25 }

sapTlsL2ptStatsOtherBpdusRx OBJECT-TYPE
    SYNTAX          Counter32
    MAX-ACCESS      read-only
    STATUS          current
    DESCRIPTION     "The value of sapTlsL2ptStatsOtherBpdusRx indicates the
                     number of other bpdus received on this SAP."
    ::= { sapTlsL2ptStatsEntry 26 }

sapTlsL2ptStatsOtherBpdusTx OBJECT-TYPE
    SYNTAX          Counter32
    MAX-ACCESS      read-only
    STATUS          current
    DESCRIPTION     "The value of sapTlsL2ptStatsOtherBpdusTx indicates the
                     number of other bpdus transmitted on this SAP."
    ::= { sapTlsL2ptStatsEntry 27 }

sapTlsL2ptStatsOtherL2ptBpdusRx OBJECT-TYPE
    SYNTAX          Counter32
    MAX-ACCESS      read-only
    STATUS          current
    DESCRIPTION     "The value of sapTlsL2ptStatsOtherL2ptBpdusRx indicates the
                     number of other L2PT bpdus received on this SAP."
    ::= { sapTlsL2ptStatsEntry 28 }

sapTlsL2ptStatsOtherL2ptBpdusTx OBJECT-TYPE
    SYNTAX          Counter32
    MAX-ACCESS      read-only
    STATUS          current
    DESCRIPTION     "The value of sapTlsL2ptStatsOtherL2ptBpdusTx indicates the
                     number of other L2PT bpdus transmitted on this SAP."
    ::= { sapTlsL2ptStatsEntry 29 }

sapTlsL2ptStatsOtherInvalidBpdusRx OBJECT-TYPE
    SYNTAX          Counter32
    MAX-ACCESS      read-only
    STATUS          current
    DESCRIPTION     "The value of sapTlsL2ptStatsOtherInvalidBpdusRx indicates the
                     number of other invalid bpdus received on this SAP."
    ::= { sapTlsL2ptStatsEntry 30 }

sapTlsL2ptStatsOtherInvalidBpdusTx OBJECT-TYPE
    SYNTAX          Counter32
    MAX-ACCESS      read-only
    STATUS          current
    DESCRIPTION     "The value of sapTlsL2ptStatsOtherInvalidBpdusTx indicates the
                     number of other invalid bpdus transmitted on this SAP."
    ::= { sapTlsL2ptStatsEntry 31 }

sapTlsL2ptStatsL2ptEncapCdpBpdusRx OBJECT-TYPE
    SYNTAX          Counter32
    MAX-ACCESS      read-only
    STATUS          current
    DESCRIPTION     "The value of sapTlsL2ptStatsL2ptEncapCdpBpdusRx indicates the
                     number of L2PT encapsulated CDP bpdus received on this SAP."
    ::= { sapTlsL2ptStatsEntry 32 }

sapTlsL2ptStatsL2ptEncapCdpBpdusTx OBJECT-TYPE
    SYNTAX          Counter32
    MAX-ACCESS      read-only
    STATUS          current
    DESCRIPTION     "The value of sapTlsL2ptStatsL2ptEncapCdpBpdusTx indicates the
                     number of L2PT encapsulated CDP bpdus transmitted on this SAP."
    ::= { sapTlsL2ptStatsEntry 33 }

sapTlsL2ptStatsL2ptEncapVtpBpdusRx OBJECT-TYPE
    SYNTAX          Counter32
    MAX-ACCESS      read-only
    STATUS          current
    DESCRIPTION     "The value of sapTlsL2ptStatsL2ptEncapVtpBpdusRx indicates the
                     number of L2PT encapsulated VTP bpdus received on this SAP."
    ::= { sapTlsL2ptStatsEntry 34 }

sapTlsL2ptStatsL2ptEncapVtpBpdusTx OBJECT-TYPE
    SYNTAX          Counter32
    MAX-ACCESS      read-only
    STATUS          current
    DESCRIPTION     "The value of sapTlsL2ptStatsL2ptEncapVtpBpdusTx indicates the
                     number of L2PT encapsulated VTP bpdus transmitted on this SAP."
    ::= { sapTlsL2ptStatsEntry 35 }

sapTlsL2ptStatsL2ptEncapDtpBpdusRx OBJECT-TYPE
    SYNTAX          Counter32
    MAX-ACCESS      read-only
    STATUS          current
    DESCRIPTION     "The value of sapTlsL2ptStatsL2ptEncapDtpBpdusRx indicates the
                     number of L2PT encapsulated DTP bpdus received on this SAP."
    ::= { sapTlsL2ptStatsEntry 36 }

sapTlsL2ptStatsL2ptEncapDtpBpdusTx OBJECT-TYPE
    SYNTAX          Counter32
    MAX-ACCESS      read-only
    STATUS          current
    DESCRIPTION     "The value of sapTlsL2ptStatsL2ptEncapDtpBpdusTx indicates the
                     number of L2PT encapsulated DTP bpdus transmitted on this SAP."
    ::= { sapTlsL2ptStatsEntry 37 }

sapTlsL2ptStatsL2ptEncapPagpBpdusRx OBJECT-TYPE
    SYNTAX          Counter32
    MAX-ACCESS      read-only
    STATUS          current
    DESCRIPTION     "The value of sapTlsL2ptStatsL2ptEncapPagpBpdusRx indicates the
                     number of L2PT encapsulated PAGP bpdus received on this SAP."
    ::= { sapTlsL2ptStatsEntry 38 }

sapTlsL2ptStatsL2ptEncapPagpBpdusTx OBJECT-TYPE
    SYNTAX          Counter32
    MAX-ACCESS      read-only
    STATUS          current
    DESCRIPTION     "The value of sapTlsL2ptStatsL2ptEncapPagpBpdusTx indicates the
                     number of L2PT encapsulated PAGP bpdus transmitted on this SAP."
    ::= { sapTlsL2ptStatsEntry 39 }


sapTlsL2ptStatsL2ptEncapUdldBpdusRx OBJECT-TYPE
    SYNTAX          Counter32
    MAX-ACCESS      read-only
    STATUS          current
    DESCRIPTION     "The value of sapTlsL2ptStatsL2ptEncapUdldBpdusRx indicates the
                     number of L2PT encapsulated UDLD bpdus received on this SAP."
    ::= { sapTlsL2ptStatsEntry 40 }

sapTlsL2ptStatsL2ptEncapUdldBpdusTx OBJECT-TYPE
    SYNTAX          Counter32
    MAX-ACCESS      read-only
    STATUS          current
    DESCRIPTION     "The value of sapTlsL2ptStatsL2ptEncapUdldBpdusTx indicates the
                     number of L2PT encapsulated UDLD bpdus transmitted on this SAP."
    ::= { sapTlsL2ptStatsEntry 41 }

sapTlsL2ptStatsCdpBpdusRx OBJECT-TYPE
    SYNTAX          Counter32
    MAX-ACCESS      read-only
    STATUS          current
    DESCRIPTION     "The value of sapTlsL2ptStatsCdpBpdusRx indicates the
                     number of CDP bpdus received on this SAP."
    ::= { sapTlsL2ptStatsEntry 42 }

sapTlsL2ptStatsCdpBpdusTx OBJECT-TYPE
    SYNTAX          Counter32
    MAX-ACCESS      read-only
    STATUS          current
    DESCRIPTION     "The value of sapTlsL2ptStatsCdpBpdusTx indicates the
                     number of CDP bpdus transmitted on this SAP."
    ::= { sapTlsL2ptStatsEntry 43 }

sapTlsL2ptStatsVtpBpdusRx OBJECT-TYPE
    SYNTAX          Counter32
    MAX-ACCESS      read-only
    STATUS          current
    DESCRIPTION     "The value of sapTlsL2ptStatsVtpBpdusRx indicates the
                     number of VTP bpdus received on this SAP."
    ::= { sapTlsL2ptStatsEntry 44 }

sapTlsL2ptStatsVtpBpdusTx OBJECT-TYPE
    SYNTAX          Counter32
    MAX-ACCESS      read-only
    STATUS          current
    DESCRIPTION     "The value of sapTlsL2ptStatsVtpBpdusTx indicates the
                     number of VTP bpdus transmitted on this SAP."
    ::= { sapTlsL2ptStatsEntry 45 }


sapTlsL2ptStatsDtpBpdusRx OBJECT-TYPE
    SYNTAX          Counter32
    MAX-ACCESS      read-only
    STATUS          current
    DESCRIPTION     "The value of sapTlsL2ptStatsDtpBpdusRx indicates the
                     number of DTP bpdus received on this SAP."
    ::= { sapTlsL2ptStatsEntry 46 }

sapTlsL2ptStatsDtpBpdusTx OBJECT-TYPE
    SYNTAX          Counter32
    MAX-ACCESS      read-only
    STATUS          current
    DESCRIPTION     "The value of sapTlsL2ptStatsDtpBpdusTx indicates the
                     number of DTP bpdus transmitted on this SAP."
    ::= { sapTlsL2ptStatsEntry 47 }

sapTlsL2ptStatsPagpBpdusRx OBJECT-TYPE
    SYNTAX          Counter32
    MAX-ACCESS      read-only
    STATUS          current
    DESCRIPTION     "The value of sapTlsL2ptStatsPagpBpdusRx indicates the
                     number of PAGP bpdus received on this SAP."
    ::= { sapTlsL2ptStatsEntry 48 }

sapTlsL2ptStatsPagpBpdusTx OBJECT-TYPE
    SYNTAX          Counter32
    MAX-ACCESS      read-only
    STATUS          current
    DESCRIPTION     "The value of sapTlsL2ptStatsPagpBpdusTx indicates the
                     number of PAGP bpdus transmitted on this SAP."
    ::= { sapTlsL2ptStatsEntry 49 }


sapTlsL2ptStatsUdldBpdusRx OBJECT-TYPE
    SYNTAX          Counter32
    MAX-ACCESS      read-only
    STATUS          current
    DESCRIPTION     "The value of sapTlsL2ptStatsUdldBpdusRx indicates the
                     number of UDLD bpdus received on this SAP."
    ::= { sapTlsL2ptStatsEntry 50 }

sapTlsL2ptStatsUdldBpdusTx OBJECT-TYPE
    SYNTAX          Counter32
    MAX-ACCESS      read-only
    STATUS          current
    DESCRIPTION     "The value of sapTlsL2ptStatsUdldBpdusTx indicates the
                     number of UDLD bpdus transmitted on this SAP."
    ::= { sapTlsL2ptStatsEntry 51 }


-- ---------------------------------------------------------------------
-- Ethernet SAP Table
--
--
--  Sparse Dependent Extension of the sapBaseInfoTable.
--
--  The same indexes are used for both the base table, sapBaseInfoTable,
--  and the sparse dependent table, sapEthernetInfoTable.
--
--  This in effect extends the sapBaseInfoTable with additional columns.
--  Rows are created in the sapEthernetInfoTable only for those entries
--  in the sapBaseInfoTable that are created on a port with a 
--  tmnxPortEncapType of 'EthernetEncap.'
--
--  Deletion of a row in the sapBaseInfoTable results in the
--  same fate for the row in the sapEthernetInfoTable.
-- ---------------------------------------------------------------------
sapEthernetInfoTable OBJECT-TYPE
    SYNTAX          SEQUENCE OF SapEthernetInfoEntry
    MAX-ACCESS      not-accessible
    STATUS          current
    DESCRIPTION     "A table that contains Ethernet SAP information."
    ::= { tmnxSapObjs 43 }

sapEthernetInfoEntry OBJECT-TYPE
    SYNTAX          SapEthernetInfoEntry
    MAX-ACCESS      not-accessible
    STATUS          current
    DESCRIPTION     "Information about a specific Ethernet SAP."
    INDEX           { svcId, sapPortId, sapEncapValue }
    ::= { sapEthernetInfoTable 1 }

SapEthernetInfoEntry ::=
    SEQUENCE {
        sapEthernetLLFAdminStatus     ServiceAdminStatus,
        sapEthernetLLFOperStatus      INTEGER
    }

sapEthernetLLFAdminStatus OBJECT-TYPE
    SYNTAX          ServiceAdminStatus
    MAX-ACCESS      read-create
    STATUS          current
    DESCRIPTION     "sapEthernetLLFAdminStatus specifies whether or not Link-
                    Loss Forwarding is enabled ('up'). When this object is set
                    to 'up' the underlying port will be forced into the
                    operationally 'down' state if the service is operationally
                    'down', or any of the 'sdpBindPwPeerStatusBits' are set,
                    and will set the underlying port's
                    tmnxPortEtherReasonDownFlags 'linklossFwd' bit. Setting
                    this object to 'down' will clear the 'linklossFwd' reason.
                    sapEthernetLLFAdminStatus can only be enabled on saps 
                    configured for an EPIPE service using an Ethernet 
                    port with the tmnxPortEncapType set to 'nullEncap.'"
    DEFVAL          { down }
    ::= { sapEthernetInfoEntry 1 }

sapEthernetLLFOperStatus OBJECT-TYPE
    SYNTAX          INTEGER {
                        fault (1),   -- service is down or fault detected.
                        clear (2)    -- service is up and no fault detected.
                    }
    MAX-ACCESS      read-only
    STATUS          current
    DESCRIPTION     "sapEthernetLLFOperStatus indicates whether or not the
                    underlying port is forced operationally 'down' due to the
                    service being operationally 'down' or an
                    sdpBindPwPeerStatusBits bit is set. 
                    sapEthernetLLFOperStatus is set to 'fault' when the 
                    sapEthernetLLFAdminStatus is set to 'up,' and either a 
                    fault has occurred on the pseudo-wire, or the service is 
                    down, otherwise sapEthernetLLFOperStatus is set to 'clear.'"
    ::= { sapEthernetInfoEntry 2 }

-- --------------------------------------------------------
-- msapPlcyTable
-- --------------------------------------------------------
msapPlcyTable OBJECT-TYPE
    SYNTAX      SEQUENCE OF MsapPlcyEntry
    MAX-ACCESS  not-accessible
    STATUS      current
    DESCRIPTION
        "The msapPlcyTable has an entry for each managed SAP(MSAP) policy
         configured in the system."
    ::= { tmnxSapObjs 44 }

msapPlcyEntry    OBJECT-TYPE
    SYNTAX      MsapPlcyEntry
    MAX-ACCESS  not-accessible
    STATUS      current
    DESCRIPTION
        "Each entry represents the configuration for a managed SAP(MSAP) policy.

         The values for each entry will be used to populate the following
         tables when the MSAP policy is applied to a MSAP:
 
         TIMETRA-SAP-MIB::sapBaseInfoTable
         TIMETRA-SAP-MIB::sapSubMgmtInfoTable
        "
    INDEX { msapPlcyName }
    ::= { msapPlcyTable 1}

MsapPlcyEntry ::= SEQUENCE
    {
        msapPlcyName                     TNamedItem,
        msapPlcyRowStatus                RowStatus,
        msapPlcyLastChanged              TimeStamp,
        msapPlcyDescription              TItemDescription,
        msapPlcyCpmProtPolicyId          TCpmProtPolicyID,
        msapPlcyCpmProtMonitorMac        TruthValue,
        msapPlcySubMgmtDefSubId          TmnxDefSubIdSource,
        msapPlcySubMgmtDefSubIdStr       TNamedItemOrEmpty,
        msapPlcySubMgmtDefSubProfile     TNamedItemOrEmpty,
        msapPlcySubMgmtDefSlaProfile     TNamedItemOrEmpty,
        msapPlcySubMgmtDefAppProfile     TNamedItemOrEmpty,
        msapPlcySubMgmtSubIdPlcy         TPolicyStatementNameOrEmpty,
        msapPlcySubMgmtSubscriberLimit   TmnxSapSubscriberLimit,
        msapPlcySubMgmtProfiledTrafOnly  TruthValue,
        msapPlcySubMgmtNonSubTrafSubId   TNamedItemOrEmpty,
        msapPlcySubMgmtNonSubTrafSubProf TNamedItemOrEmpty,
        msapPlcySubMgmtNonSubTrafSlaProf TNamedItemOrEmpty,
        msapPlcySubMgmtNonSubTrafAppProf TNamedItemOrEmpty,
        msapPlcyAssociatedMsaps          Counter32,
        msapPlcySubMgmtDefInterDestId    TmnxDefInterDestIdSource,
        msapPlcySubMgmtDefInterDestIdStr TNamedItemOrEmpty,
        msapPlcyIgmpTrkExpiryTime        Unsigned32,
        msapPlcyIgmpTrkImportPlcy        TPolicyStatementNameOrEmpty,
        msapPlcyIgmpTrkMaxNbrGrps        Unsigned32,
        msapPlcyIgmpTrkMaxNbrSrcs        Unsigned32,
        msapPlcySubMgmtDefFilterProfile  TNamedItemOrEmpty,
        msapPlcyLagLinkMapProfile        TmnxLinkMapProfileIdOrZero,
        msapPlcyIgmpTrkMaxNbrGrpSrcs     Unsigned32,
        msapPlcyDCpuProtPolicy           TNamedItemOrEmpty,
        msapPlcyCpmProtMonitorIP         TruthValue
    }

msapPlcyName        OBJECT-TYPE
    SYNTAX      TNamedItem
    MAX-ACCESS  not-accessible
    STATUS      current
    DESCRIPTION
        "The value of msapPlcyName specifies the name of the MSAP policy."
    ::= { msapPlcyEntry 1 }

msapPlcyRowStatus        OBJECT-TYPE
    SYNTAX      RowStatus
    MAX-ACCESS  read-create
    STATUS      current
    DESCRIPTION
        "The value of msapPlcyRowStatus is used for the creation
         and deletion of MSAP policies."
    ::= { msapPlcyEntry 2 }

msapPlcyLastChanged        OBJECT-TYPE
    SYNTAX      TimeStamp
    MAX-ACCESS  read-only
    STATUS      current
    DESCRIPTION
        "The value of msapPlcyLastChanged indicates the sysUpTime
         at the time of the last modification of this entry.

         If no changes were made to the entry since the last
         re-initialization of the local network management subsystem,
         then this object contains a zero value."
    ::= { msapPlcyEntry 3 }

msapPlcyDescription        OBJECT-TYPE
    SYNTAX      TItemDescription
    MAX-ACCESS  read-create
    STATUS      current
    DESCRIPTION
        "The value of msapPlcyDescription specifies the description
         of the MSAP policy."
    DEFVAL { "" }
    ::= { msapPlcyEntry 4 }

msapPlcyCpmProtPolicyId  OBJECT-TYPE
    SYNTAX          TCpmProtPolicyID
    MAX-ACCESS      read-create
    STATUS          current
    DESCRIPTION
        "The value of msapPlcyCpmProtPolicyId specifies a CPM Protection
         policy for the MSAP policy.
         
         If a corresponding policy is not defined in 
         TIMETRA-SECURITY-MIB::tmnxCpmProtPolTable, an 'inconsistentValue'
         error will be returned.

         A value of 254 specifies that the default CPM Protection
         policy is associated with the Managed SAP.

         This object is not supported on 7710, where the value of
         TIMETRA-CHASSIS-MIB::tmnxChassisType is '7' or '9'.

         An attempt  to set msapPlcyCpmProtPolicyId to a non-zero 
         value on one of these unsupported chassis types will return
         an 'inconsistentValue' error."
    DEFVAL { 254 }
    ::= { msapPlcyEntry 5 }

msapPlcyCpmProtMonitorMac OBJECT-TYPE
    SYNTAX          TruthValue
    MAX-ACCESS      read-create
    STATUS          current
    DESCRIPTION
         "The value of msapPlcyCpmProtMonitorMac specifies whether the 
          tmnxCpmProtPolPerSrcRateLimit of the CPM Protection policy,
          as specified by msapPlcyCpmProtPolicyId, must be applied.
         
         If the value of msapPlcyCpmProtMonitorMac is 'true', the
         per-source rate limit must be applied.
         
         If the value of msapPlcyCpmProtPolicyId is equal to zero,
         the value of msapPlcyCpmProtMonitorMac is irrelevant and
         will be ignored.

         This object is not supported on 7710, where the value of
         TIMETRA-CHASSIS-MIB::tmnxChassisType is '7' or '9'.
         
         An attempt  to set msapPlcyCpmProtMonitorMac to 'true' 
         on one of these unsupported chassis types will return an
         'inconsistentValue' error."
    DEFVAL { false }
    ::= { msapPlcyEntry 6 }

msapPlcySubMgmtDefSubId        OBJECT-TYPE
    SYNTAX      TmnxDefSubIdSource
    MAX-ACCESS  read-create
    STATUS      current
    DESCRIPTION
        "The value of msapPlcySubMgmtDefSubId specifies what will be used as
         the default subscriber identification applicable on the MSAP.

         This value is used in case no other source (like Radius) provides a 
         subscriber identification string.

         If the value of this object is set to 'useSapId', the SAP-id will
         be used as the default subscriber identification string. In this case,
         msapPlcySubMgmtDefSubIdStr must contain the empty string, so any
         non-empty string in msapPlcySubMgmtDefSubIdStr will be set to an empty
         string.

         If the value of this object is set to 'useAutoId',
         the auto-generated subscriber identification string, as defined in
         tmnxSubMgmtAutoSubIdObjs, is used as the default subscriber
         identification string. In this case, msapPlcySubMgmtDefSubIdStr
         must contain the empty string, so any non-empty string in
         msapPlcySubMgmtDefSubIdStr will be set to an empty string.

         If the value of this object is set to 'useString', the value of
         msapPlcySubMgmtDefSubIdStr will be used as the default subscriber 
         identification string. In this case, an empty msapPlcySubMgmtDefSubIdStr
         means that there is no default subscriber identification configured."
    DEFVAL { useString }
    ::= { msapPlcyEntry 7 }

msapPlcySubMgmtDefSubIdStr        OBJECT-TYPE
    SYNTAX      TNamedItemOrEmpty
    MAX-ACCESS  read-create
    STATUS      current
    DESCRIPTION
        "The value of msapPlcySubMgmtDefSubIdStr specifies the default 
         subscriber identification string applicable on this MSAP."
    DEFVAL { "" }
    ::= { msapPlcyEntry 8 }

msapPlcySubMgmtDefSubProfile        OBJECT-TYPE
    SYNTAX      TNamedItemOrEmpty
    MAX-ACCESS  read-create
    STATUS      current
    DESCRIPTION
        "The value of msapPlcySubMgmtDefSubProfile specifies the default
         subscriber profile applicable on the MSAP.

         If a corresponding profile is not defined in tmnxSubProfileTable, an 
         'inconsistentValue' error will be returned.

         A value of 'default' is not allowed for this object."
    DEFVAL { "" }
    ::= { msapPlcyEntry 9 }

msapPlcySubMgmtDefSlaProfile        OBJECT-TYPE
    SYNTAX      TNamedItemOrEmpty
    MAX-ACCESS  read-create
    STATUS      current
    DESCRIPTION
        "The value of msapPlcySubMgmtDefSlaProfile specifies the default SLA
         profile applicable on the MSAP. 

         If a corresponding profile is not defined in tmnxSLAProfileTable, an 
         'inconsistentValue' error will be returned."
    DEFVAL { "" }
    ::= { msapPlcyEntry 10 }

msapPlcySubMgmtDefAppProfile        OBJECT-TYPE
    SYNTAX      TNamedItemOrEmpty
    MAX-ACCESS  read-create
    STATUS      current
    DESCRIPTION
        "The value of msapPlcySubMgmtDefAppProfile specifies the default
         application profile applicable on the MSAP. 

         If a corresponding profile is not defined in
         TIMETRA-BSX-NG-MIB::tmnxBsxAppProfTable, an 'inconsistentValue'
         error will be returned."
    DEFVAL { "" }
    ::= { msapPlcyEntry 11 }

msapPlcySubMgmtSubIdPlcy        OBJECT-TYPE
    SYNTAX      TPolicyStatementNameOrEmpty
    MAX-ACCESS  read-create
    STATUS      current
    DESCRIPTION
        "The value of msapPlcySubMgmtSubIdPlcy specifies the subscriber 
         identification policy applicable on the MSAP.

         If a corresponding profile is not defined in tmnxSubIdentPolicyTable,
         an 'inconsistentValue' error will be returned."
    DEFVAL { "" }
    ::= { msapPlcyEntry 12 }

msapPlcySubMgmtSubscriberLimit OBJECT-TYPE
    SYNTAX          TmnxSapSubscriberLimit
    MAX-ACCESS      read-create
    STATUS          current
    DESCRIPTION     
        "The value of msapPlcySubMgmtSubscriberLimit specifies the
         maximum number of subscribers allowed for the MSAP.
        
         A value is 0 means there is no limit.

         The values for the objects msapPlcySubMgmtProfiledTrafOnly,
         msapPlcySubMgmtNonSubTrafSubProf, and
         msapPlcySubMgmtNonSubTrafSlaProf are only meaningful when
         the value of msapPlcySubMgmtSubscriberLimit is 1 and will not
         be used when the value of msapPlcySubMgmtSubscriberLimit is 
         not 1."
    DEFVAL { 1 }
    ::= { msapPlcyEntry 13 }

msapPlcySubMgmtProfiledTrafOnly OBJECT-TYPE
    SYNTAX          TruthValue
    MAX-ACCESS      read-create
    STATUS          current
    DESCRIPTION     
        "The value of msapPlcySubMgmtProfiledTrafOnly specifies
         whether only profiled traffic is applicable for the MSAP.
         If set to 'true', the MSAP queues will be deleted.
         
         The value of this object is only meaningful if
         msapPlcySubMgmtSubscriberLimit is set to 1."
    DEFVAL { false }
    ::= { msapPlcyEntry 14 }

msapPlcySubMgmtNonSubTrafSubId OBJECT-TYPE
    SYNTAX          TNamedItemOrEmpty
    MAX-ACCESS      read-create
    STATUS          current
    DESCRIPTION     
        "The value of msapPlcySubMgmtNonSubTrafSubId specifies the
         subscriber identification applicable on the MSAP for all
         non-subscriber traffic.

         The value of this object is only meaningful if
         msapPlcySubMgmtSubscriberLimit is set to 1."
    DEFVAL { "" }
    ::= { msapPlcyEntry 15 }

msapPlcySubMgmtNonSubTrafSubProf OBJECT-TYPE
    SYNTAX          TNamedItemOrEmpty
    MAX-ACCESS      read-create
    STATUS          current
    DESCRIPTION
        "The value of msapPlcySubMgmtNonSubTrafSubProf specifies the
         subscriber profile applicable on the MSAP for all
         non-subscriber traffic.
         
         The value of this object is only meaningful if
         msapPlcySubMgmtSubscriberLimit is set to 1."
    DEFVAL { "" }
    ::= { msapPlcyEntry 16 }

msapPlcySubMgmtNonSubTrafSlaProf OBJECT-TYPE
    SYNTAX          TNamedItemOrEmpty
    MAX-ACCESS      read-create
    STATUS          current
    DESCRIPTION
        "The value of msapPlcySubMgmtNonSubTrafSlaProf specifies the
         SLA profile applicable on the MSAP for all non-subscriber
         traffic.

         The value of this object is only meaningful if
         msapPlcySubMgmtSubscriberLimit is set to 1."
    DEFVAL { "" }
    ::= { msapPlcyEntry 17 }

msapPlcySubMgmtNonSubTrafAppProf OBJECT-TYPE
    SYNTAX          TNamedItemOrEmpty
    MAX-ACCESS      read-create
    STATUS          current
    DESCRIPTION
        "The value of msapPlcySubMgmtNonSubTrafAppProf specifies the
         Application profile applicable on the MSAP for all 
         non-subscriber traffic.

         The value of this object is only meaningful if
         msapPlcySubMgmtSubscriberLimit is set to 1."
    DEFVAL { "" }
    ::= { msapPlcyEntry 18 }

msapPlcyAssociatedMsaps OBJECT-TYPE
    SYNTAX          Counter32
    MAX-ACCESS      read-only
    STATUS          current
    DESCRIPTION     
        "The value of msapPlcyAssociatedMsaps indicates the
         number of MSAPs associated with this MSAP policy."
    ::= { msapPlcyEntry 19 }

msapPlcySubMgmtDefInterDestId OBJECT-TYPE
    SYNTAX      TmnxDefInterDestIdSource
    MAX-ACCESS  read-create
    STATUS      current
    DESCRIPTION
        "The value of msapPlcySubMgmtDefInterDestId specifies what will be
         used as the default intermediate destination identifier applicable
         on the MSAP.

         This value is used in case no other source (like Radius) provides an 
         intermediate destination identifier.

         If the value of this object is set to 'useString', the value of
         msapPlcySubMgmtDefInterDestIdStr will be used as the default
         intermediate destination identifier. In this case, an empty
         msapPlcySubMgmtDefInterDestIdStr means that there is no default
         intermediate destination identifier configured.

         If the value of this object is set to 'useTopQTag', the top q-tag of
         the MSAP will be used as the default intermediate destination
         identifier. In this case, msapPlcySubMgmtDefInterDestIdStr must
         contain the empty string.

         If the value of this object is set to 'useVpi', the ATM VPI of
         the MSAP will be used as the default intermediate destination
         identifier. In this case, msapPlcySubMgmtDefInterDestIdStr must
         contain the empty string."
    DEFVAL { useString }
    ::= { msapPlcyEntry 20 }

msapPlcySubMgmtDefInterDestIdStr OBJECT-TYPE
    SYNTAX      TNamedItemOrEmpty
    MAX-ACCESS  read-create
    STATUS      current
    DESCRIPTION
        "The value of msapPlcySubMgmtDefSubIdStr specifies the default 
         subscriber identification string applicable on this MSAP."
    DEFVAL { "" }
    ::= { msapPlcyEntry 21 }

msapPlcyIgmpTrkExpiryTime OBJECT-TYPE
    SYNTAX      Unsigned32 (0|1..65535)
    UNITS       "seconds"
    MAX-ACCESS      read-create
    STATUS      current
    DESCRIPTION
        "The value of msapPlcyIgmpTrkExpiryTime specifies 
         the time in seconds that this system continues to track an inactive
         host.
         
         The value zero specifies that the value must be set to the actual 
         value of the object svcIgmpTrkExpiryTime of the service an MSAP 
         belongs to."
    DEFVAL { 0 }
    ::= { msapPlcyEntry 22 }

msapPlcyIgmpTrkImportPlcy OBJECT-TYPE
    SYNTAX      TPolicyStatementNameOrEmpty
    MAX-ACCESS  read-create
    STATUS      current
    DESCRIPTION
        "The value of the object msapPlcyIgmpTrkImportPlcy specifies
         the policy statement that must be applied to all
         incoming IGMP messages on the MSAP."
    DEFVAL { "" }
    ::= { msapPlcyEntry 23 }

msapPlcyIgmpTrkMaxNbrGrps OBJECT-TYPE
    SYNTAX      Unsigned32 (0..16000)
    MAX-ACCESS  read-create
    STATUS      current
    DESCRIPTION
        "The value of the object msapPlcyIgmpTrkMaxNbrGrps specifies
         how many group addresses are allowed for the MSAP.

         The value 0 means that no limit is imposed."
    DEFVAL { 0 }
    ::= { msapPlcyEntry 24 }

msapPlcyIgmpTrkMaxNbrSrcs OBJECT-TYPE
    SYNTAX      Unsigned32 (0..1000)
    MAX-ACCESS  read-create
    STATUS      current
    DESCRIPTION
        "The value of the object msapPlcyIgmpTrkMaxNbrSrcs specifies
         how many source addresses are allowed per group address for the MSAP.

         The value 0 means that no limit is imposed."
    DEFVAL { 0 }
    ::= { msapPlcyEntry 25 }

msapPlcySubMgmtDefFilterProfile        OBJECT-TYPE
    SYNTAX      TNamedItemOrEmpty
    MAX-ACCESS  read-create
    STATUS      current
    DESCRIPTION
        "The value of msapPlcySubMgmtDefFilterProfile specifies the default 
         filter profile applicable on the MSAP. 

         The specified filter profile needs to exists in the
         TIMETRA-SUBSCRIBER-MGMT-MIB::tmnxSubFilterProfileTable."
    DEFVAL { "" }
    ::= { msapPlcyEntry 26 }

msapPlcyLagLinkMapProfile OBJECT-TYPE
    SYNTAX          TmnxLinkMapProfileIdOrZero
    MAX-ACCESS      read-create
    STATUS          current
    DESCRIPTION
        "The value of msapPlcyLagLinkMapProfile specifies the LAG link map
         profile identifier associated with this MSAP policy."
    DEFVAL          { 0 }
    ::= { msapPlcyEntry 27 }

msapPlcyIgmpTrkMaxNbrGrpSrcs OBJECT-TYPE
    SYNTAX      Unsigned32 (0..32000)
    MAX-ACCESS  read-create
    STATUS      current
    DESCRIPTION
        "The value of the object msapPlcyIgmpTrkMaxNbrGrpSrcs specifies how
         many group source addresses are allowed per group address for the MSAP.

         The value 0 means that no limit is imposed."
    DEFVAL { 0 }
    ::= { msapPlcyEntry 28 }

msapPlcyDCpuProtPolicy OBJECT-TYPE
    SYNTAX          TNamedItemOrEmpty
    MAX-ACCESS      read-create
    STATUS          current
    DESCRIPTION     
        "The value of msapPlcyDCpuProtPolicy associates Distributed CPU
         Protection Policy with a MSAP policy."
    DEFVAL { ''H }
    ::= { msapPlcyEntry 29 }

msapPlcyCpmProtMonitorIP OBJECT-TYPE
    SYNTAX          TruthValue
    MAX-ACCESS      read-create
    STATUS          current
    DESCRIPTION
        "The value of msapPlcyCpmProtMonitorIP specifies whether or not to apply
         the tmnxCpmProtPolPerSrcRateLimit of this MSAP policy's CPM Protection 
         policy to IPv4 DHCP packets served by the MSAP policy, on a per source
         IP address basis.

         For example, suppose msapPlcyCpmProtMonitorIP is 'true', and this MSAP 
         policy's msapPlcyCpmProtPolicyId points to a policy table row with
         tmnxCpmProtPolPerSrcRateLimit set to 100 packets/second. Suppose two
         source IP addresses (e.g. 138.120.141.173 and 138.120.141.174)
         each send 150 DHCP packets/second to this SAP. Approx. 50 DCHP
         packets/second from each source will be discarded.

         If the value of msapPlcyCpmProtPolicyId is equal to zero, the value of
         msapPlcyCpmProtMonitorIP is irrelevant and will be ignored.

         This object is not supported on 7710, where the value
         of TIMETRA-CHASSIS-MIB::tmnxChassisType is '7' or '9'. An attempt to 
         set msapPlcyCpmProtMonitorIP to a non-zero value on one of these 
         unsupported chassis types will return an 'inconsistentValue' error."
    DEFVAL { false }
    ::= { msapPlcyEntry 30 }

-- --------------------------------------------------------
-- msapTlsPlcyTable
-- --------------------------------------------------------
msapTlsPlcyTable OBJECT-TYPE
    SYNTAX      SEQUENCE OF MsapTlsPlcyEntry
    MAX-ACCESS  not-accessible
    STATUS      current
    DESCRIPTION
        "The msapTlsPlcyTable has an entry for each managed SAP (MSAP)
         policy configured in the system."
    ::= { tmnxSapObjs 45 }

msapTlsPlcyEntry    OBJECT-TYPE
    SYNTAX      MsapTlsPlcyEntry
    MAX-ACCESS  not-accessible
    STATUS      current
    DESCRIPTION
        "Each entry represents the VPLS-related configuration for a managed
         SAP (MSAP) policy.

         The values for each entry will be used to populate the following
         VPLS-related tables when the MSAP policy is applied to a MSAP:
 
         TIMETRA-SAP-MIB::sapTlsInfoTable
         TIMETRA-SAP-MIB::sapTlsDhcpInfoTable
         ALCATEL-IGMP-SNOOPING-MIB::tlsIgmpSnpgConfigTable
        "
    AUGMENTS { msapPlcyEntry }
    ::= { msapTlsPlcyTable 1}

MsapTlsPlcyEntry ::= SEQUENCE
    {
        msapTlsPlcyLastChanged           TimeStamp,
        msapTlsPlcySplitHorizonGrp       TNamedItemOrEmpty,
        msapTlsPlcyArpReplyAgent         INTEGER,
        msapTlsPlcySubMgmtMacDaHashing   TruthValue,
        msapTlsPlcyDhcpLeasePopulate     Unsigned32,
        msapTlsPlcyDhcpPrxyAdminState    TmnxEnabledDisabled,
        msapTlsPlcyDhcpPrxyServAddrType  InetAddressType,
        msapTlsPlcyDhcpPrxyServAddr      InetAddress,
        msapTlsPlcyDhcpPrxyLeaseTime     Unsigned32,
        msapTlsPlcyDhcpPrxyLTRadOverride TruthValue,
        msapTlsPlcyDhcpInfoAction        INTEGER,
        msapTlsPlcyDhcpCircuitId         INTEGER,
        msapTlsPlcyDhcpRemoteId          INTEGER,
        msapTlsPlcyDhcpRemoteIdString    TNamedItemOrEmpty,
        msapTlsPlcyDhcpVendorInclOpts    BITS,
        msapTlsPlcyDhcpVendorOptStr      TNamedItemOrEmpty,
        msapTlsPlcyEgressMcastGroup      TNamedItemOrEmpty,
        msapTlsPlcyIgmpSnpgImportPlcy    TPolicyStatementNameOrEmpty,
        msapTlsPlcyIgmpSnpgFastLeave     TmnxEnabledDisabled,
        msapTlsPlcyIgmpSnpgSendQueries   TmnxEnabledDisabled,
        msapTlsPlcyIgmpSnpgGenQueryIntv  Unsigned32,
        msapTlsPlcyIgmpSnpgQueryRespIntv Unsigned32,
        msapTlsPlcyIgmpSnpgRobustCount   Unsigned32,
        msapTlsPlcyIgmpSnpgLastMembIntvl Unsigned32,
        msapTlsPlcyIgmpSnpgMaxNbrGrps    Unsigned32,
        msapTlsPlcyIgmpSnpgMvrFromVplsId TmnxServId,
        msapTlsPlcyIgmpSnpgVersion       TmnxIgmpVersion,
        msapTlsPlcyIgmpSnpgMcacPlcyName  TPolicyStatementNameOrEmpty,
        msapTlsPlcyIgmpSnpgMcacUncnstBW  Integer32,
        msapTlsPlcyIgmpSnpgMcacPrRsvMnBW Integer32,
        msapTlsPlcyArpHostMaxNumHosts    Unsigned32,
        msapTlsPlcyArpHostMinAuthIntvl   Unsigned32,
        msapTlsPlcyIgmpSnpgMcacUsePortWt TruthValue,
        msapTlsPlcyIngQosPolicyId            TSapIngressPolicyID,
        msapTlsPlcyIngQosQueueingType        INTEGER
    }

msapTlsPlcyLastChanged        OBJECT-TYPE
    SYNTAX      TimeStamp
    MAX-ACCESS  read-only
    STATUS      current
    DESCRIPTION
        "The value of msapTlsPlcyLastChanged indicates the sysUpTime
         at the time of the last modification of this entry.

         If no changes were made to the entry since the last
         re-initialization of the local network management subsystem,
         then this object contains a zero value."
    ::= { msapTlsPlcyEntry 1 }

msapTlsPlcySplitHorizonGrp        OBJECT-TYPE
    SYNTAX      TNamedItemOrEmpty
    MAX-ACCESS  read-create
    STATUS      current
    DESCRIPTION
        "The value of msapTlsPlcySplitHorizonGrp specifies the name of the 
         split-horizon group for the MSAP.

         If the name specified does not correspond to a tlsShgInfoEntry
         for the VPLS service, the creation of the MSAP will fail.
         Additionally, if msapTlsPlcySplitHorizonGrp is set to a new value,
         the sapSplitHorizonGrp object for any existing MSAPs created by 
         this policy will not be updated."
    DEFVAL { "" }
    ::= { msapTlsPlcyEntry 2 }

msapTlsPlcyArpReplyAgent        OBJECT-TYPE
    SYNTAX      INTEGER {
                    disabled               (1),
                    enabled                (2),
                    enabledWithSubscrIdent (3)
                }
    MAX-ACCESS  read-create
    STATUS      current
    DESCRIPTION
        "The value of msapTlsPlcyArpReplyAgent specifies the status of the special
         ARP response mechanism in the system for ARP requests destined to 
         static or dynamic hosts associated with the MSAP.

         'disabled'               - the ARP reply function is not operational
         'enabled'                - the ARP reply function is enabled without
                                      subscriber identification.
         'enabledWithSubscrIdent' - the ARP reply function is enabled
                                      with subscriber identification."
    DEFVAL { disabled }
    ::= { msapTlsPlcyEntry 3 }

msapTlsPlcySubMgmtMacDaHashing OBJECT-TYPE
    SYNTAX          TruthValue
    MAX-ACCESS      read-create
    STATUS          current
    DESCRIPTION
        "The value of msapTlsPlcySubMgmtMacDaHashing specifies whether
         subscriber traffic egressing a LAG MSAP has its egress LAG
         link selected by a function of the MAC destination address
         instead of subscriber id."
    DEFVAL { false }
    ::= { msapTlsPlcyEntry 4 }

msapTlsPlcyDhcpLeasePopulate        OBJECT-TYPE
    SYNTAX      Unsigned32 (1..131071)
    MAX-ACCESS  read-create
    STATUS      current
    DESCRIPTION
        "The value of msapTlsPlcyDhcpLeasePopulate specifies the maximum number of
         DHCP lease states allowed on the MSAP."
    DEFVAL { 1 }
    ::= { msapTlsPlcyEntry 5 }

msapTlsPlcyDhcpPrxyAdminState        OBJECT-TYPE
    SYNTAX      TmnxEnabledDisabled
    MAX-ACCESS  read-create
    STATUS      current
    DESCRIPTION
        "The value of msapTlsPlcyDhcpPrxyAdminState specifies the desired 
         administrative state of the proxy server on the interface."
    DEFVAL { disabled }
    ::= { msapTlsPlcyEntry 6 }

msapTlsPlcyDhcpPrxyServAddrType        OBJECT-TYPE
    SYNTAX      InetAddressType
    MAX-ACCESS  read-create
    STATUS      current
    DESCRIPTION
        "The value of msapTlsPlcyDhcpPrxyServAddrType specifies the address type
        of msapTlsPlcyDhcpPrxyServAddr."
    DEFVAL { unknown }
    ::= { msapTlsPlcyEntry 7 }

msapTlsPlcyDhcpPrxyServAddr        OBJECT-TYPE
    SYNTAX      InetAddress (SIZE(0|4|16|20))
    MAX-ACCESS  read-create
    STATUS      current
    DESCRIPTION
        "The value of msapTlsPlcyDhcpPrxyServAddr specifies the IP address of the
         which will be used as the source address of the emulated DHCP server 
         in the context of the VPLS MSAP.
                     
         This address is mandatory for the proxy server capability and it 
         should be in the context of the subnet represented by the VPLS."
    DEFVAL { ''H }
    ::= { msapTlsPlcyEntry 8 }

msapTlsPlcyDhcpPrxyLeaseTime        OBJECT-TYPE
    SYNTAX      Unsigned32 (0|300..315446399)
    UNITS       "seconds"
    MAX-ACCESS  read-create
    STATUS      current
    DESCRIPTION
        "The value of msapTlsPlcyDhcpPrxyLeaseTime specifies, in seconds, how long
         a DHCP client is allowed to use the offered IP address.
                    
         A value of 0 means the lease time provided by a RADIUS or an upstream
         DHCP server will not be overridden. A value of 
         7 days (315446399 seconds) is used when RADIUS does not provide a
         lease time."
    DEFVAL { 0 }
    ::= { msapTlsPlcyEntry 9 }

msapTlsPlcyDhcpPrxyLTRadOverride        OBJECT-TYPE
    SYNTAX      TruthValue
    MAX-ACCESS  read-create
    STATUS      current
    DESCRIPTION
        "The value of msapTlsPlcyDhcpPrxyLTRadOverride specifies whether or not the
         lease time provided by the RADIUS server is presented to the DHCP 
         client.

         By default the proxy-server will always make use of 
         msapTlsPlcyDhcpPrxyLeaseTime, regardless of what lease time information is
         provided from the RADIUS server. When msapTlsPlcyDhcpPrxyLTRadOverride is
         set to 'true', the proxy-server will use the lease time 
         information provided by the RADIUS server, regardless of the 
         configured lease time."
    DEFVAL { false }
    ::= { msapTlsPlcyEntry 10 }

msapTlsPlcyDhcpInfoAction        OBJECT-TYPE
    SYNTAX      INTEGER {
                    replace (1),
                    drop    (2),
                    keep    (3)
                }
    MAX-ACCESS  read-create
    STATUS      current
    DESCRIPTION
        "The value of msapTlsPlcyDhcpInfoAction specifies the DHCP option 
         reforwarding policy:

         'replace' - replace existing information with configured 
                       information
         'drop'    - discard messages with existing relay information if the
                       option-82 information is also present
         'keep'    - retain the existing relay information"
    DEFVAL { keep }
    ::= { msapTlsPlcyEntry 11 }

msapTlsPlcyDhcpCircuitId        OBJECT-TYPE
    SYNTAX      INTEGER {
                    none           (0),
                    asciiTuple     (1),
                    vlanAsciiTuple (2)
                }
    MAX-ACCESS  read-create
    STATUS      current
    DESCRIPTION
        "The value of msapTlsPlcyDhcpCircuitId specifies whether or not the 
         circuit-id suboption is present, and if it is present what
         information goes in it:
         
         none           - the circuit-id suboption will not be part of
                          the information option (Option 82).
         asciiTuple     - the ASCII-encoded concatenated tuple consisting
                          of the
                              - access-node-identifier
                              - service-id
                              - interface-name
                          is used.
         vlanAsciiTuple - the format will include VLAN-id and dot1p bits
                          in addition to what is included in ascii-tuple
                          already.  The format is supported on dot1q and
                          qinq encapsulated ports only.  Thus, when the
                          option 82 bits are stripped, dot1p bits will be 
                          copied to the Ethernet header of an outgoing
                          packet."
    DEFVAL { asciiTuple }
    ::= { msapTlsPlcyEntry 12 }

msapTlsPlcyDhcpRemoteId        OBJECT-TYPE
    SYNTAX      INTEGER {
                    none      (1),
                    mac       (2),
                    remote-id (3)
                }
    MAX-ACCESS  read-create
    STATUS      current
    DESCRIPTION
        "The value of msapTlsPlcyDhcpRemoteId specifies what information goes into
         the remote-id suboption in the DHCP Relay packet.

         If the value of this object is set to 'none', the remote-id suboption
         will not be part of the information option (Option 82).

         If the value of this object is set to 'mac', the MAC address of the
         remote end is encoded in the suboption.

         If the value of this object is set to 'remote-id', 
         msapTlsPlcyDhcpRemoteIdString will represent the remote-id.

         By default, the remote-id value is none."
    DEFVAL { none }
    ::= { msapTlsPlcyEntry 13 }

msapTlsPlcyDhcpRemoteIdString        OBJECT-TYPE
    SYNTAX      TNamedItemOrEmpty
    MAX-ACCESS  read-create
    STATUS      current
    DESCRIPTION
        "The value of msapTlsPlcyDhcpRemoteIdString specifies the remote-id. The
         value of this object is ignored if msapTlsPlcyDhcpRemoteId does not 
         have the value of 'remote-id'."
    DEFVAL { "" }
    ::= { msapTlsPlcyEntry 14 }

msapTlsPlcyDhcpVendorInclOpts        OBJECT-TYPE
    SYNTAX      BITS {
                    systemId  (0),
                    clientMac (1),
                    serviceId (2),
                    sapId     (3)
                }
    MAX-ACCESS  read-create
    STATUS      current
    DESCRIPTION
        "The value of msapTlsPlcyDhcpVendorInclOpts specifies what is encoded 
         in the Nokia vendor specific sub-option of option 82.

         The value of this object is only used when msapTlsPlcyDhcpInfoAction is
         'replace'."
    DEFVAL { { } }
    ::= { msapTlsPlcyEntry 15 }

msapTlsPlcyDhcpVendorOptStr        OBJECT-TYPE
    SYNTAX      TNamedItemOrEmpty
    MAX-ACCESS  read-create
    STATUS      current
    DESCRIPTION
        "The value of msapTlsPlcyDhcpVendorOptStr specifies the string that goes
         into the Nokia vendor specific sub-option of option 82.

         This string is only used when msapTlsPlcyDhcpInfoAction is set to
         'replace'."
    DEFVAL { "" }
    ::= { msapTlsPlcyEntry 16 }

msapTlsPlcyEgressMcastGroup OBJECT-TYPE
    SYNTAX          TNamedItemOrEmpty
    MAX-ACCESS      read-create
    STATUS          current
    DESCRIPTION
        "The value of msapTlsPlcyEgressMcastGroup specifies the Egress Multicast
         Group for the MSAP."
    DEFVAL { "" }
    ::= { msapTlsPlcyEntry 17 }

msapTlsPlcyIgmpSnpgImportPlcy OBJECT-TYPE
    SYNTAX      TPolicyStatementNameOrEmpty
    MAX-ACCESS  read-create
    STATUS      current
    DESCRIPTION
        "The value of msapTlsPlcyIgmpSnpgImportPlcy specifies the policy statement
         that is be applied to all incoming IGMP messages on the MSAP."
    DEFVAL { "" }
    ::= { msapTlsPlcyEntry 18 }

msapTlsPlcyIgmpSnpgFastLeave OBJECT-TYPE
    SYNTAX      TmnxEnabledDisabled
    MAX-ACCESS  read-create
    STATUS      current
    DESCRIPTION
        "The value of msapTlsPlcyIgmpSnpgFastLeave specifies
         whether fast leave is allowed on this MSAP.
         
         If set to 'enabled', the system prunes the port on which an IGMP
         'leave' message has been received without waiting for the Group
         Specific Query to timeout."
    DEFVAL { disabled }
    ::= { msapTlsPlcyEntry 19 }

msapTlsPlcyIgmpSnpgSendQueries OBJECT-TYPE
    SYNTAX      TmnxEnabledDisabled
    MAX-ACCESS  read-create
    STATUS      current
    DESCRIPTION
        "The value of msapTlsPlcyIgmpSnpgSendQueries specifies
         whether the system generates General Queries by itself on
         the MSAP."
    DEFVAL { disabled }
    ::= { msapTlsPlcyEntry 20 }

msapTlsPlcyIgmpSnpgGenQueryIntv OBJECT-TYPE
    SYNTAX      Unsigned32 (2..1024)
    UNITS       "seconds"
    MAX-ACCESS  read-create
    STATUS      current
    DESCRIPTION
        "The value of msapTlsPlcyIgmpSnpgGenQueryIntv specifies
         the interval (in seconds) between two consecutive general queries sent
         by the system on the MSAP.

         The value of this object is only meaningful when the value of
         msapTlsPlcyIgmpSnpgSendQueries is 'enabled'."
    DEFVAL { 125 }
    ::= { msapTlsPlcyEntry 21 }

msapTlsPlcyIgmpSnpgQueryRespIntv OBJECT-TYPE
    SYNTAX      Unsigned32 (1..1023)
    UNITS       "seconds"
    MAX-ACCESS  read-create
    STATUS      current
    DESCRIPTION
        "The value of msapTlsPlcyIgmpSnpgQueryRespIntv specifies
         the maximum response time (in seconds) advertised in IGMPv2/v3
         queries.

         The value of this object is only meaningful when the value of
         msapTlsPlcyIgmpSnpgSendQueries is 'enabled'."
    DEFVAL { 10 }
    ::= { msapTlsPlcyEntry 22 }

msapTlsPlcyIgmpSnpgRobustCount OBJECT-TYPE
    SYNTAX      Unsigned32 (2..7)
    MAX-ACCESS  read-create
    STATUS      current
    DESCRIPTION
        "The value of msapTlsPlcyIgmpSnpgRobustCount specifies
         the robustness variable on the MSAP.

         This object allows tuning for the expected packet loss on the MSAP.
         If a MSAP is expected to be lossy, the Robustness Variable may be
         increased. IGMP snooping is robust to (Robustness Variable-1) packet
         losses.

         The value of this object is only meaningful when the value of
         msapTlsPlcyIgmpSnpgSendQueries is 'enabled'."
    DEFVAL { 2 }
    ::= { msapTlsPlcyEntry 23 }

msapTlsPlcyIgmpSnpgLastMembIntvl OBJECT-TYPE
    SYNTAX      Unsigned32 (1..50)
    UNITS       "deci-seconds"
    MAX-ACCESS  read-create
    STATUS      current
    DESCRIPTION
        "The value of msapTlsPlcyIgmpSnpgLastMembIntvl specifies the 
         Max Response Time (in tenths of a second) used in
         Group-Specific and Group-Source-Specific Queries sent in response
         to 'leave' messages. This is also the amount of time between
         Group-Specific Query messages.

         This value may be tuned to modify the leave latency of the network.
         A reduced value results in reduced time to detect the loss of the last
         member of a group."
    DEFVAL { 10 }
    ::= { msapTlsPlcyEntry 24 }

msapTlsPlcyIgmpSnpgMaxNbrGrps OBJECT-TYPE
    SYNTAX      Unsigned32 (0..16000)
    MAX-ACCESS  read-create
    STATUS      current
    DESCRIPTION
        "The value of msapTlsPlcyIgmpSnpgMaxNbrGrps specifies how many group
         addresses are allowed for the MSAP.

         The value 0 means that no limit is imposed."
    DEFVAL { 0 }
    ::= { msapTlsPlcyEntry 25 }

msapTlsPlcyIgmpSnpgMvrFromVplsId OBJECT-TYPE
    SYNTAX      TmnxServId
    MAX-ACCESS  read-create
    STATUS      current
    DESCRIPTION
        "The value of msapTlsPlcyIgmpSnpgMvrFromVplsId specifies from which
         VPLS the multicast streams corresponding to the groups learned
         via the MSAP are copied.

         Groups which cannot be joined to the corresponding MVR VPLS
         (because MVR is not up or the configured MVR policy rejects the group)
         copy the multicast streams from the local VPLS if IGMP snooping is up
         (i.e. tlsIgmpSnpgCfgAdminState is 'enabled')."
    DEFVAL { 0 }
    ::= { msapTlsPlcyEntry 26 }

msapTlsPlcyIgmpSnpgVersion OBJECT-TYPE
    SYNTAX      TmnxIgmpVersion
    MAX-ACCESS  read-create
    STATUS      current
    DESCRIPTION
        "The value of msapTlsPlcyIgmpSnpgVersion specifies the version
         of IGMP running on the MSAP."
    DEFVAL { version3 }
    ::= { msapTlsPlcyEntry 27 }

msapTlsPlcyIgmpSnpgMcacPlcyName OBJECT-TYPE
    SYNTAX     TPolicyStatementNameOrEmpty
    MAX-ACCESS read-create
    STATUS     current
    DESCRIPTION
        "The value of msapTlsPlcyIgmpSnpgMcacPlcyName specifies the name
         of the multicast CAC (Connection Admission Control) policy."
    DEFVAL { "" }
    ::= { msapTlsPlcyEntry 28 }

msapTlsPlcyIgmpSnpgMcacUncnstBW OBJECT-TYPE
    SYNTAX      Integer32 (-1|0..2147483647)
    UNITS       "kbps"
    MAX-ACCESS  read-create
    STATUS      current
    DESCRIPTION
        "The value of msapTlsPlcyIgmpSnpgMcacUncnstBW specifies the bandwidth
         assigned for interface's multicast CAC policy traffic in kilo-bits per
         second(kbps). 

         If the default value of '-1' is set, there is no constraint on
         bandwidth allocated at the interface. 

         If the value of msapTlsPlcyIgmpSnpgMcacUncnstBW is set to '0' and if 
         a multicast CAC policy is assigned on the interface, then 
         no group (channel) from that policy is allowed on that interface."
    DEFVAL { -1 }
    ::= { msapTlsPlcyEntry 29 }

msapTlsPlcyIgmpSnpgMcacPrRsvMnBW OBJECT-TYPE
    SYNTAX      Integer32 (-1|0..2147483647)
    UNITS       "kbps"
    MAX-ACCESS  read-create
    STATUS      current
    DESCRIPTION
        "The value of msapTlsPlcyIgmpSnpgMcacPrRsvMnBW specifies the bandwidth
         pre-reserved for all the mandatory channels on a given interface
         in kilo-bits per second(kbps). 
              
         If the value of msapTlsPlcyIgmpSnpgMcacUncnstBW is '0', no mandatory
         channels are allowed. If the value of msapTlsPlcyIgmpSnpgMcacPrRsvMnBW 
         is '-1', then all mandatory and optional channels are allowed.

         If the value of msapTlsPlcyIgmpSnpgMcacPrRsvMnBW is equal to the 
         value of msapTlsPlcyIgmpSnpgMcacUncnstBW, then all the unconstrained 
         bandwidth on a given interface is allocated to mandatory channels 
         configured through multicast CAC policy on that interface and no 
         optional groups (channels) are allowed.

         The value of msapTlsPlcyIgmpSnpgMcacPrRsvMnBW should always be less 
         than or equal to that of msapTlsPlcyIgmpSnpgMcacUncnstBW. An attempt 
         to set the value of msapTlsPlcyIgmpSnpgMcacPrRsvMnBW greater than 
         that of msapTlsPlcyIgmpSnpgMcacUncnstBW will result in 
         'inconsistentValue' error."
    DEFVAL { -1 }
    ::= { msapTlsPlcyEntry 30 }

msapTlsPlcyArpHostMaxNumHosts OBJECT-TYPE
    SYNTAX      Unsigned32 (1..131071)
    MAX-ACCESS  read-create
    STATUS      current
    DESCRIPTION
        "The value of msapTlsPlcyArpHostMaxNumHosts specifies the maximum
         number of ARP hosts allowed on the TLS MSAP."
    DEFVAL { 1 }
    ::= { msapTlsPlcyEntry 31 }

msapTlsPlcyArpHostMinAuthIntvl OBJECT-TYPE
    SYNTAX      Unsigned32 (1..6000)
    UNITS       "minutes"
    MAX-ACCESS  read-create
    STATUS      current
    DESCRIPTION
        "The value of msapTlsPlcyArpHostMinAuthIntvl specifies the minimum
         interval between two consecutive authentication attempts for the
         same ARP host."
    DEFVAL { 15 }
    ::= { msapTlsPlcyEntry 32 }

msapTlsPlcyIgmpSnpgMcacUsePortWt OBJECT-TYPE
    SYNTAX      TruthValue  
    MAX-ACCESS  read-create
    STATUS      current
    DESCRIPTION
        "The value of msapTlsPlcyIgmpSnpgMcacUsePortWt specifies
         if this system must use the LAG port weight
         while calculating Multicast CAC constraints.
         
         The LAG port weight is configured with the object TIMETRA-LAG-MIB::tLagPortWeightSpeed."
    DEFVAL { false }
    ::= { msapTlsPlcyEntry 33 }

msapTlsPlcyIngQosPolicyId OBJECT-TYPE
    SYNTAX          TSapIngressPolicyID (1)
    MAX-ACCESS      read-create
    STATUS          current
    DESCRIPTION
        "The value of msapTlsPlcyIngQosPolicyId specifies the ingress QoS
         policy applicable to this MSAP policy in VPLS (L2) services. The
         corresponding policy is defined in TIMETRA-QOS-MIB::tSapIngressTable."
    DEFVAL { 1 }
    ::= { msapTlsPlcyEntry 34 }

msapTlsPlcyIngQosQueueingType OBJECT-TYPE
    SYNTAX          INTEGER {
                        multipointShared    (1),
                        serviceQueueing     (2)
                    }
    MAX-ACCESS      read-create
    STATUS          current
    DESCRIPTION
        "The value of msapTlsPlcyIngQosQueueingType specifies the ingress
         queueing type applicable to this MSAP policy in VPLS (L2) services."
    DEFVAL { multipointShared }
    ::= { msapTlsPlcyEntry 35 }

-- --------------------------------------------------------
--
--  msapIgmpSnpgMcacLevelTable
--
-- --------------------------------------------------------

msapIgmpSnpgMcacLevelTable OBJECT-TYPE
    SYNTAX      SEQUENCE OF MSapIgmpSnpgMcacLevelEntry
    MAX-ACCESS  not-accessible
    STATUS      current
    DESCRIPTION "The msapIgmpSnpgMcacLevelTable has an entry for each
                 multicast CAC policy constraint level configured for
                 a Managed SAP policy."
    ::= { tmnxSapObjs 46 }

msapIgmpSnpgMcacLevelEntry OBJECT-TYPE
    SYNTAX      MSapIgmpSnpgMcacLevelEntry
    MAX-ACCESS  not-accessible
    STATUS      current
    DESCRIPTION "Each row entry represents a multicast CAC policy
                 bundle level constraints for a particular Managed
                 SAP policy. Entries are created and deleted by
                 the user."
    INDEX { msapPlcyName, msapIgmpSnpgMcacLevelId }
    ::= { msapIgmpSnpgMcacLevelTable 1}

MSapIgmpSnpgMcacLevelEntry ::= SEQUENCE {
   msapIgmpSnpgMcacLevelId          Unsigned32,
   msapIgmpSnpgMcacLevelRowStatus   RowStatus,
   msapIgmpSnpgMcacLevelLastChanged TimeStamp,
   msapIgmpSnpgMcacLevelBW          Unsigned32
}

msapIgmpSnpgMcacLevelId OBJECT-TYPE
    SYNTAX      Unsigned32 (1..8)
    MAX-ACCESS  not-accessible
    STATUS      current
    DESCRIPTION "The value of msapIgmpSnpgMcacLevelId indicates
                 the level id of the multicast CAC policy bundle
                 constraint.

                 The value of level 1 has the highest priority and
                 level 8 the lowest."
    ::= { msapIgmpSnpgMcacLevelEntry 1 }

msapIgmpSnpgMcacLevelRowStatus OBJECT-TYPE
    SYNTAX      RowStatus
    MAX-ACCESS  read-create
    STATUS      current
    DESCRIPTION "The value of msapIgmpSnpgMcacLevelRowStatus is
                 used for creation and deletion of level constraint
                 in a CAC for a Managed SAP policy."
    ::= { msapIgmpSnpgMcacLevelEntry 2 }

msapIgmpSnpgMcacLevelLastChanged OBJECT-TYPE
    SYNTAX      TimeStamp
    MAX-ACCESS  read-only
    STATUS      current
    DESCRIPTION "The value of msapIgmpSnpgMcacLevelLastChanged indicates
                 the sysUpTime at the time of the last modification
                 of this entry.

                 If no changes were made to the entry since the last
                 re-initialization of the local network management
                 subsystem, then this object contains a zero value."
    ::= { msapIgmpSnpgMcacLevelEntry 3 }

msapIgmpSnpgMcacLevelBW OBJECT-TYPE
    SYNTAX      Unsigned32
    UNITS       "kbps"
    MAX-ACCESS  read-create
    STATUS      current
    DESCRIPTION "The value of msapIgmpSnpgMcacLevelBW specifies
                 the bandwidth in kilo-bits per second (kbps) for
                 the level."
    DEFVAL { 1 }
    ::= { msapIgmpSnpgMcacLevelEntry 4 }

-- --------------------------------------------------------
--
--  msapIgmpSnpgMcacLagTable
--
-- --------------------------------------------------------

msapIgmpSnpgMcacLagTable OBJECT-TYPE
    SYNTAX      SEQUENCE OF MSapIgmpSnpgMcacLagEntry
    MAX-ACCESS  not-accessible
    STATUS      current
    DESCRIPTION "The msapIgmpSnpgMcacLagTable has an entry for each lag
                 port configured for a multicast CAC policy bundle configured
                 for a Managed SAP policy."
    ::= { tmnxSapObjs 47 }

msapIgmpSnpgMcacLagEntry OBJECT-TYPE
    SYNTAX      MSapIgmpSnpgMcacLagEntry
    MAX-ACCESS  not-accessible
    STATUS      current
    DESCRIPTION "Each row entry represents a particular multicast CAC lag port
                 constraints for a Managed SAP policy.. Entries are
                 created and deleted by the user."
    INDEX { msapPlcyName, msapIgmpSnpgMcacLagPortsDown } 
    ::= { msapIgmpSnpgMcacLagTable 1}

MSapIgmpSnpgMcacLagEntry ::= SEQUENCE {
   msapIgmpSnpgMcacLagPortsDown    Unsigned32,
   msapIgmpSnpgMcacLagRowStatus    RowStatus,
   msapIgmpSnpgMcacLagLastChanged  TimeStamp,
   msapIgmpSnpgMcacLagLevel        Unsigned32
}

msapIgmpSnpgMcacLagPortsDown OBJECT-TYPE
    SYNTAX      Unsigned32 (1..64)
    MAX-ACCESS  not-accessible
    STATUS      current
    DESCRIPTION "The value of msapIgmpSnpgMcacLagPortsDown indicates
                 the configured number of ports in a lag group that are down.

                 If the number of ports available in the lag is reduced by the  
                 number of ports configured for msapIgmpSnpgMcacLagPortsDown
                 object then bandwidth allowed for bundle will be updated to
                 the value of msapIgmpSnpgMcacLevelBW indexed by
                 msapIgmpSnpgMcacLagLevel value."
    ::= { msapIgmpSnpgMcacLagEntry 1 }

msapIgmpSnpgMcacLagRowStatus OBJECT-TYPE
    SYNTAX      RowStatus
    MAX-ACCESS  read-create
    STATUS      current
    DESCRIPTION "The value of msapIgmpSnpgMcacLagRowStatus is used for
                 creation and deletion of lag constraint in a CAC policy."      
    ::= { msapIgmpSnpgMcacLagEntry 2 }

msapIgmpSnpgMcacLagLastChanged OBJECT-TYPE
    SYNTAX      TimeStamp
    MAX-ACCESS  read-only
    STATUS      current
    DESCRIPTION "The value of msapIgmpSnpgMcacLagLastChanged indicates the 
                 sysUpTime at the time of the last modification of this entry.

                 If no changes were made to the entry since the last
                 re-initialization of the local network management subsystem,
                 then this object contains a zero value."
    ::= { msapIgmpSnpgMcacLagEntry 3 }

msapIgmpSnpgMcacLagLevel OBJECT-TYPE
    SYNTAX      Unsigned32 (1..8)
    MAX-ACCESS  read-create
    STATUS      current
    DESCRIPTION "The value of msapIgmpSnpgMcacLagLevel specifies the level
                 id to use when the value of msapIgmpSnpgMcacLagPortsDown
                 matches the actual number of ports down in a lag.
    
                 Using the value of msapIgmpSnpgMcacLagLevel as an index,
                 the operational MSAP unconstrained bandwidth will be set
                 to msapIgmpSnpgMcacLevelBW.

                 By default, for all lag constraints the link level will
                 be set to 1 at row creation."
    DEFVAL { 1 }         
    ::= { msapIgmpSnpgMcacLagEntry 4 }

-- ---------------------------------------------------------------------
--  Managed SAP Information Table
--
--  Sparse Dependent Extension of the sapBaseInfoTable.
--
--  The same indexes are used for both the base table, sapBaseInfoTable,
--  and the sparse dependent table, msapInfoTable.
--
--  This in effect extends the sapBaseInfoTable with additional columns.
--  Rows are created in the msapInfoTable only for those entries
--  in the sapBaseInfoTable that are created on a port with a 
--  sapSubType of 'managed'.
--
--  Deletion of a row in the sapBaseInfoTable results in the
--  same fate for the row in the msapInfoTable.
-- ---------------------------------------------------------------------

msapInfoTable OBJECT-TYPE
    SYNTAX          SEQUENCE OF MSapInfoEntry
    MAX-ACCESS      not-accessible
    STATUS          current
    DESCRIPTION     "A table that contains Managed SAP information."
    ::= { tmnxSapObjs 48 }

msapInfoEntry OBJECT-TYPE
    SYNTAX          MSapInfoEntry
    MAX-ACCESS      not-accessible
    STATUS          current
    DESCRIPTION     "Information about a specific Managed SAP."
    INDEX           { svcId, sapPortId, sapEncapValue }
    ::= { msapInfoTable 1 }

MSapInfoEntry ::=
    SEQUENCE {
        msapInfoCreationSapPortEncapVal      TmnxEncapVal,
        msapInfoCreationPlcyName             TNamedItem,
        msapInfoReEvalPolicy                 TmnxActionType,
        msapInfoLastChanged                  TimeStamp
    }

msapInfoCreationSapPortEncapVal OBJECT-TYPE
    SYNTAX            TmnxEncapVal
    MAX-ACCESS        read-only
    STATUS            current
    DESCRIPTION       "The value of msapInfoCreationSapPortEncapVal indicates
                       the port encapsulation value of the SAP with a sapSubType
                       value of 'capture' that created this MSAP."
    ::= { msapInfoEntry 1 }

msapInfoCreationPlcyName OBJECT-TYPE
    SYNTAX           TNamedItem
    MAX-ACCESS       read-only
    STATUS           current
    DESCRIPTION      "The value of msapInfoCreationPlcyName indicates
                      the value of the msapPlcyName object for MSAP policy
                      used to create this MSAP."
    ::= { msapInfoEntry 2 }

msapInfoReEvalPolicy OBJECT-TYPE
    SYNTAX           TmnxActionType
    MAX-ACCESS       read-write
    STATUS           current
    DESCRIPTION      "The value of msapInfoReEvalPolicy specifies whether
                      to re-apply the Managed SAP policy associated with
                      this MSAP.

                      When a SET of this object is done with a value of
                      'doAction', the system will attempt to re-apply the
                      MSAP policy indicated by msapInfoCreationPlcyName.
                      If this action is successful, 'noError' will be returned.
                      If this action is unsuccessful, an 'inconsistentValue'
                      error will be returned. Attempting to SET this object with
                      a value of 'notApplicable' will have no effect and will
                      return 'noError'.

                      SNMP GET and GETNEXT requests on this object will 
                      return 'notApplicable'."
    DEFVAL { notApplicable }
    ::= { msapInfoEntry 3 }

msapInfoLastChanged OBJECT-TYPE
    SYNTAX      TimeStamp
    MAX-ACCESS  read-only
    STATUS      current
    DESCRIPTION "The value of msapInfoLastChanged indicates the 
                 sysUpTime at the time of the last modification of this entry.

                 If no changes were made to the entry since the last
                 re-initialization of the local network management subsystem,
                 then this object contains a zero value."
    ::= { msapInfoEntry 4 }

-- ---------------------------------------------------------------------
-- Capture SAP Stats Table
--
--
--  Sparse Dependent Extension of the sapBaseInfoTable.
--
--  The same indexes are used for both the base table, sapBaseInfoTable,
--  and the sparse dependent table, msapCaptureSapStatsTable.
--
--  This in effect extends the sapBaseInfoTable with additional columns.
--  Rows are created in the msapTriggerPktStatsTable only for those entries
--  in the sapBaseInfoTable that have a sapSubType of 'capture'.
--
--  Deletion of a row in the sapBaseInfoTable results in the
--  same fate for the row in the msapTriggerPktStatsTable.
-- ---------------------------------------------------------------------
msapCaptureSapStatsTable OBJECT-TYPE
    SYNTAX          SEQUENCE OF MSapCaptureSapStatsEntry
    MAX-ACCESS      not-accessible
    STATUS          current
    DESCRIPTION     "A table that contains statistics for SAPs 
                     with a sapSubType value of 'capture'."
    ::= { tmnxSapObjs 49 }

msapCaptureSapStatsEntry OBJECT-TYPE
    SYNTAX          MSapCaptureSapStatsEntry
    MAX-ACCESS      not-accessible
    STATUS          current
    DESCRIPTION     "Statistics for a specific 'capture' SAP."
    INDEX           { svcId, 
                      sapPortId,
                      sapEncapValue,
                      msapCaptureSapStatsTriggerType }
    ::= { msapCaptureSapStatsTable 1 }

MSapCaptureSapStatsEntry ::=
    SEQUENCE {
        msapCaptureSapStatsTriggerType   INTEGER,
        msapCaptureSapStatsPktsRecvd     Counter32,
        msapCaptureSapStatsPktsRedirect  Counter32,
        msapCaptureSapStatsPktsDropped   Counter32
    }

msapCaptureSapStatsTriggerType OBJECT-TYPE
    SYNTAX            INTEGER {
                          dhcp   (1),
                          pppoe  (2),
                          arp    (3),
                          dhcp6  (4),
                          ppp    (5),
                          rtrsol (6)
                      }
    MAX-ACCESS        not-accessible
    STATUS            current
    DESCRIPTION       "The value of msapCaptureSapStatsTriggerType indicates the
                       type of trigger packets this entry is for."
    ::= { msapCaptureSapStatsEntry 1 }

msapCaptureSapStatsPktsRecvd OBJECT-TYPE
    SYNTAX           Counter32
    MAX-ACCESS       read-only
    STATUS           current
    DESCRIPTION      "The value of msapCaptureSapStatsPktsRecvd indicates the
                      number of packets received on this 'capture' SAP."
    ::= { msapCaptureSapStatsEntry 2 }

msapCaptureSapStatsPktsRedirect OBJECT-TYPE
    SYNTAX           Counter32
    MAX-ACCESS       read-only
    STATUS           current
    DESCRIPTION      "The value of msapCaptureSapStatsPktsRedirect indicates the
                      number of packets redirected on this 'capture' SAP."
    ::= { msapCaptureSapStatsEntry 3 }

msapCaptureSapStatsPktsDropped OBJECT-TYPE
    SYNTAX           Counter32
    MAX-ACCESS       read-only
    STATUS           current
    DESCRIPTION      "The value of msapCaptureSapStatsPktsDropped indicates the
                      number of packets dropped on this 'capture' SAP."
    ::= { msapCaptureSapStatsEntry 4 }
 
-- -------------------------------------
-- TLS SAP MRP Table
-- -------------------------------------
sapTlsMrpTable OBJECT-TYPE
    SYNTAX          SEQUENCE OF SapTlsMrpEntry
    MAX-ACCESS      not-accessible
    STATUS          current
    DESCRIPTION     "The sapTlsMrpTable augments sapTlsInfoTable with
                     attributes of the Multiple Registration Protocol (MRP)
                     feature for the TLS SAP."
    ::= { tmnxSapObjs 50 }

sapTlsMrpEntry OBJECT-TYPE
    SYNTAX          SapTlsMrpEntry
    MAX-ACCESS      not-accessible
    STATUS          current
    DESCRIPTION     "MRP specific information about a SAP in a TLS."
    INDEX           { svcId, sapPortId, sapEncapValue }
    ::= { sapTlsMrpTable 1 }

SapTlsMrpEntry ::=
    SEQUENCE {
        sapTlsMrpRxPdus               Counter32,
        sapTlsMrpDroppedPdus          Counter32,
        sapTlsMrpTxPdus               Counter32,
        sapTlsMrpRxNewEvent           Counter32,
        sapTlsMrpRxJoinInEvent        Counter32,
        sapTlsMrpRxInEvent            Counter32,
        sapTlsMrpRxJoinEmptyEvent     Counter32,
        sapTlsMrpRxEmptyEvent         Counter32,
        sapTlsMrpRxLeaveEvent         Counter32,
        sapTlsMrpTxNewEvent           Counter32,
        sapTlsMrpTxJoinInEvent        Counter32,
        sapTlsMrpTxInEvent            Counter32,
        sapTlsMrpTxJoinEmptyEvent     Counter32,
        sapTlsMrpTxEmptyEvent         Counter32,
        sapTlsMrpTxLeaveEvent         Counter32
    }

sapTlsMrpRxPdus OBJECT-TYPE
    SYNTAX           Counter32
    MAX-ACCESS       read-only
    STATUS           current
    DESCRIPTION      
        "The value of sapTlsMrpRxPdus indicates the number of MRP packets
        received on this SAP."
    ::= { sapTlsMrpEntry 1 }

sapTlsMrpDroppedPdus OBJECT-TYPE
    SYNTAX           Counter32
    MAX-ACCESS       read-only
    STATUS           current
    DESCRIPTION      
        "The value of sapTlsMrpDroppedPdus indicates the number of dropped MRP
        packets on this SAP."
    ::= { sapTlsMrpEntry 2 }

sapTlsMrpTxPdus OBJECT-TYPE
    SYNTAX           Counter32
    MAX-ACCESS       read-only
    STATUS           current
    DESCRIPTION      
        "The value of sapTlsMrpTxPdus indicates the number of MRP packets
        transmitted on this SAP."
    ::= { sapTlsMrpEntry 3 }

sapTlsMrpRxNewEvent OBJECT-TYPE
    SYNTAX           Counter32
    MAX-ACCESS       read-only
    STATUS           current
    DESCRIPTION      
        "The value of sapTlsMrpRxNewEvent indicates the number of 'New' MRP
        events received on this SAP."
    ::= { sapTlsMrpEntry 4 }

sapTlsMrpRxJoinInEvent OBJECT-TYPE
    SYNTAX           Counter32
    MAX-ACCESS       read-only
    STATUS           current
    DESCRIPTION      
        "The value of sapTlsMrpRxJoinInEvent indicates the number of 'Join-In'
        MRP events received on this SAP."
    ::= { sapTlsMrpEntry 5 }

sapTlsMrpRxInEvent OBJECT-TYPE
    SYNTAX           Counter32
    MAX-ACCESS       read-only
    STATUS           current
    DESCRIPTION      
        "The value of sapTlsMrpRxInEvent indicates the number of 'In' MRP
        events received on this SAP."
    ::= { sapTlsMrpEntry 6 }

sapTlsMrpRxJoinEmptyEvent OBJECT-TYPE
    SYNTAX           Counter32
    MAX-ACCESS       read-only
    STATUS           current
    DESCRIPTION      
        "The value of sapTlsMrpRxJoinEmptyEvent indicates the number of
        'Join Empty' MRP events received on this SAP."
    ::= { sapTlsMrpEntry 7 }
    
sapTlsMrpRxEmptyEvent OBJECT-TYPE
    SYNTAX           Counter32
    MAX-ACCESS       read-only
    STATUS           current
    DESCRIPTION      
        "The value of sapTlsMrpRxEmptyEvent indicates the number of 'Empty'
        MRP events received on this SAP."
    ::= { sapTlsMrpEntry 8 }
    
sapTlsMrpRxLeaveEvent OBJECT-TYPE
    SYNTAX           Counter32
    MAX-ACCESS       read-only
    STATUS           current
    DESCRIPTION      
        "The value of sapTlsMrpRxLeaveEvent indicates the number of 'Leave'
        MRP events received on this SAP."
    ::= { sapTlsMrpEntry 9 }
    
sapTlsMrpTxNewEvent OBJECT-TYPE
    SYNTAX           Counter32
    MAX-ACCESS       read-only
    STATUS           current
    DESCRIPTION      
        "The value of sapTlsMrpTxNewEvent indicates the number of 'New' MRP
        events transmitted on this SAP."
    ::= { sapTlsMrpEntry 10 }
    
sapTlsMrpTxJoinInEvent OBJECT-TYPE
    SYNTAX           Counter32
    MAX-ACCESS       read-only
    STATUS           current
    DESCRIPTION      
        "The value of sapTlsMrpTxJoinInEvent indicates the number of 'Join-In'
        MRP events transmitted on this SAP."
    ::= { sapTlsMrpEntry 11 }
    
sapTlsMrpTxInEvent OBJECT-TYPE
    SYNTAX           Counter32
    MAX-ACCESS       read-only
    STATUS           current
    DESCRIPTION      
        "The value of sapTlsMrpTxInEvent indicates the number of 'In' MRP
        events transmitted on this SAP."
    ::= { sapTlsMrpEntry 12 }
    
sapTlsMrpTxJoinEmptyEvent OBJECT-TYPE
    SYNTAX           Counter32
    MAX-ACCESS       read-only
    STATUS           current
    DESCRIPTION      
        "The value of sapTlsMrpTxJoinEmptyEvent indicates the number of
        'Join Empty' MRP events transmitted on this SAP."
    ::= { sapTlsMrpEntry 13 }

sapTlsMrpTxEmptyEvent OBJECT-TYPE
    SYNTAX           Counter32
    MAX-ACCESS       read-only
    STATUS           current
    DESCRIPTION      
        "The value of sapTlsMrpTxEmptyEvent indicates the number of 'Empty'
        MRP events transmitted on this SAP."
    ::= { sapTlsMrpEntry 14 }

sapTlsMrpTxLeaveEvent OBJECT-TYPE
    SYNTAX           Counter32
    MAX-ACCESS       read-only
    STATUS           current
    DESCRIPTION      
        "The value of sapTlsMrpTxLeaveEvent indicates the number of 'Leave'
        MRP events transmitted on this SAP."
    ::= { sapTlsMrpEntry 15 }

-- -------------------------------------
-- TLS SAP MMRP Table
-- -------------------------------------
sapTlsMmrpTable OBJECT-TYPE
    SYNTAX          SEQUENCE OF SapTlsMmrpEntry
    MAX-ACCESS      not-accessible
    STATUS          current
    DESCRIPTION     "This table contains an entry for each MAC address managed
                    by Multiple MAC Registration Protocol (MMRP) on the SAP
                    for the TLS.  Entries are dynamically created and
                    destroyed by the system as the MAC Addresses are registered
                    or declared in MMRP."
    ::= { tmnxSapObjs 51 }

sapTlsMmrpEntry OBJECT-TYPE
    SYNTAX          SapTlsMmrpEntry
    MAX-ACCESS      not-accessible
    STATUS          current
    DESCRIPTION     "MMRP specific information about a MAC address managed by
                    MMRP on a SAP in a TLS."
    INDEX           { svcId, sapPortId, sapEncapValue, sapTlsMmrpMacAddr }
    ::= { sapTlsMmrpTable 1 }

SapTlsMmrpEntry ::=
    SEQUENCE {
        sapTlsMmrpMacAddr              MacAddress,
        sapTlsMmrpDeclared             TruthValue,
        sapTlsMmrpRegistered           TruthValue,
        sapTlsMmrpEndStation           TruthValue
    }

sapTlsMmrpMacAddr OBJECT-TYPE
    SYNTAX        MacAddress
    MAX-ACCESS    not-accessible
    STATUS        current
    DESCRIPTION
        "The value of sapTlsMmrpMacAddr indicates an ethernet MAC address which
        is being managed by MMRP on this SAP."
    ::= { sapTlsMmrpEntry 1 }

sapTlsMmrpDeclared OBJECT-TYPE
    SYNTAX        TruthValue
    MAX-ACCESS    read-only
    STATUS        current
    DESCRIPTION
        "The value of sapTlsMmrpDeclared indicates whether the MRP applicant
        on this SAP is declaring this MAC address on behalf of MMRP."
    ::= { sapTlsMmrpEntry 2 }

sapTlsMmrpRegistered OBJECT-TYPE
    SYNTAX        TruthValue
    MAX-ACCESS    read-only
    STATUS        current
    DESCRIPTION
        "The value of sapTlsMmrpRegistered indicates whether the MRP registrant
        on this SAP has notified MMRP of a registration of this MAC address."
    ::= { sapTlsMmrpEntry 3 }

sapTlsMmrpEndStation OBJECT-TYPE
    SYNTAX        TruthValue
    MAX-ACCESS    read-only
    STATUS        current
    DESCRIPTION
        "The value of sapTlsMmrpEndStation indicates whether the MRP registrant
        on this SAP is registered per end station."
    ::= { sapTlsMmrpEntry 4 }

-- --------------------------------------------
-- SAP HSMDA QOS Ingress Queue Overrides Table
-- --------------------------------------------
sapIngQosHsmdaQueueTable OBJECT-TYPE
    SYNTAX      SEQUENCE OF SapIngQosHsmdaQueueEntry 
    MAX-ACCESS  not-accessible
    STATUS      obsolete
    DESCRIPTION
        "The sapIngQosHsmdaQueueTable has an entry for each Hsmda 
         SAP-level ingress queue override configured on the system.

         This table is obsoleted in 10.0 release."
    ::= { tmnxSapObjs 52 }

sapIngQosHsmdaQueueEntry     OBJECT-TYPE
    SYNTAX      SapIngQosHsmdaQueueEntry 
    MAX-ACCESS  not-accessible
    STATUS      obsolete
    DESCRIPTION
        "Each row entry represents a Hsmda SAP-level ingress queue
         override record.

         Entries are created and deleted via SNMP SET operations on
         sapIngQosHsmdaQueueRowStatus."
    INDEX { svcId, sapPortId, sapEncapValue, sapIngQosHsmdaQueueId }
    ::= { sapIngQosHsmdaQueueTable 1}

SapIngQosHsmdaQueueEntry  ::= SEQUENCE
    {
        sapIngQosHsmdaQueueId           TIngressHsmdaQueueId,
        sapIngQosHsmdaQueueRowStatus    RowStatus,
        sapIngQosHsmdaQueueLastChanged  TimeStamp,
        sapIngQosHsmdaQueueAdminPIR     THsmdaPIRKRateOverride,
        sapIngQosHsmdaQueueAdminCIR     THsmdaCIRKRateOverride,
        sapIngQosHsmdaQueueSlopePolicy  TNamedItemOrEmpty
    }

sapIngQosHsmdaQueueId        OBJECT-TYPE
    SYNTAX      TIngressHsmdaQueueId
    MAX-ACCESS  not-accessible
    STATUS      obsolete
    DESCRIPTION
        "The value of sapIngQosHsmdaQueueId index specifies the Hsmda
         egress queue which this override record will affect."
    ::= { sapIngQosHsmdaQueueEntry 1 }

sapIngQosHsmdaQueueRowStatus        OBJECT-TYPE
    SYNTAX      RowStatus
    MAX-ACCESS  read-create
    STATUS      obsolete
    DESCRIPTION
        "The value of sapIngQosHsmdaQueueRowStatus specifies..."
    ::= { sapIngQosHsmdaQueueEntry 2 }

sapIngQosHsmdaQueueLastChanged        OBJECT-TYPE
    SYNTAX      TimeStamp
    MAX-ACCESS  read-only
    STATUS      obsolete
    DESCRIPTION
        "The value of sapIngQosHsmdaQueueLastChanged indicates the sysUpTime
         at the time of the most recent management-initiated change to this
         table row."
    ::= { sapIngQosHsmdaQueueEntry 3 }

sapIngQosHsmdaQueueAdminPIR        OBJECT-TYPE
    SYNTAX      THsmdaPIRKRateOverride
    UNITS       "kbps"
    MAX-ACCESS  read-create
    STATUS      obsolete
    DESCRIPTION
        "The value of sapIngQosHsmdaQueueAdminPIR specifies the PIR rate in kbps
         allowed for this Hsmda ingress queue."
    DEFVAL { -2 }
    ::= { sapIngQosHsmdaQueueEntry 4 }

sapIngQosHsmdaQueueAdminCIR        OBJECT-TYPE
    SYNTAX      THsmdaCIRKRateOverride
    UNITS       "kbps"
    MAX-ACCESS  read-create
    STATUS      obsolete
    DESCRIPTION
        "The value of sapIngQosHsmdaQueueAdminCIR specifies the CIR rate in kbps
         allowed for this Hsmda ingress queue."
    DEFVAL { -2 }
    ::= { sapIngQosHsmdaQueueEntry 5 }

sapIngQosHsmdaQueueSlopePolicy        OBJECT-TYPE
    SYNTAX      TNamedItemOrEmpty
    MAX-ACCESS  read-create
    STATUS      obsolete
    DESCRIPTION
        "The value of sapIngQosHsmdaQueueSlopePolicy specifies the slope
         policy that defines the RED slopes for this Hsmda ingress queue."
    DEFVAL { "" }
    ::= { sapIngQosHsmdaQueueEntry 6 }

------------------------------------------------
-- Ingress QoS HSMDA Queue SAP Statistics Table
------------------------------------------------
sapIngQosHsmdaQueueStatsTable OBJECT-TYPE
    SYNTAX          SEQUENCE OF SapIngQosHsmdaQueueStatsEntry
    MAX-ACCESS      not-accessible
    STATUS          obsolete
    DESCRIPTION
        "A table that contains ingress QoS HSMDA queue SAP statistics.

         This table is obsoleted in 10.0 release."
    ::= { tmnxSapObjs 53 }

sapIngQosHsmdaQueueStatsEntry OBJECT-TYPE
    SYNTAX          SapIngQosHsmdaQueueStatsEntry
    MAX-ACCESS      not-accessible
    STATUS          obsolete
    DESCRIPTION
        "Ingress statistics about a specific SAP's QoS HSMDA queue."
    INDEX           { svcId, sapPortId, sapEncapValue, sapIngQosHsmdaQueueId }
    ::= { sapIngQosHsmdaQueueStatsTable 1 }

SapIngQosHsmdaQueueStatsEntry ::= SEQUENCE {
        sapIngHsmdaQStatCustId             TmnxCustId,
        sapIngHsmdaQStatHiPktsDropped      Counter64,
        sapIngHsmdaQStatLoPktsDropped      Counter64,
        sapIngHsmdaQStatHiOctsDropped      Counter64,
        sapIngHsmdaQStatLoOctsDropped      Counter64,
        sapIngHsmdaQStatInProfPktsFwd      Counter64,
        sapIngHsmdaQStatOutProfPktsFwd     Counter64,
        sapIngHsmdaQStatInProfOctsFwd      Counter64,
        sapIngHsmdaQStatOutProfOctsFwd     Counter64,
        sapIngHsmdaQStatAllPktsOffered     Counter64,
        sapIngHsmdaQStatAllOctsOffered     Counter64
    }

sapIngHsmdaQStatCustId  OBJECT-TYPE
    SYNTAX          TmnxCustId
    MAX-ACCESS      read-only
    STATUS          obsolete
    DESCRIPTION
        "The value of sapIngHsmdaQStatCustId indicates the customer ID
         for the statistics."
    ::= { sapIngQosHsmdaQueueStatsEntry 1 }

sapIngHsmdaQStatHiPktsDropped        OBJECT-TYPE
    SYNTAX      Counter64
    MAX-ACCESS  read-only
    STATUS      obsolete
    DESCRIPTION
        "The value of sapIngHsmdaQStatHiPktsDropped indicates the
         number of high-priority packets dropped on ingress on
         this SAP."
    ::= { sapIngQosHsmdaQueueStatsEntry 2 }

sapIngHsmdaQStatLoPktsDropped        OBJECT-TYPE
    SYNTAX      Counter64
    MAX-ACCESS  read-only
    STATUS      obsolete
    DESCRIPTION
        "The value of sapIngHsmdaQStatLoPktsDropped indicates the
         number of low-priority packets dropped on ingress on
         this SAP."
    ::= { sapIngQosHsmdaQueueStatsEntry 3 }

sapIngHsmdaQStatHiOctsDropped        OBJECT-TYPE
    SYNTAX      Counter64
    MAX-ACCESS  read-only
    STATUS      obsolete
    DESCRIPTION
        "The value of sapIngHsmdaQStatHiOctsDropped indicates the
         number of high-priority octets dropped on ingress on
         this SAP."
    ::= { sapIngQosHsmdaQueueStatsEntry 4 }

sapIngHsmdaQStatLoOctsDropped        OBJECT-TYPE
    SYNTAX      Counter64
    MAX-ACCESS  read-only
    STATUS      obsolete
    DESCRIPTION
        "The value of sapIngHsmdaQStatLoOctsDropped indicates the
         number of low-priority octets dropped on ingress on
         this SAP."
    ::= { sapIngQosHsmdaQueueStatsEntry 5 }

sapIngHsmdaQStatInProfPktsFwd        OBJECT-TYPE
    SYNTAX      Counter64
    MAX-ACCESS  read-only
    STATUS      obsolete
    DESCRIPTION
        "The value of sapIngHsmdaQStatInProfPktsFwd indicates the
         number of in-profile packets forwarded on ingress on
         this SAP."
    ::= { sapIngQosHsmdaQueueStatsEntry 6 }

sapIngHsmdaQStatOutProfPktsFwd        OBJECT-TYPE
    SYNTAX      Counter64
    MAX-ACCESS  read-only
    STATUS      obsolete
    DESCRIPTION
        "The value of sapIngHsmdaQStatOutProfPktsFwd indicates the
         number of out-of-profile packets forwarded on ingress on
         this SAP."
    ::= { sapIngQosHsmdaQueueStatsEntry 7 }

sapIngHsmdaQStatInProfOctsFwd        OBJECT-TYPE
    SYNTAX      Counter64
    MAX-ACCESS  read-only
    STATUS      obsolete
    DESCRIPTION
        "The value of sapIngHsmdaQStatInProfOctsFwd indicates the
         number of out-of-profile packets forwarded on ingress on
         this SAP."
    ::= { sapIngQosHsmdaQueueStatsEntry 8 }

sapIngHsmdaQStatOutProfOctsFwd        OBJECT-TYPE
    SYNTAX      Counter64
    MAX-ACCESS  read-only
    STATUS      obsolete
    DESCRIPTION
        "The value of sapIngHsmdaQStatOutProfOctsFwd indicates the
         number of out-of-profile packets forwarded on ingress on
         this SAP."
    ::= { sapIngQosHsmdaQueueStatsEntry 9 }

sapIngHsmdaQStatAllPktsOffered        OBJECT-TYPE
    SYNTAX      Counter64
    MAX-ACCESS  read-only
    STATUS      obsolete
    DESCRIPTION
        "The value of sapIngHsmdaQStatAllPktsOffered indicates the
         total number of packets offered on ingress on this SAP."
    ::= { sapIngQosHsmdaQueueStatsEntry 10 }

sapIngHsmdaQStatAllOctsOffered        OBJECT-TYPE
    SYNTAX      Counter64
    MAX-ACCESS  read-only
    STATUS      obsolete
    DESCRIPTION
        "The value of sapIngHsmdaQStatAllOctsOffered indicates the
         total number of octets offered on ingress on this SAP."
    ::= { sapIngQosHsmdaQueueStatsEntry 11 }

------------------------------------------------------
-- Ingress QoS HSMDA Queue Counter SAP Statistics Table
------------------------------------------------------
sapIngQosHsmdaCntrStatsTable OBJECT-TYPE
    SYNTAX          SEQUENCE OF SapIngQosHsmdaCntrStatsEntry
    MAX-ACCESS      not-accessible
    STATUS          obsolete
    DESCRIPTION
        "A table that contains ingress QoS HSMDA counter SAP statistics.

         This table is obsoleted in 10.0 release."
    ::= { tmnxSapObjs 54 }

sapIngQosHsmdaCntrStatsEntry OBJECT-TYPE
    SYNTAX          SapIngQosHsmdaCntrStatsEntry
    MAX-ACCESS      not-accessible
    STATUS          obsolete
    DESCRIPTION
        "Ingress statistics about a specific SAP's QoS HSMDA counter."
    INDEX           { svcId, sapPortId, sapEncapValue, sapIngHsmdaCntrStCntrId }
    ::= { sapIngQosHsmdaCntrStatsTable 1 }

SapIngQosHsmdaCntrStatsEntry ::= SEQUENCE {
        sapIngHsmdaCntrStCntrId             TIngressHsmdaCounterId,
        sapIngHsmdaCntrStCustId             TmnxCustId,
        sapIngHsmdaCntrStHiPktDrop      Counter64,
        sapIngHsmdaCntrStLoPktDrop      Counter64,
        sapIngHsmdaCntrStHiOctDrop      Counter64,
        sapIngHsmdaCntrStLoOctDrop      Counter64,
        sapIngHsmdaCntrStInProfPktFwd      Counter64,
        sapIngHsmdaCntrStOutProfPktFwd     Counter64,
        sapIngHsmdaCntrStInProfOctFwd      Counter64,
        sapIngHsmdaCntrStOutProfOctFwd     Counter64,
        sapIngHsmdaCntrStAllPktOffered     Counter64,
        sapIngHsmdaCntrStAllOctOffered     Counter64
    }

sapIngHsmdaCntrStCntrId  OBJECT-TYPE
    SYNTAX          TIngressHsmdaCounterId
    MAX-ACCESS      not-accessible
    STATUS          obsolete
    DESCRIPTION
        "The value of sapIngHsmdaCntrStCntrId indicates the counter ID
         for the statistics."
    ::= { sapIngQosHsmdaCntrStatsEntry 1 }

sapIngHsmdaCntrStCustId  OBJECT-TYPE
    SYNTAX          TmnxCustId
    MAX-ACCESS      read-only
    STATUS          obsolete
    DESCRIPTION
        "The value of sapIngHsmdaCntrStCustId indicates the customer ID
         for the statistics."
    ::= { sapIngQosHsmdaCntrStatsEntry 2 }

sapIngHsmdaCntrStHiPktDrop        OBJECT-TYPE
    SYNTAX      Counter64
    MAX-ACCESS  read-only
    STATUS      obsolete
    DESCRIPTION
        "The value of sapIngHsmdaCntrStHiPktDrop indicates the
         number of high-priority packets dropped for the ingress
         counter, specified by the index sapIngHsmdaCntrStCntrId, 
         on this SAP."
    ::= { sapIngQosHsmdaCntrStatsEntry 3 }

sapIngHsmdaCntrStLoPktDrop        OBJECT-TYPE
    SYNTAX      Counter64
    MAX-ACCESS  read-only
    STATUS      obsolete
    DESCRIPTION
        "The value of sapIngHsmdaCntrStLoPktDrop indicates the
         number of low-priority packets dropped for the ingress
         counter, specified by the index sapIngHsmdaCntrStCntrId, 
         on this SAP."
    ::= { sapIngQosHsmdaCntrStatsEntry 4 }

sapIngHsmdaCntrStHiOctDrop        OBJECT-TYPE
    SYNTAX      Counter64
    MAX-ACCESS  read-only
    STATUS      obsolete
    DESCRIPTION
        "The value of sapIngHsmdaCntrStHiOctDrop indicates the
         number of high-priority octets dropped for the ingress
         counter, specified by the index sapIngHsmdaCntrStCntrId, 
         on this SAP."
    ::= { sapIngQosHsmdaCntrStatsEntry 5 }

sapIngHsmdaCntrStLoOctDrop        OBJECT-TYPE
    SYNTAX      Counter64
    MAX-ACCESS  read-only
    STATUS      obsolete
    DESCRIPTION
        "The value of sapIngHsmdaCntrStLoOctDrop indicates the
         number of low-priority octets dropped for the ingress
         counter, specified by the index sapIngHsmdaCntrStCntrId, 
         on this SAP."
    ::= { sapIngQosHsmdaCntrStatsEntry 6 }

sapIngHsmdaCntrStInProfPktFwd        OBJECT-TYPE
    SYNTAX      Counter64
    MAX-ACCESS  read-only
    STATUS      obsolete
    DESCRIPTION
        "The value of sapIngHsmdaCntrStInProfPktFwd indicates the
         number of in-profile packets forwarded for the ingress
         counter, specified by the index sapIngHsmdaCntrStCntrId, 
         on this SAP."
    ::= { sapIngQosHsmdaCntrStatsEntry 7 }

sapIngHsmdaCntrStOutProfPktFwd        OBJECT-TYPE
    SYNTAX      Counter64
    MAX-ACCESS  read-only
    STATUS      obsolete
    DESCRIPTION
        "The value of sapIngHsmdaCntrStOutProfPktFwd indicates the
         number of out-of-profile packets forwarded for the ingress
         counter, specified by the index sapIngHsmdaCntrStCntrId, 
         on this SAP."
    ::= { sapIngQosHsmdaCntrStatsEntry 8 }

sapIngHsmdaCntrStInProfOctFwd        OBJECT-TYPE
    SYNTAX      Counter64
    MAX-ACCESS  read-only
    STATUS      obsolete
    DESCRIPTION
        "The value of sapIngHsmdaCntrStInProfOctFwd indicates the
         number of out-of-profile packets forwarded for the ingress
         counter, specified by the index sapIngHsmdaCntrStCntrId, 
         on this SAP."
    ::= { sapIngQosHsmdaCntrStatsEntry 9 }

sapIngHsmdaCntrStOutProfOctFwd        OBJECT-TYPE
    SYNTAX      Counter64
    MAX-ACCESS  read-only
    STATUS      obsolete
    DESCRIPTION
        "The value of sapIngHsmdaCntrStOutProfOctFwd indicates the
         number of out-of-profile packets forwarded for the ingress 
         counter, specified by the index sapIngHsmdaCntrStCntrId, 
         on this SAP."
    ::= { sapIngQosHsmdaCntrStatsEntry 10 }

sapIngHsmdaCntrStAllPktOffered        OBJECT-TYPE
    SYNTAX      Counter64
    MAX-ACCESS  read-only
    STATUS      obsolete
    DESCRIPTION
        "The value of sapIngHsmdaCntrStAllPktOffered indicates the
         total number of packets offered on ingress on this SAP."
    ::= { sapIngQosHsmdaCntrStatsEntry 11 }

sapIngHsmdaCntrStAllOctOffered        OBJECT-TYPE
    SYNTAX      Counter64
    MAX-ACCESS  read-only
    STATUS      obsolete
    DESCRIPTION
        "The value of sapIngHsmdaCntrStAllOctOffered indicates the
         total number of octets offered on ingress on this SAP."
    ::= { sapIngQosHsmdaCntrStatsEntry 12 }


-- --------------------------------------------
-- SAP HSMDA QOS Egress Queue Overrides Table
-- --------------------------------------------

sapEgrQosHsmdaQueueTable OBJECT-TYPE
    SYNTAX      SEQUENCE OF SapEgrQosHsmdaQueueEntry 
    MAX-ACCESS  not-accessible
    STATUS      current
    DESCRIPTION
        "The sapEgrQosHsmdaQueueTable has an entry for each Hsmda 
         SAP-level egress queue override configured on the system."
    ::= { tmnxSapObjs 55 }

sapEgrQosHsmdaQueueEntry     OBJECT-TYPE
    SYNTAX      SapEgrQosHsmdaQueueEntry 
    MAX-ACCESS  not-accessible
    STATUS      current
    DESCRIPTION
        "Each row entry represents a Hsmda SAP-level egress queue
         override record.

         Entries are created and deleted via SNMP SET operations on
         sapEgrQosHsmdaQueueRowStatus."
    INDEX { svcId, sapPortId, sapEncapValue, sapEgrQosHsmdaQueueId }
    ::= { sapEgrQosHsmdaQueueTable 1}

SapEgrQosHsmdaQueueEntry  ::= SEQUENCE
    {
        sapEgrQosHsmdaQueueId           TEgressHsmdaQueueId,
        sapEgrQosHsmdaQueueRowStatus    RowStatus,
        sapEgrQosHsmdaQueueLastChanged  TimeStamp,
        sapEgrQosHsmdaQueueAdminPIR     THsmdaPIRKRateOverride,
        sapEgrQosHsmdaQueueAdminCIR     THsmdaCIRKRateOverride,
        sapEgrQosHsmdaQueueSlopePolicy  TNamedItemOrEmpty,
        sapEgrQosHsmdaQueueWrrWeight    THsmdaWrrWeightOverride,
        sapEgrQosHsmdaQueueMBS          THSMDABurstSizeBytesOverride

    }

sapEgrQosHsmdaQueueId        OBJECT-TYPE
    SYNTAX      TEgressHsmdaQueueId
    MAX-ACCESS  not-accessible
    STATUS      current
    DESCRIPTION
         "The value of sapEgrQosHsmdaQueueId index specifies the Hsmda
          egress queue which this override record will affect."
    ::= { sapEgrQosHsmdaQueueEntry 1 }

sapEgrQosHsmdaQueueRowStatus        OBJECT-TYPE
    SYNTAX      RowStatus
    MAX-ACCESS  read-create
    STATUS      current
    DESCRIPTION
        "The value of sapEgrQosHsmdaQueueRowStatus controls the creation
         and deletion of rows in this table."
    ::= { sapEgrQosHsmdaQueueEntry 2 }

sapEgrQosHsmdaQueueLastChanged        OBJECT-TYPE
    SYNTAX      TimeStamp
    MAX-ACCESS  read-only
    STATUS      current
    DESCRIPTION
        "The value of sapEgrQosHsmdaQueueLastChanged indicates the sysUpTime
         at the time of the most recent management-initiated change to this
         table row."
    ::= { sapEgrQosHsmdaQueueEntry 3 }

sapEgrQosHsmdaQueueAdminPIR        OBJECT-TYPE
    SYNTAX      THsmdaPIRKRateOverride
    UNITS       "kbps"
    MAX-ACCESS  read-create
    STATUS      current
    DESCRIPTION
        "The value of sapEgrQosHsmdaQueueAdminPIR specifies the PIR rate in kbps
         allowed for this Hsmda ingress queue."
    DEFVAL { -2 }
    ::= { sapEgrQosHsmdaQueueEntry 4 }

sapEgrQosHsmdaQueueAdminCIR        OBJECT-TYPE
    SYNTAX      THsmdaCIRKRateOverride
    UNITS       "kbps"
    MAX-ACCESS  read-create
    STATUS      obsolete
    DESCRIPTION
        "The value of sapEgrQosHsmdaQueueAdminCIR specifies the CIR rate in kbps
         allowed for this Hsmda ingress queue.

         This object is obsoleted in 10.0 Release." 
    DEFVAL { -2 }
    ::= { sapEgrQosHsmdaQueueEntry 5 }

sapEgrQosHsmdaQueueSlopePolicy        OBJECT-TYPE
    SYNTAX      TNamedItemOrEmpty
    MAX-ACCESS  read-create
    STATUS      current
    DESCRIPTION
        "The value of sapEgrQosHsmdaQueueSlopePolicy specifies the slope
         policy that defines the RED slopes for this Hsmda ingress queue."
    DEFVAL { "" }
    ::= { sapEgrQosHsmdaQueueEntry 6 }

sapEgrQosHsmdaQueueWrrWeight        OBJECT-TYPE
    SYNTAX      THsmdaWrrWeightOverride
    MAX-ACCESS  read-create
    STATUS      current
    DESCRIPTION
        "The value of sapEgrQosHsmdaQueueWrrWeight specifies the weighted 
         round-robin weight override for the given egress hsmda queue on this
         SAP. When set to default value, the weighted round-robin weight is not 
         overridden and the weighted round-robin weight from the sap-egress qos
         policy is honored.  When a non-default value is given, that is used 
         instead of the weighted round-robin weight given in the sap-egress
         policy."
    DEFVAL { -2 }
    ::= { sapEgrQosHsmdaQueueEntry 7 }

sapEgrQosHsmdaQueueMBS        OBJECT-TYPE
    SYNTAX      THSMDABurstSizeBytesOverride
    UNITS       "bytes"
    MAX-ACCESS  read-create
    STATUS      current
    DESCRIPTION
        "The value of sapEgrQosHsmdaQueueMBS specifies the maximum buffer space 
         (MBS) override in bytes for the given egress hsmda queue on this SAP. 
         When set to default value, the MBS is not overridden and the MBS from 
         the sap-egress qos policy is honored. When a non-default value is 
         given, that is used instead of the MBS given in the sap-egress policy."
    DEFVAL { -2 }
    ::= { sapEgrQosHsmdaQueueEntry 8 }

------------------------------------------------
-- Egress QoS HSMDA Queue SAP Statistics Table
------------------------------------------------
sapEgrQosHsmdaQueueStatsTable OBJECT-TYPE
    SYNTAX          SEQUENCE OF SapEgrQosHsmdaQueueStatsEntry
    MAX-ACCESS      not-accessible
    STATUS          current
    DESCRIPTION
        "A table that contains egress QoS HSMDA queue SAP statistics."
    ::= { tmnxSapObjs 56 }

sapEgrQosHsmdaQueueStatsEntry OBJECT-TYPE
    SYNTAX          SapEgrQosHsmdaQueueStatsEntry
    MAX-ACCESS      not-accessible
    STATUS          current
    DESCRIPTION
        "Egress statistics about a specific SAP's QoS HSMDA queue."
    INDEX           { svcId, sapPortId, sapEncapValue, sapEgrQosHsmdaQueueId }
    ::= { sapEgrQosHsmdaQueueStatsTable 1 }

SapEgrQosHsmdaQueueStatsEntry ::= SEQUENCE {
        sapEgrHsmdaQStatCustId             TmnxCustId,
        sapEgrHsmdaQStatInProfPktFwd      Counter64,
        sapEgrHsmdaQStatInProfPktDropd    Counter64,
        sapEgrHsmdaQStatOutProfPktFwd     Counter64,
        sapEgrHsmdaQStatOutProfPktDropd   Counter64,
        sapEgrHsmdaQStatInProfOctFwd      Counter64,
        sapEgrHsmdaQStatInProfOctDropd    Counter64,
        sapEgrHsmdaQStatOutProfOctFwd     Counter64,
        sapEgrHsmdaQStatOutProfOctDropd   Counter64
    }

sapEgrHsmdaQStatCustId  OBJECT-TYPE
    SYNTAX          TmnxCustId
    MAX-ACCESS      read-only
    STATUS          current
    DESCRIPTION     
        "The value of sapEgrHsmdaQStatCustId indicates the
        customer ID for the statistics."
    ::= { sapEgrQosHsmdaQueueStatsEntry 1 }

sapEgrHsmdaQStatInProfPktFwd        OBJECT-TYPE
    SYNTAX      Counter64
    MAX-ACCESS  read-only
    STATUS      current
    DESCRIPTION
        "The value of sapEgrHsmdaQStatInProfPktFwd indicates the
         number of in-profile packets forwarded on egress on
         this SAP."
    ::= { sapEgrQosHsmdaQueueStatsEntry 2 }

sapEgrHsmdaQStatInProfPktDropd        OBJECT-TYPE
    SYNTAX      Counter64
    MAX-ACCESS  read-only
    STATUS      current
    DESCRIPTION
        "The value of sapEgrHsmdaQStatInProfPktDropd indicates the
         number of in-profile packets dropped on egress on
         this SAP."
    ::= { sapEgrQosHsmdaQueueStatsEntry 3 }

sapEgrHsmdaQStatOutProfPktFwd        OBJECT-TYPE
    SYNTAX      Counter64
    MAX-ACCESS  read-only
    STATUS      current
    DESCRIPTION
        "The value of sapEgrHsmdaQStatOutProfPktFwd indicates the
         number of out-of-profile packets forwarded on egress on
         this SAP."
    ::= { sapEgrQosHsmdaQueueStatsEntry 4 }

sapEgrHsmdaQStatOutProfPktDropd        OBJECT-TYPE
    SYNTAX      Counter64
    MAX-ACCESS  read-only
    STATUS      current
    DESCRIPTION
        "The value of sapEgrHsmdaQStatOutProfPktDropd indicates the
         number of out-of-profile packets dropped on egress on
         this SAP."
    ::= { sapEgrQosHsmdaQueueStatsEntry 5 }

sapEgrHsmdaQStatInProfOctFwd        OBJECT-TYPE
    SYNTAX      Counter64
    MAX-ACCESS  read-only
    STATUS      current
    DESCRIPTION
        "The value of sapEgrHsmdaQStatInProfOctFwd indicates the
         number of out-of-profile packets forwarded on egress on
         this SAP."
    ::= { sapEgrQosHsmdaQueueStatsEntry 6 }

sapEgrHsmdaQStatInProfOctDropd        OBJECT-TYPE
    SYNTAX      Counter64
    MAX-ACCESS  read-only
    STATUS      current
    DESCRIPTION
        "The value of sapEgrHsmdaQStatInProfOctDropd indicates the
         number of out-of-profile packets dropped on egress on
         this SAP."
    ::= { sapEgrQosHsmdaQueueStatsEntry 7 }

sapEgrHsmdaQStatOutProfOctFwd        OBJECT-TYPE
    SYNTAX      Counter64
    MAX-ACCESS  read-only
    STATUS      current
    DESCRIPTION
        "The value of sapEgrHsmdaQStatOutProfOctFwd indicates the
         number of out-of-profile packets forwarded on egress on
         this SAP."
    ::= { sapEgrQosHsmdaQueueStatsEntry 8 }

sapEgrHsmdaQStatOutProfOctDropd        OBJECT-TYPE
    SYNTAX      Counter64
    MAX-ACCESS  read-only
    STATUS      current
    DESCRIPTION
        "The value of sapEgrHsmdaQStatOutProfOctDropd indicates the
         number of out-of-profile packets dropped on egress on
         this SAP."
    ::= { sapEgrQosHsmdaQueueStatsEntry 9 }

------------------------------------------------------
-- Egress QoS HSMDA Queue Counter SAP Statistics Table
------------------------------------------------------
sapEgrQosHsmdaCntrStatsTable OBJECT-TYPE
    SYNTAX          SEQUENCE OF SapEgrQosHsmdaCntrStatsEntry
    MAX-ACCESS      not-accessible
    STATUS          current
    DESCRIPTION
        "A table that contains egress QoS HSMDA counter SAP statistics."
    ::= { tmnxSapObjs 57 }

sapEgrQosHsmdaCntrStatsEntry OBJECT-TYPE
    SYNTAX          SapEgrQosHsmdaCntrStatsEntry
    MAX-ACCESS      not-accessible
    STATUS          current
    DESCRIPTION
        "Egress statistics about a specific SAP's QoS HSMDA counter."
    INDEX           { svcId, sapPortId, sapEncapValue, sapEgrHsmdaCntrStCntrId }
    ::= { sapEgrQosHsmdaCntrStatsTable 1 }

SapEgrQosHsmdaCntrStatsEntry ::= SEQUENCE {
        sapEgrHsmdaCntrStCntrId             TEgressHsmdaCounterId,
        sapEgrHsmdaCntrStCustId             TmnxCustId,
        sapEgrHsmdaCntrStInProfPktFwd      Counter64,
        sapEgrHsmdaCntrStInProfPktDrop    Counter64,
        sapEgrHsmdaCntrStOutProfPktFwd     Counter64,
        sapEgrHsmdaCntrStOutProfPktDrop   Counter64,
        sapEgrHsmdaCntrStInProfOctFwd      Counter64,
        sapEgrHsmdaCntrStInProfOctDrop    Counter64,
        sapEgrHsmdaCntrStOutProfOctFwd     Counter64,
        sapEgrHsmdaCntrStOutProfOctDrop   Counter64
    }

sapEgrHsmdaCntrStCntrId  OBJECT-TYPE
    SYNTAX          TEgressHsmdaCounterId
    MAX-ACCESS      not-accessible
    STATUS          current
    DESCRIPTION
        "The value of sapEgrHsmdaCntrStCntrId indicates the counter ID
         for the statistics."
    ::= { sapEgrQosHsmdaCntrStatsEntry 1 }

sapEgrHsmdaCntrStCustId  OBJECT-TYPE
    SYNTAX          TmnxCustId
    MAX-ACCESS      read-only
    STATUS          current
    DESCRIPTION
        "The value of sapEgrHsmdaCntrStCustId indicates the customer ID
         for the statistics."
    ::= { sapEgrQosHsmdaCntrStatsEntry 2 }

sapEgrHsmdaCntrStInProfPktFwd        OBJECT-TYPE
    SYNTAX      Counter64
    MAX-ACCESS  read-only
    STATUS      current
    DESCRIPTION
        "The value of sapEgrHsmdaCntrStInProfPktFwd indicates the
         number of in-profile packets forwarded for the egress
         counter, specified by the index sapIngHsmdaCntrStCntrId,
         on this SAP."
    ::= { sapEgrQosHsmdaCntrStatsEntry 3 }

sapEgrHsmdaCntrStInProfPktDrop        OBJECT-TYPE
    SYNTAX      Counter64
    MAX-ACCESS  read-only
    STATUS      current
    DESCRIPTION
        "The value of sapEgrHsmdaCntrStInProfPktDrop indicates the
         number of in-profile packets dropped for the egress
         counter, specified by the index sapIngHsmdaCntrStCntrId,
         on this SAP."
    ::= { sapEgrQosHsmdaCntrStatsEntry 4 }

sapEgrHsmdaCntrStOutProfPktFwd        OBJECT-TYPE
    SYNTAX      Counter64
    MAX-ACCESS  read-only
    STATUS      current
    DESCRIPTION
        "The value of sapEgrHsmdaCntrStOutProfPktFwd indicates the
         number of out-of-profile packets forwarded for the egress
         counter, specified by the index sapIngHsmdaCntrStCntrId,
         on this SAP."
    ::= { sapEgrQosHsmdaCntrStatsEntry 5 }

sapEgrHsmdaCntrStOutProfPktDrop        OBJECT-TYPE
    SYNTAX      Counter64
    MAX-ACCESS  read-only
    STATUS      current
    DESCRIPTION
        "The value of sapEgrHsmdaCntrStOutProfPktDrop indicates the
         number of out-of-profile packets dropped for the egress
         counter, specified by the index sapIngHsmdaCntrStCntrId,
         on this SAP."
    ::= { sapEgrQosHsmdaCntrStatsEntry 6 }

sapEgrHsmdaCntrStInProfOctFwd        OBJECT-TYPE
    SYNTAX      Counter64
    MAX-ACCESS  read-only
    STATUS      current
    DESCRIPTION
        "The value of sapEgrHsmdaCntrStInProfOctFwd indicates the
         number of out-of-profile packets forwarded for the egress
         counter, specified by the index sapIngHsmdaCntrStCntrId,
         on this SAP."
    ::= { sapEgrQosHsmdaCntrStatsEntry 7 }

sapEgrHsmdaCntrStInProfOctDrop        OBJECT-TYPE
    SYNTAX      Counter64
    MAX-ACCESS  read-only
    STATUS      current
    DESCRIPTION
        "The value of sapEgrHsmdaCntrStInProfOctDrop indicates the
         number of out-of-profile packets dropped for the egress
         counter, specified by the index sapIngHsmdaCntrStCntrId,
         on this SAP."
    ::= { sapEgrQosHsmdaCntrStatsEntry 8 }

sapEgrHsmdaCntrStOutProfOctFwd        OBJECT-TYPE
    SYNTAX      Counter64
    MAX-ACCESS  read-only
    STATUS      current
    DESCRIPTION
        "The value of sapEgrHsmdaCntrStOutProfOctFwd indicates the
         number of out-of-profile packets forwarded for the egress
         counter, specified by the index sapIngHsmdaCntrStCntrId,
         on this SAP."
    ::= { sapEgrQosHsmdaCntrStatsEntry 9 }

sapEgrHsmdaCntrStOutProfOctDrop        OBJECT-TYPE
    SYNTAX      Counter64
    MAX-ACCESS  read-only
    STATUS      current
    DESCRIPTION
        "The value of sapEgrHsmdaCntrStOutProfOctDrop indicates the
         number of out-of-profile packets dropped for the egress
         counter, specified by the index sapIngHsmdaCntrStCntrId,
         on this SAP."
    ::= { sapEgrQosHsmdaCntrStatsEntry 10 }

-- --------------------------------------------------------
-- msapL3PlcyTable
-- --------------------------------------------------------
msapL3PlcyTable OBJECT-TYPE
    SYNTAX      SEQUENCE OF MsapL3PlcyEntry
    MAX-ACCESS  not-accessible
    STATUS      current
    DESCRIPTION
        "The msapL3PlcyTable has an entry for each managed SAP (MSAP)
         policy configured in the system."
    ::= { tmnxSapObjs 58 }

msapL3PlcyEntry    OBJECT-TYPE
    SYNTAX      MsapL3PlcyEntry
    MAX-ACCESS  not-accessible
    STATUS      current
    DESCRIPTION
        "Each entry represents the L3-related configuration for a managed
         SAP (MSAP) policy."
    AUGMENTS { msapPlcyEntry }
    ::= { msapL3PlcyTable 1}

MsapL3PlcyEntry ::= SEQUENCE
    {
        msapL3PlcyLastChanged         TimeStamp,
        msapL3PlcyAntiSpoof           INTEGER,
        msapL3PlcyIngQosPolicyId      TSapIngressPolicyID,
        msapL3PlcyIngQosQueueingType  INTEGER
    }

msapL3PlcyLastChanged        OBJECT-TYPE
    SYNTAX      TimeStamp
    MAX-ACCESS  read-only
    STATUS      current
    DESCRIPTION
        "The value of msapL3PlcyLastChanged indicates the sysUpTime
         at the time of the last modification of this entry.

         If no changes were made to the entry since the last
         re-initialization of the local network management subsystem,
         then this object contains a zero value."
    ::= { msapL3PlcyEntry 1 }

msapL3PlcyAntiSpoof        OBJECT-TYPE
    SYNTAX          INTEGER {
                        sourceIpAndMacAddr  (3),
                        nextHopIpAndMacAddr (4)
                    }
    MAX-ACCESS      read-create
    STATUS          current
    DESCRIPTION     "The value of the object msapL3PlcyAntiSpoof specifies
                     the type of anti-spoof filtering applicable on this MSAP."
    DEFVAL { sourceIpAndMacAddr }
    ::= { msapL3PlcyEntry 2 }

msapL3PlcyIngQosPolicyId OBJECT-TYPE
    SYNTAX          TSapIngressPolicyID (1)
    MAX-ACCESS      read-create
    STATUS          current
    DESCRIPTION
        "The value of msapL3PlcyIngQosPolicyId specifies the ingress QoS
         policy applicable to this MSAP policy in IES/VPRN (L3) services. The
         corresponding policy is defined in TIMETRA-QOS-MIB::tSapIngressTable."
    DEFVAL { 1 }
    ::= { msapL3PlcyEntry 3 }

msapL3PlcyIngQosQueueingType OBJECT-TYPE
    SYNTAX          INTEGER {
                        sharedQueueing      (1),
                        serviceQueueing     (2)
                    }
    MAX-ACCESS      read-create
    STATUS          current
    DESCRIPTION
        "The value of msapL3PlcyIngQosQueueingType specifies the ingress
         queueing type applicable to this MSAP policy in IES/VPRN (L3)
         services."
    DEFVAL { sharedQueueing }
    ::= { msapL3PlcyEntry 4 }

-- --------------------------------------
-- TblLastChgd objects for msap tables
-- --------------------------------------

msapPlcyTblLastChgd  OBJECT-TYPE
    SYNTAX          TimeStamp
    MAX-ACCESS      read-only
    STATUS          current
    DESCRIPTION     "The value of msapPlcyTblLastChgd indicates the
                     sysUpTime at the time of the last modification of
                     msapPlcyTable.

                     If no changes were made to the entry since the last
                     re-initialization of the local network management subsystem,
                     then this object contains a zero value."
    ::= { tmnxSapObjs 59 }

msapTlsPlcyTblLastChgd  OBJECT-TYPE
    SYNTAX          TimeStamp
    MAX-ACCESS      read-only
    STATUS          current
    DESCRIPTION     "The value of msapTlsPlcyTblLastChgd indicates the
                     sysUpTime at the time of the last modification of
                     msapTlsPlcyTable.

                     If no changes were made to the entry since the last
                     re-initialization of the local network management subsystem,
                     then this object contains a zero value."
    ::= { tmnxSapObjs 60 }

msapIgmpSnpgMcacLvlTblLastChgd  OBJECT-TYPE
    SYNTAX          TimeStamp
    MAX-ACCESS      read-only
    STATUS          current
    DESCRIPTION     "The value of msapIgmpSnpgMcacLvlTblLastChgd indicates the
                     sysUpTime at the time of the last modification of
                     msapIgmpSnpgMcacLevelTable.

                     If no changes were made to the entry since the last
                     re-initialization of the local network management subsystem,
                     then this object contains a zero value."
    ::= { tmnxSapObjs 61 }

msapIgmpSnpgMcacLagTblLastChgd  OBJECT-TYPE
    SYNTAX          TimeStamp
    MAX-ACCESS      read-only
    STATUS          current
    DESCRIPTION     "The value of msapIgmpSnpgMcacLagTblLastChgd indicates the
                     sysUpTime at the time of the last modification of
                     msapIgmpSnpgMcacLagTable.

                     If no changes were made to the entry since the last
                     re-initialization of the local network management subsystem,
                     then this object contains a zero value."
    ::= { tmnxSapObjs 62 }

msapInfoTblLastChgd  OBJECT-TYPE
    SYNTAX          TimeStamp
    MAX-ACCESS      read-only
    STATUS          current
    DESCRIPTION     "The value of msapInfoTblLastChgd indicates the
                     sysUpTime at the time of the last modification of
                     msapInfoTable.

                     If no changes were made to the entry since the last
                     re-initialization of the local network management subsystem,
                     then this object contains a zero value."
    ::= { tmnxSapObjs 63 }

msapL3PlcyTblLastChgd  OBJECT-TYPE
    SYNTAX          TimeStamp
    MAX-ACCESS      read-only
    STATUS          current
    DESCRIPTION     "The value of msapL3PlcyTblLastChgd indicates the
                     sysUpTime at the time of the last modification of
                     msapL3PlcyTable.

                     If no changes were made to the entry since the last
                     re-initialization of the local network management subsystem,
                     then this object contains a zero value."
    ::= { tmnxSapObjs 64 }

msapAtmPlcyTblLastChgd  OBJECT-TYPE
    SYNTAX          TimeStamp
    MAX-ACCESS      read-only
    STATUS          current
    DESCRIPTION     "The value of msapAtmPlcyTblLastChgd indicates the
                     sysUpTime at the time of the last modification of
                     msapAtmPlcyTable.

                     If no changes were made to the entry since the last
                     re-initialization of the local network management subsystem,
                     then this object contains a zero value."
    ::= { tmnxSapObjs 118 }
    
-- -----------------------------------------
-- SAP Static Host Managed Route Table
-- -----------------------------------------

sapStaticHostMRtTblLastChgd OBJECT-TYPE
    SYNTAX          TimeStamp
    MAX-ACCESS      read-only
    STATUS          current
    DESCRIPTION     "The value of sapStaticHostMRtTblLastChgd indicates the
                     sysUpTime at the time of the last modification of
                     sapStaticHostMRtTable.

                     If no changes were made to the entry since the last
                     re-initialization of the local network management 
                     subsystem, this object contains a zero value."
    ::= { tmnxSapObjs 65 }



sapStaticHostMRtTable OBJECT-TYPE
    SYNTAX          SEQUENCE OF SapStaticHostMRtEntry
    MAX-ACCESS      not-accessible
    STATUS          current
    DESCRIPTION     "The sapStaticHostMRtTable contains managed routes of
                     SAP static hosts.

                     Entries can be created and deleted via SNMP SET 
                     operations."
    ::= { tmnxSapObjs 66 }

sapStaticHostMRtEntry OBJECT-TYPE
    SYNTAX          SapStaticHostMRtEntry
    MAX-ACCESS      not-accessible
    STATUS          current
    DESCRIPTION     "Each row entry represents information on a specific
                     managed route."
    INDEX           { svcId,
                      sapPortId,
                      sapEncapValue,
                      sapStaticHostIpAddress,
                      sapStaticHostMacAddress,
                      sapStaticHostMRtAddrType,
                      sapStaticHostMRtAddr,
                      sapStaticHostMRtPrefixLen }
    ::= { sapStaticHostMRtTable 1 }

SapStaticHostMRtEntry ::=
    SEQUENCE {
        sapStaticHostMRtAddrType         InetAddressType,
        sapStaticHostMRtAddr             InetAddress,
        sapStaticHostMRtPrefixLen        InetAddressPrefixLength,
        sapStaticHostMRtRowStatus        RowStatus,
        sapStaticHostMRtLastMgmtChange   TimeStamp, 
        sapStaticHostMRtStatus           TmnxManagedRouteStatus
    }

sapStaticHostMRtAddrType OBJECT-TYPE
    SYNTAX          InetAddressType
    MAX-ACCESS      not-accessible
    STATUS          current
    DESCRIPTION     "The value of sapStaticHostMRtAddrType indicates
                     the address type of sapStaticHostMRtAddr."
    ::= { sapStaticHostMRtEntry 1 }

sapStaticHostMRtAddr OBJECT-TYPE
    SYNTAX          InetAddress (SIZE(4|16))
    MAX-ACCESS      not-accessible
    STATUS          current
    DESCRIPTION     "The value of sapStaticHostMRtAddr indicates
                     the IP address of the managed route."
    ::= { sapStaticHostMRtEntry 2 }

sapStaticHostMRtPrefixLen OBJECT-TYPE
    SYNTAX          InetAddressPrefixLength (0..32)
    MAX-ACCESS      not-accessible
    STATUS          current
    DESCRIPTION     "The value of sapStaticHostMRtPrefixLen indicates
                     the prefix length of the subnet associated with
                     sapStaticHostMRtAddr."
    ::= { sapStaticHostMRtEntry 3 }

sapStaticHostMRtRowStatus OBJECT-TYPE
    SYNTAX          RowStatus
    MAX-ACCESS      read-create
    STATUS          current
    DESCRIPTION     "The value of sapStaticHostMRtRowStatus controls the 
                     creation and deletion of rows in this table."
    ::= { sapStaticHostMRtEntry 4 }

sapStaticHostMRtLastMgmtChange OBJECT-TYPE
    SYNTAX          TimeStamp
    MAX-ACCESS      read-only
    STATUS          current
    DESCRIPTION     "The value of sapStaticHostMRtLastMgmtChange indicates the
                     value of sysUpTime at the time of the last management
                     change of any writable object of this row."
    ::= { sapStaticHostMRtEntry 5 }

sapStaticHostMRtStatus OBJECT-TYPE
    SYNTAX          TmnxManagedRouteStatus
    MAX-ACCESS      read-only
    STATUS          current
    DESCRIPTION     "The value of svcDhcpManagedRouteStatus indicates
                     the state of this managed route."
    ::= { sapStaticHostMRtEntry 6 }

-- ---------------------------------------------------------------------
--  sapTlsArpHostTable
--
--
--  Sparse Dependent Extension of the sapTlsInfoTable.
--
--  The same indexes are used for both the base table, sapTlsInfoTable,
--  and the sparse dependent table, sapTlsArpHostTable.
--
--  This in effect extends the sapTlsInfoTable with additional columns.
--  A row is automatically created in the sapTlsArpHostTable for each row
--  in the sapTlsInfoTable .
--
--  Deletion of a row in the sapTlsInfoTable results in the
--  same fate for the row in the sapTlsArpHostTable.
-- ---------------------------------------------------------------------

sapTlsArpHostTableLastMgmtChange OBJECT-TYPE
    SYNTAX      TimeStamp
    MAX-ACCESS  read-only
    STATUS      current
    DESCRIPTION
        "The value of sapTlsArpHostTableLastMgmtChange indicates the sysUpTime 
         at the time of the most recent management-initiated change to the
         sapTlsArpHostTable."
    ::= { tmnxSapObjs 67 }

sapTlsArpHostTable OBJECT-TYPE
    SYNTAX      SEQUENCE OF SapTlsArpHostEntry
    MAX-ACCESS  not-accessible
    STATUS      current
    DESCRIPTION
        "A table that contains ARP host configuration 
         information about a SAP in a TLS."
    ::= { tmnxSapObjs 68 }

sapTlsArpHostEntry OBJECT-TYPE
    SYNTAX      SapTlsArpHostEntry
    MAX-ACCESS  not-accessible
    STATUS      current
    DESCRIPTION
        "ARP host specific information about a SAP in a TLS."
    INDEX           { svcId, sapPortId, sapEncapValue }
    ::= { sapTlsArpHostTable 1 }

SapTlsArpHostEntry ::=
    SEQUENCE {
        sapTlsArpHostLastMgmtChange       TimeStamp,
        sapTlsArpHostAdminState           TmnxAdminState,
        sapTlsArpHostMaxNumHosts          Unsigned32,
        sapTlsArpHostMinAuthIntvl         Unsigned32
    }

sapTlsArpHostLastMgmtChange OBJECT-TYPE
    SYNTAX      TimeStamp
    MAX-ACCESS  read-only
    STATUS      current
    DESCRIPTION
        "The value of sapTlsArpHostLastMgmtChange indicates the sysUpTime at
         the time of the most recent management-initiated change to this
         table row."
    ::= { sapTlsArpHostEntry 1 }

sapTlsArpHostAdminState OBJECT-TYPE
    SYNTAX      TmnxAdminState
    MAX-ACCESS  read-write
    STATUS      current
    DESCRIPTION
        "The value of the object sapTlsArpHostAdminState specifies the
         administrative state of the ARP host functionality on this TLS SAP."
    DEFVAL { outOfService }
    ::= { sapTlsArpHostEntry 2 }

sapTlsArpHostMaxNumHosts OBJECT-TYPE
    SYNTAX      Unsigned32 (1..131071)
    MAX-ACCESS  read-write
    STATUS      current
    DESCRIPTION
        "The value of sapTlsArpHostMaxNumHosts specifies the maximum
         number of ARP hosts allowed on this TLS SAP."
    DEFVAL { 1 }
    ::= { sapTlsArpHostEntry 3 }

sapTlsArpHostMinAuthIntvl OBJECT-TYPE
    SYNTAX      Unsigned32 (1..6000)
    UNITS       "minutes"
    MAX-ACCESS  read-write
    STATUS      current
    DESCRIPTION
        "The value of sapTlsArpHostMinAuthIntvl specifies the minimum
         interval between two consecutive authentication attempts for the
         same ARP host."
    DEFVAL { 15 }
    ::= { sapTlsArpHostEntry 4 }

-- ---------------------------------------------------------------------
--  sapIgmpTrkTable
--
--
--  Sparse Dependent Extension of the sapBaseInfoTable.
--
--  The same indexes are used for both the base table, sapBaseInfoTable,
--  and the sparse dependent table, sapIgmpTrkTable.
--
--  This in effect extends the sapBaseInfoTable with additional columns.
--  A row is automatically created in the sapIgmpTrkTable for each applicable 
--  row in the sapBaseInfoTable .
--
--  Deletion of a row in the sapBaseInfoTable results in the
--  same fate for the row in the sapIgmpTrkTable.
-- ---------------------------------------------------------------------

sapIgmpTrkTableLastMgmtChange OBJECT-TYPE
    SYNTAX      TimeStamp
    MAX-ACCESS  read-only
    STATUS      current
    DESCRIPTION
        "The value of sapIgmpTrkTableLastMgmtChange indicates the sysUpTime 
         at the time of the most recent management-initiated change to the
         sapIgmpTrkTable."
    ::= { tmnxSapObjs 69 }

sapIgmpTrkTable OBJECT-TYPE
    SYNTAX      SEQUENCE OF SapIgmpTrkEntry
    MAX-ACCESS  not-accessible
    STATUS      current
    DESCRIPTION
        "A table that contains IGMP host tracking configuration 
         information about SAP's.

         The system automatically creates an entry in this table
         for each SAP where it creates a corresponding entry in the 
         sapSubMgmtInfoTable. 
         
         This means that all SAP's that support Enhanced Subscriber Management 
         have en entry in this table."
    ::= { tmnxSapObjs 70 }

sapIgmpTrkEntry OBJECT-TYPE
    SYNTAX      SapIgmpTrkEntry
    MAX-ACCESS  not-accessible
    STATUS      current
    DESCRIPTION
        "IGMP host tracking specific information about a SAP."
    INDEX           { svcId, sapPortId, sapEncapValue }
    ::= { sapIgmpTrkTable 1 }

SapIgmpTrkEntry ::=
    SEQUENCE {
        sapIgmpTrkLastMgmtChange          TimeStamp,
        sapIgmpTrkExpiryTime              Unsigned32,
        sapIgmpTrkImportPlcy              TPolicyStatementNameOrEmpty,
        sapIgmpTrkMaxNbrGrps              Unsigned32,
        sapIgmpTrkNbrGrps                 Gauge32,
        sapIgmpTrkMaxNbrSrcs              Unsigned32,
        sapIgmpTrkDisRtrAlertChk          TruthValue,
        sapIgmpTrkMaxNbrGrpSrcs           Unsigned32
    }

sapIgmpTrkLastMgmtChange OBJECT-TYPE
    SYNTAX      TimeStamp
    MAX-ACCESS  read-only
    STATUS      current
    DESCRIPTION
        "The value of sapIgmpTrkLastMgmtChange indicates the sysUpTime at
         the time of the most recent management-initiated change to this
         table row."
    ::= { sapIgmpTrkEntry 1 }

sapIgmpTrkExpiryTime OBJECT-TYPE
    SYNTAX      Unsigned32 (0|1..65535)
    UNITS       "seconds"
    MAX-ACCESS  read-write
    STATUS      current
    DESCRIPTION
        "The value of sapIgmpTrkExpiryTime specifies 
         the time in seconds that this system continues to track an inactive
         host.
         
         The value zero specifies that the value must be set to the actual 
         value of the object svcIgmpTrkExpiryTime of the service this SAP 
         belongs to."
    DEFVAL { 0 }
    ::= { sapIgmpTrkEntry 2 }

sapIgmpTrkImportPlcy OBJECT-TYPE
    SYNTAX      TPolicyStatementNameOrEmpty
    MAX-ACCESS  read-write
    STATUS      current
    DESCRIPTION
        "The value of the object sapIgmpTrkImportPlcy specifies
         the policy statement that must be applied to all
         incoming IGMP messages on this SAP."
    DEFVAL { "" }
    ::= { sapIgmpTrkEntry 3 }

sapIgmpTrkMaxNbrGrps OBJECT-TYPE
    SYNTAX      Unsigned32 (0..16000)
    MAX-ACCESS  read-write
    STATUS      current
    DESCRIPTION
        "The value of the object sapIgmpTrkMaxNbrGrps specifies
         how many group addresses are allowed for this SAP.

         The value 0 means that no limit is imposed."
    DEFVAL { 0 }
    ::= { sapIgmpTrkEntry 4 }

sapIgmpTrkNbrGrps OBJECT-TYPE
    SYNTAX      Gauge32
    MAX-ACCESS  read-only
    STATUS      current
    DESCRIPTION
        "The value of the object sapIgmpTrkNbrGrps indicates
         how many group addresses are tracked for this SAP."
    ::= { sapIgmpTrkEntry 5 }

sapIgmpTrkMaxNbrSrcs OBJECT-TYPE
    SYNTAX      Unsigned32 (0..1000)
    MAX-ACCESS  read-write
    STATUS      current
    DESCRIPTION
        "The value of the object sapIgmpTrkMaxNbrSrcs specifies
         how many source addresses are allowed per group address for this SAP.

         The value 0 means that no limit is imposed."
    DEFVAL { 0 }
    ::= { sapIgmpTrkEntry 6 }

sapIgmpTrkDisRtrAlertChk OBJECT-TYPE
    SYNTAX     TruthValue
    MAX-ACCESS read-write
    STATUS     current
    DESCRIPTION
        "sapIgmpTrkDisRtrAlertChk is used to enable/disable router
         alert checking for IGMP messages received on this sap.

         If this flag is set to 'true', checking is disabled." 
    DEFVAL     { false }
    ::= { sapIgmpTrkEntry 7 }

sapIgmpTrkMaxNbrGrpSrcs OBJECT-TYPE
    SYNTAX      Unsigned32 (0..32000)
    MAX-ACCESS  read-write
    STATUS      current
    DESCRIPTION
        "The value of the object sapIgmpTrkMaxNbrGrpSrcs specifies how
         many group source addresses are allowed per group address for this SAP.

         The value 0 means that no limit is imposed."
    DEFVAL { 0 }
    ::= { sapIgmpTrkEntry 8 }

-- ---------------------------------------------------------------------
-- FR SAP Table
--
--
--  Sparse Dependent Extention of the sapBaseInfoTable.
--
--  The same indexes are used for both the base table, sapBaseInfoTable,
--  and the sparse dependent table, sapFrInfoTable.
--
--  This in effect extends the sapBaseInfoTable with additional columns.
--  Rows are created in the sapFrInfoTable only for those entries
--  in the sapBaseInfoTable that are created on a port that has 
--  'frEncap' set for port encapsulation.
--
--  Deletion of a row in the sapBaseInfoTable results in the
--  same fate for the row in the sapFrInfoTable.
-- ---------------------------------------------------------------------
sapFrInfoTable OBJECT-TYPE
    SYNTAX          SEQUENCE OF SapFrInfoEntry
    MAX-ACCESS      not-accessible
    STATUS          current
    DESCRIPTION     "A table that contains FR SAP information."
    ::= { tmnxSapObjs 71 }

sapFrInfoEntry OBJECT-TYPE
    SYNTAX          SapFrInfoEntry
    MAX-ACCESS      not-accessible
    STATUS          current
    DESCRIPTION     "Information about a specific FR SAP."
    INDEX           { svcId, sapPortId, sapEncapValue }
    ::= { sapFrInfoTable 1 }

SapFrInfoEntry ::=
    SEQUENCE {
        sapFrInfoFrf12Mode        TmnxEnabledDisabled,
        sapFrInfoSchedulingClass  TmnxMcFrClassIndex,
        sapFrInfoLastChanged      TimeStamp
    }

sapFrInfoFrf12Mode OBJECT-TYPE
    SYNTAX      TmnxEnabledDisabled
    MAX-ACCESS  read-create
    STATUS      current
    DESCRIPTION
        "The value of sapFrInfoFrf12Mode enables or disables the 
         use of FRF12 headers. This must be set to disabled for this
         entry to be added to a mlfr bundle."
    DEFVAL { disabled }
    ::= { sapFrInfoEntry 1 }

sapFrInfoSchedulingClass    OBJECT-TYPE
    SYNTAX      TmnxMcFrClassIndex
    MAX-ACCESS  read-create
    STATUS      current
    DESCRIPTION
        "The value of sapFrInfoSchedulingClass specifies the scheduling class 
         to use for this sap. This object is only applicable for a sapPortId
         that has tmnxBundleType set to 'mlfr', sapFrInfoFrf12Mode SAPs set to
         'enabled' or tmnxFrIntfFrf12Mode set to 'enabled' and
         sapFrf12InfoInterleave set to 'disabled'."
    DEFVAL      { 3 }
    ::= { sapFrInfoEntry 2 }

sapFrInfoLastChanged OBJECT-TYPE
    SYNTAX      TimeStamp
    MAX-ACCESS  read-only
    STATUS      current
    DESCRIPTION
        "The value of sapFrInfoLastChanged indicates the sysUpTime
         at the time of the last modification of this entry."
    ::= { sapFrInfoEntry 3 }

-- ---------------------------------------------------------------------
-- FRF12 SAP Table
--
--
--  Sparse Dependent Extention of the sapFrInfoTable.
--
--  The same indexes are used for both the sapFrInfoTable,
--  and the sparse dependent table, sapFrf12InfoTable.
--
--  This in effect extends the sapFrInfoTable with additional columns.
--  Rows are created in the sapFrf12InfoTable only for those entries
--  in the sapFrInfoTable that are created with sapFrInfoFrf12Mode set
--- to 'enable'.
--
--  Setting sapFrInfoFrf12Mode to 'disable' results in the removal
--  for the row in the sapFrf12InfoTable.
-- ---------------------------------------------------------------------
sapFrf12InfoTable OBJECT-TYPE
    SYNTAX          SEQUENCE OF SapFrf12InfoEntry
    MAX-ACCESS      not-accessible
    STATUS          current
    DESCRIPTION     "A table that contains FRF12 SAP information."
    ::= { tmnxSapObjs 74 }

sapFrf12InfoEntry OBJECT-TYPE
    SYNTAX          SapFrf12InfoEntry
    MAX-ACCESS      not-accessible
    STATUS          current
    DESCRIPTION     "Information about a specific FR SAP."
    INDEX           { svcId, sapPortId, sapEncapValue }
    ::= { sapFrf12InfoTable 1 }

SapFrf12InfoEntry ::=
    SEQUENCE {
        sapFrf12InfoFragmentThreshold     Unsigned32,
        sapFrf12InfoLastChanged           TimeStamp,
        sapFrf12InfoInterleave            TmnxEnabledDisabled
    }

sapFrf12InfoFragmentThreshold    OBJECT-TYPE
    SYNTAX      Unsigned32(128..512)
    MAX-ACCESS  read-create
    STATUS      current
    DESCRIPTION
        "The value of sapFrf12InfoFragmentThreshold specifies the maximum
         length of a fragment to be transmitted."
    DEFVAL      { 128 }
    ::= { sapFrf12InfoEntry 1 }

sapFrf12InfoLastChanged OBJECT-TYPE
    SYNTAX      TimeStamp
    MAX-ACCESS  read-only
    STATUS      current
    DESCRIPTION
        "The value of sapFrf12InfoLastChanged indicates the sysUpTime
         at the time of the last modification of this entry.."
    ::= { sapFrf12InfoEntry 2 }

sapFrf12InfoInterleave OBJECT-TYPE
    SYNTAX      TmnxEnabledDisabled
    MAX-ACCESS  read-create
    STATUS      current
    DESCRIPTION
        "The value of sapFrf12InfoInterleave specifies whether or not FRF12
         interleave is enabled. If enabled, sapFrInfoSchedulingClass is not
         applicable."
    DEFVAL { disabled }
    ::= { sapFrf12InfoEntry 3 }

-- ---------------------------------------------------------------------
--  sapArpHostStatTable
--
--
--  Sparse Dependent Extension of the sapBaseInfoTable.
--
--  The same indexes are used for both the base table, sapBaseInfoTable,
--  and the sparse dependent table, sapArpHostStatTable.
--
--  This in effect extends the sapBaseInfoTable with additional columns.
--  A row is automatically created in the sapArpHostStatTable for each applicable 
--  row in the sapBaseInfoTable .
--
--  Deletion of a row in the sapBaseInfoTable results in the
--  same fate for the row in the sapArpHostStatTable.
-- ---------------------------------------------------------------------

sapArpHostStatTable OBJECT-TYPE
    SYNTAX      SEQUENCE OF SapArpHostStatEntry
    MAX-ACCESS  not-accessible
    STATUS      current
    DESCRIPTION
        "A table that contains ARP host status and statistics 
         information about SAP's."
    ::= { tmnxSapObjs 75 }

sapArpHostStatEntry OBJECT-TYPE
    SYNTAX      SapArpHostStatEntry
    MAX-ACCESS  not-accessible
    STATUS      current
    DESCRIPTION
        "ARP host specific status and statistics information about a SAP."
    INDEX           { svcId, sapPortId, sapEncapValue }
    ::= { sapArpHostStatTable 1 }

SapArpHostStatEntry ::=
    SEQUENCE {
        sapArpHostStatLastClearedTime    TimeStamp,
        sapArpHostStatNumHosts           Gauge32,
        sapArpHostStatTriggersRx         Counter32,
        sapArpHostStatTriggersIgnored    Counter32,
        sapArpHostStatTrigIgnQFull       Counter32,
        sapArpHostStatNumForcedVerif     Counter32,
        sapArpHostStatNumCreated         Counter32,
        sapArpHostStatNumDeleted         Counter32,
        sapArpHostStatNumUpdated         Counter32,
        sapArpHostStatNumAuthReq         Counter32
    }

sapArpHostStatLastClearedTime OBJECT-TYPE
    SYNTAX      TimeStamp
    MAX-ACCESS  read-only
    STATUS      current
    DESCRIPTION
        "The value of sapArpHostStatLastClearedTime indicates 
         the last time that these stats were cleared. 
         
         The value zero indicates that they have not been cleared yet."
    ::= { sapArpHostStatEntry 1 }

sapArpHostStatNumHosts OBJECT-TYPE
    SYNTAX      Gauge32
    MAX-ACCESS  read-only
    STATUS      current
    DESCRIPTION
        "The value of sapArpHostStatNumHosts indicates 
         the actual number of ARP hosts on this SAP."
    ::= { sapArpHostStatEntry 2 }

sapArpHostStatTriggersRx OBJECT-TYPE
    SYNTAX      Counter32 
    MAX-ACCESS  read-only
    STATUS      current
    DESCRIPTION
        "The value of sapArpHostStatTriggersRx indicates 
         the number of ARP triggers received on this SAP
         since the last re-initialization of the local network 
         management subsystem, or the last time the system statistics were 
         cleared."
    ::= { sapArpHostStatEntry 3 }

sapArpHostStatTriggersIgnored OBJECT-TYPE
    SYNTAX      Counter32 
    MAX-ACCESS  read-only
    STATUS      current
    DESCRIPTION
        "The value of sapArpHostStatTriggersIgnored indicates 
         the number of ARP triggers received on this SAP
         that did not result in the creation of a new ARP host
         since the last re-initialization of the local network 
         management subsystem, or the last time the system statistics were 
         cleared.
         
         This number does not include the number indicated by 
         sapArpHostStatTrigIgnQFull."
    ::= { sapArpHostStatEntry 4 }

sapArpHostStatTrigIgnQFull OBJECT-TYPE
    SYNTAX      Counter32 
    MAX-ACCESS  read-only
    STATUS      current
    DESCRIPTION
        "The value of sapArpHostStatTrigIgnQFull indicates 
         the number of ARP triggers received on this SAP
         that did not result in the creation of a new ARP host because
         the internal ARP trigger event queue of the system was full,
         since the last re-initialization of the local network 
         management subsystem, or the last time the system statistics were 
         cleared."
    ::= { sapArpHostStatEntry 5 }

sapArpHostStatNumForcedVerif OBJECT-TYPE
    SYNTAX      Counter32 
    MAX-ACCESS  read-only
    STATUS      current
    DESCRIPTION
        "The value of sapArpHostStatNumForcedVerif indicates 
         the number of times that the system started a forced subscriber
         host connectivity verification for an ARP host on this SAP
         since the last re-initialization of the local network 
         management subsystem, or the last time the system statistics were 
         cleared."
    ::= { sapArpHostStatEntry 6 }

sapArpHostStatNumCreated OBJECT-TYPE
    SYNTAX      Counter32 
    MAX-ACCESS  read-only
    STATUS      current
    DESCRIPTION
        "The value of sapArpHostStatNumCreated indicates 
         the number of times that an ARP host was created on this SAP
         since the last re-initialization of the local network 
         management subsystem, or the last time the system statistics were 
         cleared."
    ::= { sapArpHostStatEntry 7 }

sapArpHostStatNumDeleted OBJECT-TYPE
    SYNTAX      Counter32 
    MAX-ACCESS  read-only
    STATUS      current
    DESCRIPTION
        "The value of sapArpHostStatNumDeleted indicates 
         the number of times that an ARP host was deleted on this SAP
         since the last re-initialization of the local network 
         management subsystem, or the last time the system statistics were 
         cleared."
    ::= { sapArpHostStatEntry 8 }

sapArpHostStatNumUpdated OBJECT-TYPE
    SYNTAX      Counter32 
    MAX-ACCESS  read-only
    STATUS      current
    DESCRIPTION
        "The value of sapArpHostStatNumUpdated indicates 
         the number of times that an ARP host was updated on this SAP
         since the last re-initialization of the local network 
         management subsystem, or the last time the system statistics were 
         cleared."
    ::= { sapArpHostStatEntry 9 }

sapArpHostStatNumAuthReq OBJECT-TYPE
    SYNTAX      Counter32 
    MAX-ACCESS  read-only
    STATUS      current
    DESCRIPTION
        "The value of sapArpHostStatNumAuthReq indicates 
         the number of times that the system initiated 
         an authentication request for an ARP host on this SAP
         since the last re-initialization of the local network 
         management subsystem, or the last time the system statistics were 
         cleared."
    ::= { sapArpHostStatEntry 10 }

-- ----------------------------------
-- PBB SAP Table
-- ----------------------------------
sapPbbTable OBJECT-TYPE
    SYNTAX          SEQUENCE OF SapPbbEntry
    MAX-ACCESS      not-accessible
    STATUS          current
    DESCRIPTION     "A table that contains 
                     Provider Backbone Bridging (PBB/IEEE 802.1ah) SAP 
                     information."
    ::= { tmnxSapObjs 76 }

sapPbbEntry OBJECT-TYPE
    SYNTAX          SapPbbEntry
    MAX-ACCESS      not-accessible
    STATUS          current
    DESCRIPTION     "PBB I-Component instance-specific information about a 
                     specific SAP in the B-Component instance.
    
                     Entries in this table can be created or deleted 
                     via SNMP operations."
    INDEX           { sapPbbSvcIdIVpls,
                      sapPbbSvcIdBVpls, 
                      sapPbbPortId, 
                      sapPbbEncapValue }
    ::= { sapPbbTable 1 }

SapPbbEntry ::=
    SEQUENCE {
        sapPbbSvcIdIVpls                 TmnxServId,
        sapPbbSvcIdBVpls                 TmnxServId,
        sapPbbPortId                     TmnxPortID,
        sapPbbEncapValue                 TmnxEncapVal,
        sapPbbRowStatus                  RowStatus,
        sapPbbLastMgmtChange             TimeStamp,
        sapPbbIgmpSnpgMRouter            TruthValue,
        sapPbbMldSnpgMRouter             TruthValue
    }

sapPbbSvcIdIVpls OBJECT-TYPE
    SYNTAX          TmnxServId
    MAX-ACCESS      not-accessible
    STATUS          current
    DESCRIPTION     "The value of the object sapPbbSvcIdIVpls specifies the
                     Service identifier of the I-Component instance."
    ::= { sapPbbEntry 1 }

sapPbbSvcIdBVpls OBJECT-TYPE
    SYNTAX          TmnxServId
    MAX-ACCESS      not-accessible
    STATUS          current
    DESCRIPTION     "The value of the object sapPbbSvcIdBVpls specifies the
                     Service identifier of the B-Component instance."
    ::= { sapPbbEntry 2 }

sapPbbPortId OBJECT-TYPE
    SYNTAX          TmnxPortID
    MAX-ACCESS      not-accessible
    STATUS          current
    DESCRIPTION     "The value of the object sapPbbPortId specifies 
                     the ID of the access port in the B-Component instance 
                     where this SAP is defined."
    ::= { sapPbbEntry 3 }

sapPbbEncapValue OBJECT-TYPE
    SYNTAX          TmnxEncapVal
    MAX-ACCESS      not-accessible
    STATUS          current
    DESCRIPTION     "The value of the object sapPbbEncapValue specifies 
                     the value of the label used to identify this SAP in the 
                     B-Component instance on the access port specified by 
                     sapPortId."
    ::= { sapPbbEntry 4 }

sapPbbRowStatus OBJECT-TYPE
    SYNTAX          RowStatus
    MAX-ACCESS      read-create
    STATUS          current
    DESCRIPTION     "The value of sapPbbRowStatus specifies 
                     the row status of this row. 
                     
                     The only values supported during a set operation are
                     'createAndGo' and 'destroy'."
    ::= { sapPbbEntry 5 }

sapPbbLastMgmtChange OBJECT-TYPE
    SYNTAX          TimeStamp
    MAX-ACCESS      read-only
    STATUS          current
    DESCRIPTION
                    "The value of sapPbbLastMgmtChange indicates 
                     the sysUpTime at the time of the most recent 
                     management-initiated change to this table row."
    ::= { sapPbbEntry 6 }

sapPbbIgmpSnpgMRouter OBJECT-TYPE
    SYNTAX          TruthValue
    MAX-ACCESS      read-create
    STATUS          current
    DESCRIPTION
                    "The value of the object sapPbbIgmpSnpgMRouter specifies 
                     if a multicast router is attached behind this SAP."
    DEFVAL { false }
    ::= { sapPbbEntry 7 }

sapPbbMldSnpgMRouter OBJECT-TYPE
    SYNTAX          TruthValue
    MAX-ACCESS      read-create
    STATUS          current
    DESCRIPTION
                    "The value of the object sapPbbMldSnpgMRouter specifies 
                     if a multicast router is attached behind this SAP."
    DEFVAL { false }
    ::= { sapPbbEntry 8 }

-- --------------------------------------------------------
-- SAP Fault Propagation Backbone Mac (BMac) Address Table
-- --------------------------------------------------------

sapFPropBMacAddrTblLastChgd OBJECT-TYPE
    SYNTAX          TimeStamp
    MAX-ACCESS      read-only
    STATUS          current
    DESCRIPTION
        "The value of sapFPropBMacAddrTblLastChgd indicates the sysUpTime 
         of the last modification of sapFPropBMacAddrTable.

         If no changes were made to the table since the last re-initialization
         of the local network management subsystem, this object contains a zero
         value."
    ::= { tmnxSapObjs 77 }

sapFPropBMacAddrTable OBJECT-TYPE
    SYNTAX          SEQUENCE OF SapFPropBMacAddrEntry
    MAX-ACCESS      not-accessible
    STATUS          current
    DESCRIPTION
        "sapFPropBMacAddrTable contains the optional configured backbone MAC
         (BMac) addresses (or MAC names) for each SAP.  This table extends the
         information in sapBaseInfoTable."
    ::= { tmnxSapObjs 78 }

sapFPropBMacAddrEntry OBJECT-TYPE
    SYNTAX          SapFPropBMacAddrEntry
    MAX-ACCESS      not-accessible
    STATUS          current
    DESCRIPTION
        "sapFPropBMacAddrEntry defines a row in the sapFPropBMacAddrTable.
         The first three index objects reside in sapBaseInfoTable.  Rows
         are created and destroyed using sapFPropBMacAddrRowStatus."
    INDEX           {
                        svcId,
                        sapPortId,
                        sapEncapValue,
                        sapFPropBMacAddrMacNameOrAddrTag,
                        sapFPropBMacAddrMacNameOrAddr
                    }
    ::= { sapFPropBMacAddrTable 1 }

SapFPropBMacAddrEntry ::=
    SEQUENCE {
        sapFPropBMacAddrMacNameOrAddrTag INTEGER,
        sapFPropBMacAddrMacNameOrAddr    TNamedItem,
        sapFPropBMacAddrRowStatus        RowStatus
    }

sapFPropBMacAddrMacNameOrAddrTag OBJECT-TYPE
    SYNTAX          INTEGER {
                        macName (1),
                        macAddr (2)
                    }
    MAX-ACCESS      not-accessible
    STATUS          current
    DESCRIPTION
        "The value of sapFPropBMacAddrMacNameOrAddrTag specifies whether
         sapFPropBMacAddrMacNameOrAddr contains a MAC name, or a MAC address."
    ::= { sapFPropBMacAddrEntry 1 }

sapFPropBMacAddrMacNameOrAddr OBJECT-TYPE
    SYNTAX          TNamedItem
    MAX-ACCESS      not-accessible
    STATUS          current
    DESCRIPTION
        "The value of sapFPropBMacAddrMacNameOrAddr specifies a MAC name or MAC
         address configured against a <svcId, sapPortId, sapEncapValue> index
         triple.

         When sapFPropBMacAddrMacNameOrAddrTag is 'macName (1)',
         sapFPropBMacAddrMacNameOrAddr must contain a MAC name which is
         present in the svcMacName column of the svcMacNameTable.

         When sapFPropBMacAddrMacNameOrAddrTag is 'macAddr (2)',
         sapFPropBMacAddrMacNameOrAddr must contain a MAC address, encoded in
         network byte order and IEEE 802.3 canonical bit order as defined in
         IEEE Std 802-2001.

         All the MAC addresses configured for a particular SAP (whether
         configured as MAC addresses, or via MAC names) must refer to one
         B-VPLS on the remote system."
    ::= { sapFPropBMacAddrEntry 2 }

sapFPropBMacAddrRowStatus OBJECT-TYPE
    SYNTAX          RowStatus
    MAX-ACCESS      read-create
    STATUS          current
    DESCRIPTION
        "The value of sapFPropBMacAddrRowStatus specifies the status of this
         row."
    ::= { sapFPropBMacAddrEntry 3 }

-- ----------------------------------------
-- SAP IPv6 Host Information Table
-- ----------------------------------------
sapIpv6HostInfoTable OBJECT-TYPE
    SYNTAX          SEQUENCE OF SapIpv6HostInfoEntry
    MAX-ACCESS      not-accessible
    STATUS          current
    DESCRIPTION     "sapIpv6HostInfoTable contains IPv6 information related to a
                     routed CO subscriber SAP.  This table complements
                     sapBaseInfoTable, and contains an entry for each
                     routed CO subscriber SAP. Rows in this table
                     are created and deleted automatically by the system."
    ::= { tmnxSapObjs 79 }

sapIpv6HostInfoEntry OBJECT-TYPE
    SYNTAX          SapIpv6HostInfoEntry
    MAX-ACCESS      not-accessible
    STATUS          current
    DESCRIPTION     "IPv6 specific information for a routed CO subscriber SAP."
    INDEX           { svcId, sapPortId, sapEncapValue }
    ::= { sapIpv6HostInfoTable 1 }

SapIpv6HostInfoEntry ::=
    SEQUENCE {
        sapIpv6HostInfoIpoeDhcp6Hosts  Unsigned32,
        sapIpv6HostInfoPppDhcp6Hosts   Unsigned32,
        sapIpv6HostInfoPppSLAACHosts   Unsigned32,
        sapIpv6HostInfoIpoeSLAACHosts  Unsigned32,
        sapIpv6HostInfoStaticHostsUp   Unsigned32
    }

sapIpv6HostInfoIpoeDhcp6Hosts OBJECT-TYPE
    SYNTAX          Unsigned32
    MAX-ACCESS      read-only
    STATUS          current
    DESCRIPTION     "The value of the object sapIpv6HostInfoIpoeDhcp6Hosts
                     indicates the number of IPoE DHCPv6 hosts for this SAP."
    ::= { sapIpv6HostInfoEntry 1 }

sapIpv6HostInfoPppDhcp6Hosts OBJECT-TYPE
    SYNTAX          Unsigned32
    MAX-ACCESS      read-only
    STATUS          current
    DESCRIPTION     "The value of the object sapIpv6HostInfoPppDhcp6Hosts
                     indicates the number of PPP DHCPv6 hosts for this SAP."
    ::= { sapIpv6HostInfoEntry 2 }

sapIpv6HostInfoPppSLAACHosts OBJECT-TYPE
    SYNTAX          Unsigned32
    MAX-ACCESS      read-only
    STATUS          current
    DESCRIPTION     "The value of the object sapIpv6HostInfoPppSLAACHosts
                     indicates the number of PPP SLAAC hosts for this SAP."
    ::= { sapIpv6HostInfoEntry 3 }

sapIpv6HostInfoIpoeSLAACHosts OBJECT-TYPE
    SYNTAX          Unsigned32
    MAX-ACCESS      read-only
    STATUS          current
    DESCRIPTION     "The value of the object sapIpv6HostInfoIpoeSLAACHosts
                     indicates the number of IPoE SLAAC hosts for this SAP."
    ::= { sapIpv6HostInfoEntry 4 }

sapIpv6HostInfoStaticHostsUp OBJECT-TYPE
    SYNTAX          Unsigned32
    MAX-ACCESS      read-only
    STATUS          current
    DESCRIPTION     "The value of the object sapIpv6HostInfoStaticHostsUp
                     indicates the number of IPv6 static IPoE hosts
                     for this SAP where the value of sapStatHost6AdminStatus
                     is equal to 'up'."
    ::= { sapIpv6HostInfoEntry 5 }

-- ------------------------------------
-- SAP ingress Policer Control Override
-- ------------------------------------
sapIngPlcrCtrlOvrTblLastChgd OBJECT-TYPE
    SYNTAX       TimeStamp
    MAX-ACCESS   read-only
    STATUS       current
    DESCRIPTION
        "sapIngPlcrCtrlOvrTblLastChgd indicates the timestamp of last change to
        the sapIngPlcrCtrlOvrTable."
    ::= { tmnxSapObjs 80 }

sapIngPlcrCtrlOvrTable OBJECT-TYPE
    SYNTAX          SEQUENCE OF SapIngPlcrCtrlOvrEntry
    MAX-ACCESS      not-accessible
    STATUS          current
    DESCRIPTION     "A table that contains SAP ingress policer control
                     override information."
    ::= { tmnxSapObjs 81 }

sapIngPlcrCtrlOvrEntry OBJECT-TYPE
    SYNTAX          SapIngPlcrCtrlOvrEntry
    MAX-ACCESS      not-accessible
    STATUS          current
    DESCRIPTION     "Policer control override information about a specific SAP
                     on the ingress side."
    INDEX           { svcId, sapPortId, sapEncapValue }
    ::= { sapIngPlcrCtrlOvrTable 1 }

SapIngPlcrCtrlOvrEntry ::=
    SEQUENCE {
        sapIngPlcrCtrlOvrRowStatus     RowStatus,
        sapIngPlcrCtrlOvrLastChgd      TimeStamp,
        sapIngPlcrCtrlOvrMaxRate       THPolPIRRateOverride,
        sapIngPlcrCtrlOvrMinMBSSep     TPlcrBurstSizeBytesOverride
    }

sapIngPlcrCtrlOvrRowStatus OBJECT-TYPE
    SYNTAX       RowStatus
    MAX-ACCESS   read-create
    STATUS       current
    DESCRIPTION
        "This is the Row Status of the entry.
        This allows creation/deletion of rows in this table."
    ::= { sapIngPlcrCtrlOvrEntry 1 }

sapIngPlcrCtrlOvrLastChgd OBJECT-TYPE
    SYNTAX       TimeStamp
    MAX-ACCESS   read-only
    STATUS       current
    DESCRIPTION
        "The value of sapIngPlcrCtrlOvrLastChgd indicates the timestamp of
        last change to this row in sapIngPlcrCtrlOvrTable."
    ::= { sapIngPlcrCtrlOvrEntry 2 }

sapIngPlcrCtrlOvrMaxRate OBJECT-TYPE
    SYNTAX       THPolPIRRateOverride
    UNITS        "kbps"
    MAX-ACCESS   read-create
    STATUS       current
    DESCRIPTION
        "The value of sapIngPlcrCtrlOvrMaxRate specifies the
        maximum frame based bandwidth limit of this policer override."
    DEFVAL { -2 }
    ::= { sapIngPlcrCtrlOvrEntry 3 }

sapIngPlcrCtrlOvrMinMBSSep OBJECT-TYPE
    SYNTAX       TPlcrBurstSizeBytesOverride
    UNITS        "bytes"
    MAX-ACCESS   read-create
    STATUS       current
    DESCRIPTION
        "The value of sapIngPlcrCtrlOvrMinMBSSep specifies the
        minimum amount of seperation buffer space (in bytes) allowed 
        by this policer override."
    DEFVAL { -2 }
    ::= { sapIngPlcrCtrlOvrEntry 4 }

-- ----------------------------------------------------
-- SAP ingress Policer Control Priority Level Override
-- ----------------------------------------------------
sapIngPlcrCtrlOvrLvlTblLastChgd OBJECT-TYPE
    SYNTAX       TimeStamp
    MAX-ACCESS   read-only
    STATUS       current
    DESCRIPTION
        "sapIngPlcrCtrlOvrLvlTblLastChgd indicates the timestamp of last change
        to the sapIngPlcrCtrlOvrLvlTable."
    ::= { tmnxSapObjs 82 }

sapIngPlcrCtrlOvrLvlTable OBJECT-TYPE
    SYNTAX          SEQUENCE OF SapIngPlcrCtrlOvrLvlEntry
    MAX-ACCESS      not-accessible
    STATUS          current
    DESCRIPTION     "A table that contains SAP ingress policer control
                     override information for the priority level."
    ::= { tmnxSapObjs 83 }

sapIngPlcrCtrlOvrLvlEntry OBJECT-TYPE
    SYNTAX          SapIngPlcrCtrlOvrLvlEntry
    MAX-ACCESS      not-accessible
    STATUS          current
    DESCRIPTION     "Policer control priority level override information about
                     a specific SAP on the ingress side.

                     Entries are created/deleted automatically by the system
                     when entries are created/delete in the
                     sapIngPlcrCtrlOvrTable."
    INDEX           { svcId, sapPortId, sapEncapValue, tQosPolicerLevel }
    ::= { sapIngPlcrCtrlOvrLvlTable 1 }

SapIngPlcrCtrlOvrLvlEntry ::=
    SEQUENCE {
        sapIngPlcrCtrlOvrLvlLastChgd      TimeStamp,
        sapIngPlcrCtrlOvrLvlMBS           TPlcrBurstSizeBytesOverride
    }

sapIngPlcrCtrlOvrLvlLastChgd OBJECT-TYPE
    SYNTAX       TimeStamp
    MAX-ACCESS   read-only
    STATUS       current
    DESCRIPTION
        "The value of sapIngPlcrCtrlOvrLvlLastChgd indicates the timestamp of
        last change to this row in sapIngPlcrCtrlOvrLvlTable."
    ::= { sapIngPlcrCtrlOvrLvlEntry 1 }

sapIngPlcrCtrlOvrLvlMBS OBJECT-TYPE
    SYNTAX       TPlcrBurstSizeBytesOverride
    UNITS        "bytes"
    MAX-ACCESS   read-create
    STATUS       current
    DESCRIPTION
        "The value of sapIngPlcrCtrlOvrLvlMBS specifies the maximum amount of
        cumulative buffer space (in bytes) allowed for this level by the
        policer of this sap."
    DEFVAL { -2 }
    ::= { sapIngPlcrCtrlOvrLvlEntry 2 }
                                
-- ------------------------------------
-- SAP ingress Policer Override
-- ------------------------------------
sapIngPlcrOvrTblLastChgd OBJECT-TYPE
    SYNTAX       TimeStamp
    MAX-ACCESS   read-only
    STATUS       current
    DESCRIPTION
        "sapIngPlcrOvrTblLastChgd indicates the timestamp of last change to
        the sapIngPlcrOvrTable."
    ::= { tmnxSapObjs 86 }

sapIngPlcrOvrTable OBJECT-TYPE
    SYNTAX          SEQUENCE OF SapIngPlcrOvrEntry
    MAX-ACCESS      not-accessible
    STATUS          current
    DESCRIPTION     "A table that contains SAP ingress policer control
                     override information."
    ::= { tmnxSapObjs 87 }

sapIngPlcrOvrEntry OBJECT-TYPE
    SYNTAX          SapIngPlcrOvrEntry
    MAX-ACCESS      not-accessible
    STATUS          current
    DESCRIPTION     "Policer control override information about a specific
                     policer of the SAP on the ingress side."
    INDEX           { svcId, sapPortId, sapEncapValue, tSapIngPolicerId }
    ::= { sapIngPlcrOvrTable 1 }

SapIngPlcrOvrEntry ::=
    SEQUENCE {
        sapIngPlcrOvrRowStatus        RowStatus,
        sapIngPlcrOvrLastChgd         TimeStamp,
        sapIngPlcrOvrAdminPIR         THPolPIRRateOverride,
        sapIngPlcrOvrAdminCIR         THPolCIRRateOverride,
        sapIngPlcrOvrStatMode         TmnxIngPolicerStatModeOverride,
        sapIngPlcrOvrMBS              TPlcrBurstSizeBytesOverride,
        sapIngPlcrOvrPktOffset        TPerPacketOffsetOvr,
        sapIngPlcrOvrCBS              TPlcrBurstSizeBytesOverride,
        sapIngPlcrOvrAdminPIRPercent  TPIRPercentOverride,
        sapIngPlcrOvrAdminCIRPercent  TCIRPercentOverride
    }

sapIngPlcrOvrRowStatus OBJECT-TYPE
    SYNTAX       RowStatus
    MAX-ACCESS   read-create
    STATUS       current
    DESCRIPTION
        "This is the Row Status of the entry.
        This allows creation/deletion of rows in this table."
    ::= { sapIngPlcrOvrEntry 1 }

sapIngPlcrOvrLastChgd OBJECT-TYPE
    SYNTAX       TimeStamp
    MAX-ACCESS   read-only
    STATUS       current
    DESCRIPTION
        "The value of sapIngPlcrOvrLastChgd indicates the timestamp of
        last change to this row in sapIngPlcrOvrTable."
    ::= { sapIngPlcrOvrEntry 2 }

sapIngPlcrOvrAdminPIR OBJECT-TYPE
    SYNTAX       THPolPIRRateOverride
    UNITS        "kbps"
    MAX-ACCESS   read-create
    STATUS       current
    DESCRIPTION
        "sapIngPlcrOvrAdminPIR specifies the administrative PIR specified by
        the user."
    DEFVAL { -2 }
    ::= { sapIngPlcrOvrEntry 3 }

sapIngPlcrOvrAdminCIR OBJECT-TYPE
    SYNTAX       THPolCIRRateOverride
    UNITS        "kbps"
    MAX-ACCESS   read-create
    STATUS       current
    DESCRIPTION
        "sapIngPlcrOvrAdminCIR specifies the administrative CIR specified by
        the user."
    DEFVAL { -2 }
    ::= { sapIngPlcrOvrEntry 4 }

sapIngPlcrOvrStatMode OBJECT-TYPE
    SYNTAX       TmnxIngPolicerStatModeOverride
    MAX-ACCESS   read-create
    STATUS       current
    DESCRIPTION
        "sapIngPlcrOvrStatMode specifies the mode of statistics collected by
        this policer on this sap."
    DEFVAL { noOverride }
    ::= { sapIngPlcrOvrEntry 5 }

sapIngPlcrOvrMBS OBJECT-TYPE
    SYNTAX       TPlcrBurstSizeBytesOverride
    UNITS        "bytes"
    MAX-ACCESS   read-create
    STATUS       current
    DESCRIPTION
        "sapIngPlcrOvrMBS specifies the maximum amount of buffer space
        (in bytes) allowed for the queue by this policer on this sap."
    DEFVAL { -2 }
    ::= { sapIngPlcrOvrEntry 6 }

sapIngPlcrOvrPktOffset OBJECT-TYPE
    SYNTAX       TPerPacketOffsetOvr
    UNITS        "bytes"
    MAX-ACCESS   read-create
    STATUS       current
    DESCRIPTION
        "sapIngPlcrOvrPktOffset specifies the packet byte offset for
        addition of policing information by this policer on this sap."
    DEFVAL { -128 }
    ::= { sapIngPlcrOvrEntry 7 }

sapIngPlcrOvrCBS OBJECT-TYPE
    SYNTAX       TPlcrBurstSizeBytesOverride
    UNITS        "bytes"
    MAX-ACCESS   read-create
    STATUS       current
    DESCRIPTION
        "sapIngPlcrOvrCBS specifies the amount of reserved buffer space
        (in bytes) for the queue set by this policer on this sap."
    DEFVAL { -2 }
    ::= { sapIngPlcrOvrEntry 8 }

sapIngPlcrOvrAdminPIRPercent OBJECT-TYPE
    SYNTAX          TPIRPercentOverride
    UNITS           "hundredths of a percent"
    MAX-ACCESS      read-create
    STATUS          current
    DESCRIPTION     "The value of sapIngPlcrOvrAdminPIRPercent specifies the 
                     desired administrative PIR value for this policer as 
                     a percentage."
    DEFVAL { -2 }
    ::= { sapIngPlcrOvrEntry 9 }

sapIngPlcrOvrAdminCIRPercent OBJECT-TYPE
    SYNTAX          TCIRPercentOverride
    UNITS           "hundredths of a percent"
    MAX-ACCESS      read-create
    STATUS          current
    DESCRIPTION     "The value of sapIngPlcrOvrAdminCIRPercent specifies the 
                     desired administrative CIR value for this policer 
                     as a percentage."
    DEFVAL { -2 }
    ::= { sapIngPlcrOvrEntry 10 }

-- ------------------------------------
-- SAP egress Policer Control Override
-- ------------------------------------
sapEgrPlcrCtrlOvrTblLastChgd OBJECT-TYPE
    SYNTAX       TimeStamp
    MAX-ACCESS   read-only
    STATUS       current
    DESCRIPTION
        "sapEgrPlcrCtrlOvrTblLastChgd indicates the timestamp of last change to
        the sapEgrPlcrCtrlOvrTable."
    ::= { tmnxSapObjs 88 }

sapEgrPlcrCtrlOvrTable OBJECT-TYPE
    SYNTAX          SEQUENCE OF SapEgrPlcrCtrlOvrEntry
    MAX-ACCESS      not-accessible
    STATUS          current
    DESCRIPTION     "A table that contains SAP egress policer control
                     override information."
    ::= { tmnxSapObjs 89 }

sapEgrPlcrCtrlOvrEntry OBJECT-TYPE
    SYNTAX          SapEgrPlcrCtrlOvrEntry
    MAX-ACCESS      not-accessible
    STATUS          current
    DESCRIPTION     "Policer control override information about a specific SAP
                     on the egress side."
    INDEX           { svcId, sapPortId, sapEncapValue }
    ::= { sapEgrPlcrCtrlOvrTable 1 }

SapEgrPlcrCtrlOvrEntry ::=
    SEQUENCE {
        sapEgrPlcrCtrlOvrRowStatus     RowStatus,
        sapEgrPlcrCtrlOvrLastChgd      TimeStamp,
        sapEgrPlcrCtrlOvrMaxRate       THPolPIRRateOverride,
        sapEgrPlcrCtrlOvrMinMBSSep     TPlcrBurstSizeBytesOverride
    }

sapEgrPlcrCtrlOvrRowStatus OBJECT-TYPE
    SYNTAX       RowStatus
    MAX-ACCESS   read-create
    STATUS       current
    DESCRIPTION
        "This is the Row Status of the entry.
        This allows creation/deletion of rows in this table."
    ::= { sapEgrPlcrCtrlOvrEntry 1 }

sapEgrPlcrCtrlOvrLastChgd OBJECT-TYPE
    SYNTAX       TimeStamp
    MAX-ACCESS   read-only
    STATUS       current
    DESCRIPTION
        "The value of sapEgrPlcrCtrlOvrLastChgd indicates the timestamp of
        last change to this row in sapEgrPlcrCtrlOvrTable."
    ::= { sapEgrPlcrCtrlOvrEntry 2 }

sapEgrPlcrCtrlOvrMaxRate OBJECT-TYPE
    SYNTAX       THPolPIRRateOverride
    UNITS        "kbps"
    MAX-ACCESS   read-create
    STATUS       current
    DESCRIPTION
        "The value of sapEgrPlcrCtrlOvrMaxRate specifies the
        maximum frame based bandwidth limit of this policer override."
    DEFVAL { -2 }
    ::= { sapEgrPlcrCtrlOvrEntry 3 }

sapEgrPlcrCtrlOvrMinMBSSep OBJECT-TYPE
    SYNTAX       TPlcrBurstSizeBytesOverride
    UNITS        "bytes"
    MAX-ACCESS   read-create
    STATUS       current
    DESCRIPTION
        "The value of sapEgrPlcrCtrlOvrMinMBSSep specifies the
        minimum amount of seperation buffer space (in bytes) allowed 
        by this policer override."
    DEFVAL { -2 }
    ::= { sapEgrPlcrCtrlOvrEntry 4 }

-- ----------------------------------------------------
-- SAP egress Policer Control Priority Level Override
-- ----------------------------------------------------
sapEgrPlcrCtrlOvrLvlTblLastChgd OBJECT-TYPE
    SYNTAX       TimeStamp
    MAX-ACCESS   read-only
    STATUS       current
    DESCRIPTION
        "sapEgrPlcrCtrlOvrLvlTblLastChgd indicates the timestamp of last change
        to the sapEgrPlcrCtrlOvrLvlTable."
    ::= { tmnxSapObjs 90 }

sapEgrPlcrCtrlOvrLvlTable OBJECT-TYPE
    SYNTAX          SEQUENCE OF SapEgrPlcrCtrlOvrLvlEntry
    MAX-ACCESS      not-accessible
    STATUS          current
    DESCRIPTION     "A table that contains SAP egress policer control
                     override information for the priority level."
    ::= { tmnxSapObjs 91 }

sapEgrPlcrCtrlOvrLvlEntry OBJECT-TYPE
    SYNTAX          SapEgrPlcrCtrlOvrLvlEntry
    MAX-ACCESS      not-accessible
    STATUS          current
    DESCRIPTION     "Policer control priority level override information about
                     a specific SAP on the egress side.

                     Entries are created/deleted automatically by the system
                     when entries are created/delete in the
                     sapEgrPlcrCtrlOvrTable."
    INDEX           { svcId, sapPortId, sapEncapValue, tQosPolicerLevel }
    ::= { sapEgrPlcrCtrlOvrLvlTable 1 }

SapEgrPlcrCtrlOvrLvlEntry ::=
    SEQUENCE {
        sapEgrPlcrCtrlOvrLvlLastChgd      TimeStamp,
        sapEgrPlcrCtrlOvrLvlMBS           TPlcrBurstSizeBytesOverride
    }

sapEgrPlcrCtrlOvrLvlLastChgd OBJECT-TYPE
    SYNTAX       TimeStamp
    MAX-ACCESS   read-only
    STATUS       current
    DESCRIPTION
        "The value of sapEgrPlcrCtrlOvrLvlLastChgd indicates the timestamp of
        last change to this row in sapEgrPlcrCtrlOvrLvlTable."
    ::= { sapEgrPlcrCtrlOvrLvlEntry 1 }

sapEgrPlcrCtrlOvrLvlMBS OBJECT-TYPE
    SYNTAX       TPlcrBurstSizeBytesOverride
    UNITS        "bytes"
    MAX-ACCESS   read-create
    STATUS       current
    DESCRIPTION
        "The value of sapEgrPlcrCtrlOvrLvlMBS specifies the maximum amount of
        cumulative buffer space (in bytes) allowed for this level by the
        policer of this sap."
    DEFVAL { -2 }
    ::= { sapEgrPlcrCtrlOvrLvlEntry 2 }
                                
-- ------------------------------------
-- SAP egress Policer Override
-- ------------------------------------
sapEgrPlcrOvrTblLastChgd OBJECT-TYPE
    SYNTAX       TimeStamp
    MAX-ACCESS   read-only
    STATUS       current
    DESCRIPTION
        "sapEgrPlcrOvrTblLastChgd indicates the timestamp of last change to
        the sapEgrPlcrOvrTable."
    ::= { tmnxSapObjs 94 }

sapEgrPlcrOvrTable OBJECT-TYPE
    SYNTAX          SEQUENCE OF SapEgrPlcrOvrEntry
    MAX-ACCESS      not-accessible
    STATUS          current
    DESCRIPTION     "A table that contains SAP egress policer control
                     override information."
    ::= { tmnxSapObjs 95 }

sapEgrPlcrOvrEntry OBJECT-TYPE
    SYNTAX          SapEgrPlcrOvrEntry
    MAX-ACCESS      not-accessible
    STATUS          current
    DESCRIPTION     "Policer control override information about a specific
                     policer of the SAP on the egress side."
    INDEX           { svcId, sapPortId, sapEncapValue, tSapEgrPolicerId }
    ::= { sapEgrPlcrOvrTable 1 }

SapEgrPlcrOvrEntry ::=
    SEQUENCE {
        sapEgrPlcrOvrRowStatus        RowStatus,
        sapEgrPlcrOvrLastChgd         TimeStamp,
        sapEgrPlcrOvrAdminPIR         THPolPIRRateOverride,
        sapEgrPlcrOvrAdminCIR         THPolCIRRateOverride,
        sapEgrPlcrOvrStatMode         TmnxEgrPolicerStatModeOverride,
        sapEgrPlcrOvrMBS              TPlcrBurstSizeBytesOverride,
        sapEgrPlcrOvrPktOffset        TEgressPerPacketOffsetOvr,
        sapEgrPlcrOvrCBS              TPlcrBurstSizeBytesOverride,
        sapEgrPlcrOvrAdminPIRPercent  TPIRPercentOverride,
        sapEgrPlcrOvrAdminCIRPercent  TCIRPercentOverride
    }

sapEgrPlcrOvrRowStatus OBJECT-TYPE
    SYNTAX       RowStatus
    MAX-ACCESS   read-create
    STATUS       current
    DESCRIPTION
        "This is the Row Status of the entry.
        This allows creation/deletion of rows in this table."
    ::= { sapEgrPlcrOvrEntry 1 }

sapEgrPlcrOvrLastChgd OBJECT-TYPE
    SYNTAX       TimeStamp
    MAX-ACCESS   read-only
    STATUS       current
    DESCRIPTION
        "The value of sapEgrPlcrOvrLastChgd indicates the timestamp of
        last change to this row in sapEgrPlcrOvrTable."
    ::= { sapEgrPlcrOvrEntry 2 }

sapEgrPlcrOvrAdminPIR OBJECT-TYPE
    SYNTAX       THPolPIRRateOverride
    UNITS        "kbps"
    MAX-ACCESS   read-create
    STATUS       current
    DESCRIPTION
        "sapEgrPlcrOvrAdminPIR specifies the administrative PIR specified by
        the user."
    DEFVAL { -2 }
    ::= { sapEgrPlcrOvrEntry 3 }

sapEgrPlcrOvrAdminCIR OBJECT-TYPE
    SYNTAX       THPolCIRRateOverride
    UNITS        "kbps"
    MAX-ACCESS   read-create
    STATUS       current
    DESCRIPTION
        "sapEgrPlcrOvrAdminCIR specifies the administrative CIR specified by
        the user."
    DEFVAL { -2 }
    ::= { sapEgrPlcrOvrEntry 4 }

sapEgrPlcrOvrStatMode OBJECT-TYPE
    SYNTAX       TmnxEgrPolicerStatModeOverride
    MAX-ACCESS   read-create
    STATUS       current
    DESCRIPTION
        "sapEgrPlcrOvrStatMode specifies the mode of statistics collected by
        this policer on this sap."
    DEFVAL { noOverride }
    ::= { sapEgrPlcrOvrEntry 5 }

sapEgrPlcrOvrMBS OBJECT-TYPE
    SYNTAX       TPlcrBurstSizeBytesOverride
    UNITS        "bytes"
    MAX-ACCESS   read-create
    STATUS       current
    DESCRIPTION
        "sapEgrPlcrOvrMBS specifies the maximum amount of buffer space
        (in bytes) allowed for the queue by this policer on this sap."
    DEFVAL { -2 }
    ::= { sapEgrPlcrOvrEntry 6 }

sapEgrPlcrOvrPktOffset OBJECT-TYPE
    SYNTAX       TEgressPerPacketOffsetOvr
    MAX-ACCESS   read-create
    STATUS       current
    DESCRIPTION
        "sapEgrPlcrOvrPktOffset specifies the packet byte offset for
        addition of policing information by this policer on this sap."
    DEFVAL { -128 }
    ::= { sapEgrPlcrOvrEntry 7 }

sapEgrPlcrOvrCBS OBJECT-TYPE
    SYNTAX       TPlcrBurstSizeBytesOverride
    UNITS        "bytes"
    MAX-ACCESS   read-create
    STATUS       current
    DESCRIPTION
        "sapEgrPlcrOvrCBS specifies the amount of reserved buffer space
        (in bytes) for the queue set by this policer on this sap."
    DEFVAL { -2 }
    ::= { sapEgrPlcrOvrEntry 8 }

sapEgrPlcrOvrAdminPIRPercent OBJECT-TYPE
    SYNTAX          TPIRPercentOverride
    UNITS           "hundredths of a percent"
    MAX-ACCESS      read-create
    STATUS          current
    DESCRIPTION     "The value of sapEgrPlcrOvrAdminPIRPercent specifies the 
                     desired administrative PIR value for this policer 
                     as a percentage."
    DEFVAL { -2 }
    ::= { sapEgrPlcrOvrEntry 9 }

sapEgrPlcrOvrAdminCIRPercent OBJECT-TYPE
    SYNTAX          TCIRPercentOverride
    UNITS           "hundredths of a percent"
    MAX-ACCESS      read-create
    STATUS          current
    DESCRIPTION     "The value of sapEgrPlcrOvrAdminCIRPercent specifies the 
                     desired administrative CIR value for this policer 
                     as a percentage."
    DEFVAL { -2 }
    ::= { sapEgrPlcrOvrEntry 10 }

-- ----------------------------------------
-- Ingress QoS Policer SAP Statistics Table
-- ----------------------------------------
sapIngQosPolicerStatsTable OBJECT-TYPE
    SYNTAX          SEQUENCE OF SapIngQosPolicerStatsEntry
    MAX-ACCESS      not-accessible
    STATUS          current
    DESCRIPTION     "A table that contains ingress QoS policer SAP statistics."
    ::= { tmnxSapObjs 96 }

sapIngQosPolicerStatsEntry OBJECT-TYPE
    SYNTAX          SapIngQosPolicerStatsEntry
    MAX-ACCESS      not-accessible
    STATUS          current
    DESCRIPTION     "Ingress statistics about a specific SAP's QoS policer."
    INDEX           { svcId, sapPortId, sapEncapValue, sapIngQosPStatsPolId }
    ::= { sapIngQosPolicerStatsTable 1 }

SapIngQosPolicerStatsEntry ::=
    SEQUENCE {
        sapIngQosPStatsPolId             TIngressPolicerId,
        sapIngQosPStatsCustId            TmnxCustId,
        sapIngQosPStatsMode              TmnxIngPolicerStatMode,
        sapIngQosPStatsOffHiPrioPkts     Counter64,
        sapIngQosPStatsOffHiPrioPktsLo   Counter32,
        sapIngQosPStatsOffHiPrioPktsHi   Counter32,
        sapIngQosPStatsDrpHiPrioPkts     Counter64,
        sapIngQosPStatsDrpHiPrioPktsLo   Counter32,
        sapIngQosPStatsDrpHiPrioPktsHi   Counter32,
        sapIngQosPStatsOffLoPrioPkts     Counter64,
        sapIngQosPStatsOffLoPrioPktsLo   Counter32,
        sapIngQosPStatsOffLoPrioPktsHi   Counter32,
        sapIngQosPStatsDrpLoPrioPkts     Counter64,
        sapIngQosPStatsDrpLoPrioPktsLo   Counter32,
        sapIngQosPStatsDrpLoPrioPktsHi   Counter32,
        sapIngQosPStatsOffHiPrioOcts     Counter64,
        sapIngQosPStatsOffHiPrioOctsLo   Counter32,
        sapIngQosPStatsOffHiPrioOctsHi   Counter32,
        sapIngQosPStatsDrpHiPrioOcts     Counter64,
        sapIngQosPStatsDrpHiPrioOctsLo   Counter32,
        sapIngQosPStatsDrpHiPrioOctsHi   Counter32,
        sapIngQosPStatsOffLoPrioOcts     Counter64,
        sapIngQosPStatsOffLoPrioOctsLo   Counter32,
        sapIngQosPStatsOffLoPrioOctsHi   Counter32,
        sapIngQosPStatsDrpLoPrioOcts     Counter64,
        sapIngQosPStatsDrpLoPrioOctsLo   Counter32,
        sapIngQosPStatsDrpLoPrioOctsHi   Counter32,
        sapIngQosPStatsFwdInProfPkts     Counter64,
        sapIngQosPStatsFwdInProfPktsLo   Counter32,
        sapIngQosPStatsFwdInProfPktsHi   Counter32,
        sapIngQosPStatsFwdOutProfPkts    Counter64,
        sapIngQosPStatsFwdOutProfPktsLo  Counter32,
        sapIngQosPStatsFwdOutProfPktsHi  Counter32,
        sapIngQosPStatsFwdInProfOcts     Counter64,
        sapIngQosPStatsFwdInProfOctsLo   Counter32,
        sapIngQosPStatsFwdInProfOctsHi   Counter32,
        sapIngQosPStatsFwdOutProfOcts    Counter64,
        sapIngQosPStatsFwdOutProfOctsLo  Counter32,
        sapIngQosPStatsFwdOutProfOctsHi  Counter32,
        sapIngQosPStatsUncolPktsOff      Counter64,
        sapIngQosPStatsUncolPktsOffLo    Counter32,
        sapIngQosPStatsUncolPktsOffHi    Counter32,
        sapIngQosPStatsUncolOctsOff      Counter64,
        sapIngQosPStatsUncolOctsOffLo    Counter32,
        sapIngQosPStatsUncolOctsOffHi    Counter32
    }

sapIngQosPStatsPolId OBJECT-TYPE
    SYNTAX          TIngressPolicerId
    MAX-ACCESS      not-accessible
    STATUS          current
    DESCRIPTION     "The index of the ingress QoS policer of this SAP."
    ::= { sapIngQosPolicerStatsEntry 1 }

sapIngQosPStatsCustId OBJECT-TYPE
    SYNTAX          TmnxCustId
    MAX-ACCESS      read-only
    STATUS          current
    DESCRIPTION     "The Customer ID for the associated service."
    ::= { sapIngQosPolicerStatsEntry 2 }

sapIngQosPStatsMode OBJECT-TYPE
    SYNTAX      TmnxIngPolicerStatMode
    MAX-ACCESS  read-only
    STATUS      current
    DESCRIPTION
        "The value of sapIngQosPStatsMode indicates the stat mode used by the policer."
    ::= { sapIngQosPolicerStatsEntry 3 }

sapIngQosPStatsOffHiPrioPkts OBJECT-TYPE
    SYNTAX          Counter64
    MAX-ACCESS      read-only
    STATUS          current
    DESCRIPTION     "The number of high priority packets,
                     as determined by the SAP ingress QoS
                     policy, offered by the Pchip to the
                     Qchip."
    ::= { sapIngQosPolicerStatsEntry 4 }

sapIngQosPStatsOffHiPrioPktsLo OBJECT-TYPE
    SYNTAX          Counter32
    MAX-ACCESS      read-only
    STATUS          current
    DESCRIPTION     "Lower 32 bits of sapIngQosPStatsOffHiPrioPkts."
    ::= { sapIngQosPolicerStatsEntry 5 }

sapIngQosPStatsOffHiPrioPktsHi OBJECT-TYPE
    SYNTAX          Counter32
    MAX-ACCESS      read-only
    STATUS          current
    DESCRIPTION     "Upper 32 bits of sapIngQosPStatsOffHiPrioPkts."
    ::= { sapIngQosPolicerStatsEntry 6 }

sapIngQosPStatsDrpHiPrioPkts OBJECT-TYPE
    SYNTAX          Counter64
    MAX-ACCESS      read-only
    STATUS          current
    DESCRIPTION     "The number of high priority packets,
                     as determined by the SAP ingress QoS
                     policy, dropped by the Pchip due to:
                     MBS exceeded, buffer pool limit
                     exceeded, etc."
    ::= { sapIngQosPolicerStatsEntry 7 }

sapIngQosPStatsDrpHiPrioPktsLo OBJECT-TYPE
    SYNTAX          Counter32
    MAX-ACCESS      read-only
    STATUS          current
    DESCRIPTION     "Lower 32 bits of sapIngQosPStatsDrpHiPrioPkts."
    ::= { sapIngQosPolicerStatsEntry 8 }

sapIngQosPStatsDrpHiPrioPktsHi OBJECT-TYPE
    SYNTAX          Counter32
    MAX-ACCESS      read-only
    STATUS          current
    DESCRIPTION     "Upper 32 bits of sapIngQosPStatsDrpHiPrioPkts."
    ::= { sapIngQosPolicerStatsEntry 9 }

sapIngQosPStatsOffLoPrioPkts OBJECT-TYPE
    SYNTAX          Counter64
    MAX-ACCESS      read-only
    STATUS          current
    DESCRIPTION     "The number of low priority packets,
                     as determined by the SAP ingress QoS
                     policy, offered by the Pchip to the
                     Qchip."
    ::= { sapIngQosPolicerStatsEntry 10 }

sapIngQosPStatsOffLoPrioPktsLo OBJECT-TYPE
    SYNTAX          Counter32
    MAX-ACCESS      read-only
    STATUS          current
    DESCRIPTION     "Lower 32 bits of sapIngQosPStatsOffLoPrioPkts."
    ::= { sapIngQosPolicerStatsEntry 11 }

sapIngQosPStatsOffLoPrioPktsHi OBJECT-TYPE
    SYNTAX          Counter32
    MAX-ACCESS      read-only
    STATUS          current
    DESCRIPTION     "Upper 32 bits of sapIngQosPStatsOffLoPrioPkts."
    ::= { sapIngQosPolicerStatsEntry 12 }

sapIngQosPStatsDrpLoPrioPkts OBJECT-TYPE
    SYNTAX          Counter64
    MAX-ACCESS      read-only
    STATUS          current
    DESCRIPTION     "The number of low priority packets,
                     as determined by the SAP ingress QoS
                     policy, dropped by the Pchip due to:
                     MBS exceeded, buffer pool limit
                     exceeded, etc."
    ::= { sapIngQosPolicerStatsEntry 13 }

sapIngQosPStatsDrpLoPrioPktsLo OBJECT-TYPE
    SYNTAX          Counter32
    MAX-ACCESS      read-only
    STATUS          current
    DESCRIPTION     "Lower 32 bits of sapIngQosPStatsDrpLoPrioPkts."
    ::= { sapIngQosPolicerStatsEntry 14 }

sapIngQosPStatsDrpLoPrioPktsHi OBJECT-TYPE
    SYNTAX          Counter32
    MAX-ACCESS      read-only
    STATUS          current
    DESCRIPTION     "Upper 32 bits of sapIngQosPStatsDrpLoPrioPkts."
    ::= { sapIngQosPolicerStatsEntry 15 }

sapIngQosPStatsOffHiPrioOcts OBJECT-TYPE
    SYNTAX          Counter64
    MAX-ACCESS      read-only
    STATUS          current
    DESCRIPTION     "The number of high priority octets,
                     as determined by the SAP ingress QoS
                     policy, offered by the Pchip to the
                     Qchip."
    ::= { sapIngQosPolicerStatsEntry 16 }

sapIngQosPStatsOffHiPrioOctsLo OBJECT-TYPE
    SYNTAX          Counter32
    MAX-ACCESS      read-only
    STATUS          current
    DESCRIPTION     "Lower 32 bits of sapIngQosPStatsOffHiPrioOcts."
    ::= { sapIngQosPolicerStatsEntry 17 }

sapIngQosPStatsOffHiPrioOctsHi OBJECT-TYPE
    SYNTAX          Counter32
    MAX-ACCESS      read-only
    STATUS          current
    DESCRIPTION     "Upper 32 bits of sapIngQosPStatsOffHiPrioOcts."
    ::= { sapIngQosPolicerStatsEntry 18 }

sapIngQosPStatsDrpHiPrioOcts OBJECT-TYPE
    SYNTAX          Counter64
    MAX-ACCESS      read-only
    STATUS          current
    DESCRIPTION     "The number of high priority octets,
                     as determined by the SAP ingress QoS
                     policy, dropped by the Pchip due to:
                     MBS exceeded, buffer pool limit
                     exceeded, etc."
    ::= { sapIngQosPolicerStatsEntry 19 }

sapIngQosPStatsDrpHiPrioOctsLo OBJECT-TYPE
    SYNTAX          Counter32
    MAX-ACCESS      read-only
    STATUS          current
    DESCRIPTION     "Lower 32 bits of sapIngQosPStatsDrpHiPrioOcts."
    ::= { sapIngQosPolicerStatsEntry 20 }

sapIngQosPStatsDrpHiPrioOctsHi OBJECT-TYPE
    SYNTAX          Counter32
    MAX-ACCESS      read-only
    STATUS          current
    DESCRIPTION     "Upper 32 bits of sapIngQosPStatsDrpHiPrioOcts."
    ::= { sapIngQosPolicerStatsEntry 21 }

sapIngQosPStatsOffLoPrioOcts OBJECT-TYPE
    SYNTAX          Counter64
    MAX-ACCESS      read-only
    STATUS          current
    DESCRIPTION     "The number of low priority octets,
                     as determined by the SAP ingress QoS
                     policy, offered by the Pchip to the
                     Pchip."
    ::= { sapIngQosPolicerStatsEntry 22 }

sapIngQosPStatsOffLoPrioOctsLo OBJECT-TYPE
    SYNTAX          Counter32
    MAX-ACCESS      read-only
    STATUS          current
    DESCRIPTION     "Lower 32 bits of sapIngQosPStatsOffLoPrioOcts."
    ::= { sapIngQosPolicerStatsEntry 23 }

sapIngQosPStatsOffLoPrioOctsHi OBJECT-TYPE
    SYNTAX          Counter32
    MAX-ACCESS      read-only
    STATUS          current
    DESCRIPTION     "Upper 32 bits of sapIngQosPStatsOffLoPrioOcts."
    ::= { sapIngQosPolicerStatsEntry 24 }

sapIngQosPStatsDrpLoPrioOcts OBJECT-TYPE
    SYNTAX          Counter64
    MAX-ACCESS      read-only
    STATUS          current
    DESCRIPTION     "The number of low priority octets,
                     as determined by the SAP ingress QoS
                     policy, dropped by the Pchip due to:
                     MBS exceeded, buffer pool limit
                     exceeded, etc."
    ::= { sapIngQosPolicerStatsEntry 25 }

sapIngQosPStatsDrpLoPrioOctsLo OBJECT-TYPE
    SYNTAX          Counter32
    MAX-ACCESS      read-only
    STATUS          current
    DESCRIPTION     "Lower 32 bits of sapIngQosPStatsDrpLoPrioOcts."
    ::= { sapIngQosPolicerStatsEntry 26 }

sapIngQosPStatsDrpLoPrioOctsHi OBJECT-TYPE
    SYNTAX          Counter32
    MAX-ACCESS      read-only
    STATUS          current
    DESCRIPTION     "Upper 32 bits of sapIngQosPStatsDrpLoPrioOcts."
    ::= { sapIngQosPolicerStatsEntry 27 }

sapIngQosPStatsFwdInProfPkts OBJECT-TYPE
    SYNTAX          Counter64
    MAX-ACCESS      read-only
    STATUS          current
    DESCRIPTION     "The number of in-profile packets
                     (rate below CIR) forwarded by the
                     ingress Pchip."
    ::= { sapIngQosPolicerStatsEntry 28 }

sapIngQosPStatsFwdInProfPktsLo OBJECT-TYPE
    SYNTAX          Counter32
    MAX-ACCESS      read-only
    STATUS          current
    DESCRIPTION     "Lower 32 bits of sapIngQosPStatsFwdInProfPkts."
    ::= { sapIngQosPolicerStatsEntry 29 }

sapIngQosPStatsFwdInProfPktsHi OBJECT-TYPE
    SYNTAX          Counter32
    MAX-ACCESS      read-only
    STATUS          current
    DESCRIPTION     "Upper 32 bits of sapIngQosPStatsFwdInProfPkts."
    ::= { sapIngQosPolicerStatsEntry 30 }

sapIngQosPStatsFwdOutProfPkts OBJECT-TYPE
    SYNTAX          Counter64
    MAX-ACCESS      read-only
    STATUS          current
    DESCRIPTION     "The number of out-of-profile packets
                     (rate above CIR) forwarded by the
                     ingress Pchip."
    ::= { sapIngQosPolicerStatsEntry 31 }

sapIngQosPStatsFwdOutProfPktsLo OBJECT-TYPE
    SYNTAX          Counter32
    MAX-ACCESS      read-only
    STATUS          current
    DESCRIPTION     "Lower 32 bits of sapIngQosPStatsFwdOutProfPkts."
    ::= { sapIngQosPolicerStatsEntry 32 }

sapIngQosPStatsFwdOutProfPktsHi OBJECT-TYPE
    SYNTAX          Counter32
    MAX-ACCESS      read-only
    STATUS          current
    DESCRIPTION     "Upper 32 bits of sapIngQosPStatsFwdOutProfPkts."
    ::= { sapIngQosPolicerStatsEntry 33 }

sapIngQosPStatsFwdInProfOcts OBJECT-TYPE
    SYNTAX          Counter64
    MAX-ACCESS      read-only
    STATUS          current
    DESCRIPTION     "The number of in-profile octets
                     (rate below CIR) forwarded by the
                     ingress Pchip."
    ::= { sapIngQosPolicerStatsEntry 34 }

sapIngQosPStatsFwdInProfOctsLo OBJECT-TYPE
    SYNTAX          Counter32
    MAX-ACCESS      read-only
    STATUS          current
    DESCRIPTION     "Lower 32 bits of sapIngQosPStatsFwdInProfOcts."
    ::= { sapIngQosPolicerStatsEntry 35 }

sapIngQosPStatsFwdInProfOctsHi OBJECT-TYPE
    SYNTAX          Counter32
    MAX-ACCESS      read-only
    STATUS          current
    DESCRIPTION     "Upper 32 bits of sapIngQosPStatsFwdInProfOcts."
    ::= { sapIngQosPolicerStatsEntry 36 }

sapIngQosPStatsFwdOutProfOcts OBJECT-TYPE
    SYNTAX          Counter64
    MAX-ACCESS      read-only
    STATUS          current
    DESCRIPTION     "The number of out-of-profile octets
                     (rate above CIR) forwarded by the
                     ingress Pchip."
    ::= { sapIngQosPolicerStatsEntry 37 }

sapIngQosPStatsFwdOutProfOctsLo OBJECT-TYPE
    SYNTAX          Counter32
    MAX-ACCESS      read-only
    STATUS          current
    DESCRIPTION     "Lower 32 bits of sapIngQosPStatsFwdOutProfOcts."
    ::= { sapIngQosPolicerStatsEntry 38 }

sapIngQosPStatsFwdOutProfOctsHi OBJECT-TYPE
    SYNTAX          Counter32
    MAX-ACCESS      read-only
    STATUS          current
    DESCRIPTION     "Upper 32 bits of sapIngQosPStatsFwdOutProfOcts."
    ::= { sapIngQosPolicerStatsEntry 39 }

sapIngQosPStatsUncolPktsOff OBJECT-TYPE
    SYNTAX          Counter64
    MAX-ACCESS      read-only
    STATUS          current
    DESCRIPTION     "The number of uncolored packets offered to the ingress Pchip."
    ::= { sapIngQosPolicerStatsEntry 40 }

sapIngQosPStatsUncolPktsOffLo OBJECT-TYPE
    SYNTAX          Counter32
    MAX-ACCESS      read-only
    STATUS          current
    DESCRIPTION     "Lower 32 bits of sapIngQosPStatsUncolPktsOff."
    ::= { sapIngQosPolicerStatsEntry 41 }

sapIngQosPStatsUncolPktsOffHi OBJECT-TYPE
    SYNTAX          Counter32
    MAX-ACCESS      read-only
    STATUS          current
    DESCRIPTION     "Upper 32 bits of sapIngQosPStatsUncolPktsOff."
    ::= { sapIngQosPolicerStatsEntry 42 }

sapIngQosPStatsUncolOctsOff OBJECT-TYPE
    SYNTAX          Counter64
    MAX-ACCESS      read-only
    STATUS          current
    DESCRIPTION     "The number of uncolored octets offered to the ingress Pchip."
    ::= { sapIngQosPolicerStatsEntry 43 }

sapIngQosPStatsUncolOctsOffLo OBJECT-TYPE
    SYNTAX          Counter32
    MAX-ACCESS      read-only
    STATUS          current
    DESCRIPTION     "Lower 32 bits of sapIngQosPStatsUncolOctsOff."
    ::= { sapIngQosPolicerStatsEntry 44 }

sapIngQosPStatsUncolOctsOffHi OBJECT-TYPE
    SYNTAX          Counter32
    MAX-ACCESS      read-only
    STATUS          current
    DESCRIPTION     "Upper 32 bits of sapIngQosPStatsUncolOctsOff."
    ::= { sapIngQosPolicerStatsEntry 45 }

-- ----------------------------------------
-- Egress QoS Policer SAP Statistics Table
-- ----------------------------------------
sapEgrQosPolicerStatsTable OBJECT-TYPE
    SYNTAX          SEQUENCE OF SapEgrQosPolicerStatsEntry
    MAX-ACCESS      not-accessible
    STATUS          current
    DESCRIPTION     "A table that contains egress QoS policer SAP statistics."
    ::= { tmnxSapObjs 97 }

sapEgrQosPolicerStatsEntry OBJECT-TYPE
    SYNTAX          SapEgrQosPolicerStatsEntry
    MAX-ACCESS      not-accessible
    STATUS          current
    DESCRIPTION     "Egress statistics about a specific SAP's QoS policer."
    INDEX           { svcId, 
                      sapPortId, 
                      sapEncapValue, 
                      sapEgrQosPStatsPolId }
    ::= { sapEgrQosPolicerStatsTable 1 }

SapEgrQosPolicerStatsEntry ::=
    SEQUENCE {
        sapEgrQosPStatsPolId             TEgressPolicerId,
        sapEgrQosPStatsCustId            TmnxCustId,
        sapEgrQosPStatsMode              TmnxEgrPolicerStatMode,
        sapEgrQosPStatsOffInProfPkts     Counter64,
        sapEgrQosPStatsOffInProfPktsLo   Counter32,
        sapEgrQosPStatsOffInProfPktsHi   Counter32,
        sapEgrQosPStatsFwdInProfPkts     Counter64,
        sapEgrQosPStatsFwdInProfPktsLo   Counter32,
        sapEgrQosPStatsFwdInProfPktsHi   Counter32,
        sapEgrQosPStatsDrpInProfPkts     Counter64,
        sapEgrQosPStatsDrpInProfPktsLo   Counter32,
        sapEgrQosPStatsDrpInProfPktsHi   Counter32,
        sapEgrQosPStatsOffOutProfPkts    Counter64,
        sapEgrQosPStatsOffOutProfPktsLo  Counter32,
        sapEgrQosPStatsOffOutProfPktsHi  Counter32,
        sapEgrQosPStatsFwdOutProfPkts    Counter64,
        sapEgrQosPStatsFwdOutProfPktsLo  Counter32,
        sapEgrQosPStatsFwdOutProfPktsHi  Counter32,
        sapEgrQosPStatsDrpOutProfPkts    Counter64,
        sapEgrQosPStatsDrpOutProfPktsLo  Counter32,
        sapEgrQosPStatsDrpOutProfPktsHi  Counter32,
        sapEgrQosPStatsOffInProfOcts     Counter64,
        sapEgrQosPStatsOffInProfOctsLo   Counter32,
        sapEgrQosPStatsOffInProfOctsHi   Counter32,
        sapEgrQosPStatsFwdInProfOcts     Counter64,
        sapEgrQosPStatsFwdInProfOctsLo   Counter32,
        sapEgrQosPStatsFwdInProfOctsHi   Counter32,
        sapEgrQosPStatsDrpInProfOcts     Counter64,
        sapEgrQosPStatsDrpInProfOctsLo   Counter32,
        sapEgrQosPStatsDrpInProfOctsHi   Counter32,
        sapEgrQosPStatsOffOutProfOcts    Counter64,
        sapEgrQosPStatsOffOutProfOctsLo  Counter32,
        sapEgrQosPStatsOffOutProfOctsHi  Counter32,
        sapEgrQosPStatsFwdOutProfOcts    Counter64,
        sapEgrQosPStatsFwdOutProfOctsLo  Counter32,
        sapEgrQosPStatsFwdOutProfOctsHi  Counter32,
        sapEgrQosPStatsDrpOutProfOcts    Counter64,
        sapEgrQosPStatsDrpOutProfOctsLo  Counter32,
        sapEgrQosPStatsDrpOutProfOctsHi  Counter32,
        sapEgrQosPStatsUncolPktsOff      Counter64,
        sapEgrQosPStatsUncolPktsOffLo    Counter32,
        sapEgrQosPStatsUncolPktsOffHi    Counter32,
        sapEgrQosPStatsUncolOctsOff      Counter64,
        sapEgrQosPStatsUncolOctsOffLo    Counter32,
        sapEgrQosPStatsUncolOctsOffHi    Counter32
    }

sapEgrQosPStatsPolId OBJECT-TYPE
    SYNTAX          TEgressPolicerId
    MAX-ACCESS      not-accessible
    STATUS          current
    DESCRIPTION     "The index of the egress QoS queue of this SAP."
    ::= { sapEgrQosPolicerStatsEntry 1 }

sapEgrQosPStatsCustId OBJECT-TYPE
    SYNTAX          TmnxCustId
    MAX-ACCESS      read-only
    STATUS          current
    DESCRIPTION     "The Customer ID for the associated service."
    ::= { sapEgrQosPolicerStatsEntry 2 }

sapEgrQosPStatsMode OBJECT-TYPE
    SYNTAX      TmnxEgrPolicerStatMode
    MAX-ACCESS  read-only
    STATUS      current
    DESCRIPTION
        "The value of sapEgrQosPStatsMode indicates the stat mode used by the policer."
    ::= { sapEgrQosPolicerStatsEntry 3 }

sapEgrQosPStatsOffInProfPkts OBJECT-TYPE
    SYNTAX          Counter64
    MAX-ACCESS      read-only
    STATUS          current
    DESCRIPTION     "The number of in-profile packets
                     (rate below CIR) offered by the
                     egress Pchip."
    ::= { sapEgrQosPolicerStatsEntry 4 }

sapEgrQosPStatsOffInProfPktsLo OBJECT-TYPE
    SYNTAX          Counter32
    MAX-ACCESS      read-only
    STATUS          current
    DESCRIPTION     "Lower 32 bits of sapEgrQosPStatsOffInProfPkts."
    ::= { sapEgrQosPolicerStatsEntry 5 }

sapEgrQosPStatsOffInProfPktsHi OBJECT-TYPE
    SYNTAX          Counter32
    MAX-ACCESS      read-only
    STATUS          current
    DESCRIPTION     "Upper 32 bits of sapEgrQosPStatsOffInProfPkts."
    ::= { sapEgrQosPolicerStatsEntry 6 }

sapEgrQosPStatsFwdInProfPkts OBJECT-TYPE
    SYNTAX          Counter64
    MAX-ACCESS      read-only
    STATUS          current
    DESCRIPTION     "The number of in-profile packets
                     (rate below CIR) forwarded by the
                     egress Pchip."
    ::= { sapEgrQosPolicerStatsEntry 7 }

sapEgrQosPStatsFwdInProfPktsLo OBJECT-TYPE
    SYNTAX          Counter32
    MAX-ACCESS      read-only
    STATUS          current
    DESCRIPTION     "Lower 32 bits of sapEgrQosPStatsFwdInProfPkts."
    ::= { sapEgrQosPolicerStatsEntry 8 }

sapEgrQosPStatsFwdInProfPktsHi OBJECT-TYPE
    SYNTAX          Counter32
    MAX-ACCESS      read-only
    STATUS          current
    DESCRIPTION     "Upper 32 bits of sapEgrQosPStatsFwdInProfPkts."
    ::= { sapEgrQosPolicerStatsEntry 9 }

sapEgrQosPStatsDrpInProfPkts OBJECT-TYPE
    SYNTAX          Counter64
    MAX-ACCESS      read-only
    STATUS          current
    DESCRIPTION     "The number of in-profile packets
                     discarded by the egress Pchip due
                     to: MBS exceeded, buffer pool limit
                     exceeded, etc."
    ::= { sapEgrQosPolicerStatsEntry 10 }

sapEgrQosPStatsDrpInProfPktsLo OBJECT-TYPE
    SYNTAX          Counter32
    MAX-ACCESS      read-only
    STATUS          current
    DESCRIPTION     "Lower 32 bits of sapEgrQosPStatsDrpInProfPkts."
    ::= { sapEgrQosPolicerStatsEntry 11 }

sapEgrQosPStatsDrpInProfPktsHi OBJECT-TYPE
    SYNTAX          Counter32
    MAX-ACCESS      read-only
    STATUS          current
    DESCRIPTION     "Upper 32 bits of sapEgrQosPStatsDrpInProfPkts."
    ::= { sapEgrQosPolicerStatsEntry 12 }

sapEgrQosPStatsOffOutProfPkts OBJECT-TYPE
    SYNTAX          Counter64
    MAX-ACCESS      read-only
    STATUS          current
    DESCRIPTION     "The number of out-of-profile packets
                     (rate above CIR) offered by the
                     egress Pchip."
    ::= { sapEgrQosPolicerStatsEntry 13 }

sapEgrQosPStatsOffOutProfPktsLo OBJECT-TYPE
    SYNTAX          Counter32
    MAX-ACCESS      read-only
    STATUS          current
    DESCRIPTION     "Lower 32 bits of sapEgrQosPStatsOffOutProfPkts."
    ::= { sapEgrQosPolicerStatsEntry 14 }

sapEgrQosPStatsOffOutProfPktsHi OBJECT-TYPE
    SYNTAX          Counter32
    MAX-ACCESS      read-only
    STATUS          current
    DESCRIPTION     "Upper 32 bits of sapEgrQosPStatsOffOutProfPkts."
    ::= { sapEgrQosPolicerStatsEntry 15 }

sapEgrQosPStatsFwdOutProfPkts OBJECT-TYPE
    SYNTAX          Counter64
    MAX-ACCESS      read-only
    STATUS          current
    DESCRIPTION     "The number of out-of-profile packets
                     (rate above CIR) forwarded by the
                     egress Pchip."
    ::= { sapEgrQosPolicerStatsEntry 16 }

sapEgrQosPStatsFwdOutProfPktsLo OBJECT-TYPE
    SYNTAX          Counter32
    MAX-ACCESS      read-only
    STATUS          current
    DESCRIPTION     "Lower 32 bits of sapEgrQosPStatsFwdOutProfPkts."
    ::= { sapEgrQosPolicerStatsEntry 17 }

sapEgrQosPStatsFwdOutProfPktsHi OBJECT-TYPE
    SYNTAX          Counter32
    MAX-ACCESS      read-only
    STATUS          current
    DESCRIPTION     "Upper 32 bits of sapEgrQosPStatsFwdOutProfPkts."
    ::= { sapEgrQosPolicerStatsEntry 18 }

sapEgrQosPStatsDrpOutProfPkts OBJECT-TYPE
    SYNTAX          Counter64
    MAX-ACCESS      read-only
    STATUS          current
    DESCRIPTION     "The number of out-of-profile packets
                     discarded by the egress Pchip due
                     to: MBS exceeded, buffer pool limit
                     exceeded, etc."
    ::= { sapEgrQosPolicerStatsEntry 19 }

sapEgrQosPStatsDrpOutProfPktsLo OBJECT-TYPE
    SYNTAX          Counter32
    MAX-ACCESS      read-only
    STATUS          current
    DESCRIPTION     "Lower 32 bits of sapEgrQosPStatsDrpOutProfPkts."
    ::= { sapEgrQosPolicerStatsEntry 20 }

sapEgrQosPStatsDrpOutProfPktsHi OBJECT-TYPE
    SYNTAX          Counter32
    MAX-ACCESS      read-only
    STATUS          current
    DESCRIPTION     "Upper 32 bits of sapEgrQosPStatsDrpOutProfPkts."
    ::= { sapEgrQosPolicerStatsEntry 21 }

sapEgrQosPStatsOffInProfOcts OBJECT-TYPE
    SYNTAX          Counter64
    MAX-ACCESS      read-only
    STATUS          current
    DESCRIPTION     "The number of in-profile octets
                     (rate below CIR) offered by the
                     egress Pchip."
    ::= { sapEgrQosPolicerStatsEntry 22 }

sapEgrQosPStatsOffInProfOctsLo OBJECT-TYPE
    SYNTAX          Counter32
    MAX-ACCESS      read-only
    STATUS          current
    DESCRIPTION     "Lower 32 bits of sapEgrQosPStatsOffInProfOcts."
    ::= { sapEgrQosPolicerStatsEntry 23 }

sapEgrQosPStatsOffInProfOctsHi OBJECT-TYPE
    SYNTAX          Counter32
    MAX-ACCESS      read-only
    STATUS          current
    DESCRIPTION     "Upper 32 bits of sapEgrQosPStatsOffInProfOcts."
    ::= { sapEgrQosPolicerStatsEntry 24 }

sapEgrQosPStatsFwdInProfOcts OBJECT-TYPE
    SYNTAX          Counter64
    MAX-ACCESS      read-only
    STATUS          current
    DESCRIPTION     "The number of in-profile octets
                     (rate below CIR) forwarded by the
                     egress Pchip."
    ::= { sapEgrQosPolicerStatsEntry 25 }

sapEgrQosPStatsFwdInProfOctsLo OBJECT-TYPE
    SYNTAX          Counter32
    MAX-ACCESS      read-only
    STATUS          current
    DESCRIPTION     "Lower 32 bits of sapEgrQosPStatsFwdInProfOcts."
    ::= { sapEgrQosPolicerStatsEntry 26 }

sapEgrQosPStatsFwdInProfOctsHi OBJECT-TYPE
    SYNTAX          Counter32
    MAX-ACCESS      read-only
    STATUS          current
    DESCRIPTION     "Upper 32 bits of sapEgrQosPStatsFwdInProfOcts."
    ::= { sapEgrQosPolicerStatsEntry 27 }

sapEgrQosPStatsDrpInProfOcts OBJECT-TYPE
    SYNTAX          Counter64
    MAX-ACCESS      read-only
    STATUS          current
    DESCRIPTION     "The number of in-profile octets
                     discarded by the egress Pchip due
                     to: MBS exceeded, buffer pool limit
                     exceeded, etc."
    ::= { sapEgrQosPolicerStatsEntry 28 }

sapEgrQosPStatsDrpInProfOctsLo OBJECT-TYPE
    SYNTAX          Counter32
    MAX-ACCESS      read-only
    STATUS          current
    DESCRIPTION     "Lower 32 bits of sapEgrQosPStatsDrpInProfOcts."
    ::= { sapEgrQosPolicerStatsEntry 29 }

sapEgrQosPStatsDrpInProfOctsHi OBJECT-TYPE
    SYNTAX          Counter32
    MAX-ACCESS      read-only
    STATUS          current
    DESCRIPTION     "Upper 32 bits of sapEgrQosPStatsDrpInProfOcts."
    ::= { sapEgrQosPolicerStatsEntry 30 }

sapEgrQosPStatsOffOutProfOcts OBJECT-TYPE
    SYNTAX          Counter64
    MAX-ACCESS      read-only
    STATUS          current
    DESCRIPTION     "The number of out-of-profile octets
                     (rate above CIR) forwarded by the
                     egress Pchip."
    ::= { sapEgrQosPolicerStatsEntry 31 }

sapEgrQosPStatsOffOutProfOctsLo OBJECT-TYPE
    SYNTAX          Counter32
    MAX-ACCESS      read-only
    STATUS          current
    DESCRIPTION     "Lower 32 bits of sapEgrQosPStatsOffOutProfOcts."
    ::= { sapEgrQosPolicerStatsEntry 32 }

sapEgrQosPStatsOffOutProfOctsHi OBJECT-TYPE
    SYNTAX          Counter32
    MAX-ACCESS      read-only
    STATUS          current
    DESCRIPTION     "Upper 32 bits of sapEgrQosPStatsOffOutProfOcts."
    ::= { sapEgrQosPolicerStatsEntry 33 }

sapEgrQosPStatsFwdOutProfOcts OBJECT-TYPE
    SYNTAX          Counter64
    MAX-ACCESS      read-only
    STATUS          current
    DESCRIPTION     "The number of out-of-profile octets
                     (rate above CIR) forwarded by the
                     egress Pchip."
    ::= { sapEgrQosPolicerStatsEntry 34 }

sapEgrQosPStatsFwdOutProfOctsLo OBJECT-TYPE
    SYNTAX          Counter32
    MAX-ACCESS      read-only
    STATUS          current
    DESCRIPTION     "Lower 32 bits of sapEgrQosPStatsFwdOutProfOcts."
    ::= { sapEgrQosPolicerStatsEntry 35 }

sapEgrQosPStatsFwdOutProfOctsHi OBJECT-TYPE
    SYNTAX          Counter32
    MAX-ACCESS      read-only
    STATUS          current
    DESCRIPTION     "Upper 32 bits of sapEgrQosPStatsFwdOutProfOcts."
    ::= { sapEgrQosPolicerStatsEntry 36 }

sapEgrQosPStatsDrpOutProfOcts OBJECT-TYPE
    SYNTAX          Counter64
    MAX-ACCESS      read-only
    STATUS          current
    DESCRIPTION     "The number of out-of-profile octets
                     discarded by the egress Pchip due
                     to: MBS exceeded, buffer pool limit
                     exceeded, etc."
    ::= { sapEgrQosPolicerStatsEntry 37 }

sapEgrQosPStatsDrpOutProfOctsLo OBJECT-TYPE
    SYNTAX          Counter32
    MAX-ACCESS      read-only
    STATUS          current
    DESCRIPTION     "Lower 32 bits of sapEgrQosPStatsDrpOutProfOcts."
    ::= { sapEgrQosPolicerStatsEntry 38 }

sapEgrQosPStatsDrpOutProfOctsHi OBJECT-TYPE
    SYNTAX          Counter32
    MAX-ACCESS      read-only
    STATUS          current
    DESCRIPTION     "Upper 32 bits of sapEgrQosPStatsDrpOutProfOcts."
    ::= { sapEgrQosPolicerStatsEntry 39 }


sapEgrQosPStatsUncolPktsOff OBJECT-TYPE
    SYNTAX          Counter64
    MAX-ACCESS      read-only
    STATUS          current
    DESCRIPTION     "The number of uncolored packets forwarded by the egress Pchip."
    ::= { sapEgrQosPolicerStatsEntry 40 }

sapEgrQosPStatsUncolPktsOffLo OBJECT-TYPE
    SYNTAX          Counter32
    MAX-ACCESS      read-only
    STATUS          current
    DESCRIPTION     "Lower 32 bits of sapIngQosPStatsUncolPktsOff."
    ::= { sapEgrQosPolicerStatsEntry 41 }

sapEgrQosPStatsUncolPktsOffHi OBJECT-TYPE
    SYNTAX          Counter32
    MAX-ACCESS      read-only
    STATUS          current
    DESCRIPTION     "Upper 32 bits of sapIngQosPStatsUncolPktsOff."
    ::= { sapEgrQosPolicerStatsEntry 42 }

sapEgrQosPStatsUncolOctsOff OBJECT-TYPE
    SYNTAX          Counter64
    MAX-ACCESS      read-only
    STATUS          current
    DESCRIPTION     "The number of uncolored octets forwarded by the egress Pchip."
    ::= { sapEgrQosPolicerStatsEntry 43 }

sapEgrQosPStatsUncolOctsOffLo OBJECT-TYPE
    SYNTAX          Counter32
    MAX-ACCESS      read-only
    STATUS          current
    DESCRIPTION     "Lower 32 bits of sapIngQosPStatsUncolOctsOff."
    ::= { sapEgrQosPolicerStatsEntry 44 }

sapEgrQosPStatsUncolOctsOffHi OBJECT-TYPE
    SYNTAX          Counter32
    MAX-ACCESS      read-only
    STATUS          current
    DESCRIPTION     "Upper 32 bits of sapIngQosPStatsUncolOctsOff."
    ::= { sapEgrQosPolicerStatsEntry 45 }

-- ------------------------------------------
-- Ingress QoS Plcy Policer SAP Statistics Table
-- ------------------------------------------
sapIngQosPlcyPolicerStatsTable OBJECT-TYPE
    SYNTAX          SEQUENCE OF SapIngQosPlcyPolicerStatsEntry
    MAX-ACCESS      not-accessible
    STATUS          current
    DESCRIPTION     "A table that contains ingress QoS policer SAP
                     statistics, per Ingress QoS Policy the policer was used by."
    ::= { tmnxSapObjs 98 }

sapIngQosPlcyPolicerStatsEntry OBJECT-TYPE
    SYNTAX          SapIngQosPlcyPolicerStatsEntry
    MAX-ACCESS      not-accessible
    STATUS          current
    DESCRIPTION     "Ingress statistics about a specific SAP's QoS policer for a given Qos policy."
    INDEX           { svcId,
                      sapPortId,
                      sapEncapValue,
                      sapIgQosPlcyPStatPlcyId,
                      sapIgQosPlcyPStatPolId }
    ::= { sapIngQosPlcyPolicerStatsTable 1 }

SapIngQosPlcyPolicerStatsEntry ::=
    SEQUENCE {
        sapIgQosPlcyPStatPlcyId          TSapIngressPolicyID,
        sapIgQosPlcyPStatPolId           TIngPolicerId,
        sapIgQosPlcyPStatCustId          TmnxCustId,
        sapIgQosPlcyPStatMode            TmnxIngPolicerStatMode,
        
        sapIgQosPlcyPStatOffHiPrioPkts   Counter64,
        sapIgQosPlcyPStatOffHiPrioPktsL  Counter32,
        sapIgQosPlcyPStatOffHiPrioPktsH  Counter32,
        sapIgQosPlcyPStatDrpHiPrioPkts   Counter64,
        sapIgQosPlcyPStatDrpHiPrioPktsL  Counter32,
        sapIgQosPlcyPStatDrpHiPrioPktsH  Counter32,
        sapIgQosPlcyPStatOffLoPrioPkts   Counter64,
        sapIgQosPlcyPStatOffLoPrioPktsL  Counter32,
        sapIgQosPlcyPStatOffLoPrioPktsH  Counter32,
        sapIgQosPlcyPStatDrpLoPrioPkts   Counter64,
        sapIgQosPlcyPStatDrpLoPrioPktsL  Counter32,
        sapIgQosPlcyPStatDrpLoPrioPktsH  Counter32,
        sapIgQosPlcyPStatOffHiPrioOcts   Counter64,
        sapIgQosPlcyPStatOffHiPrioOctsL  Counter32,
        sapIgQosPlcyPStatOffHiPrioOctsH  Counter32,
        sapIgQosPlcyPStatDrpHiPrioOcts   Counter64,
        sapIgQosPlcyPStatDrpHiPrioOctsL  Counter32,
        sapIgQosPlcyPStatDrpHiPrioOctsH  Counter32,
        sapIgQosPlcyPStatOffLoPrioOcts   Counter64,
        sapIgQosPlcyPStatOffLoPrioOctsL  Counter32,
        sapIgQosPlcyPStatOffLoPrioOctsH  Counter32,
        sapIgQosPlcyPStatDrpLoPrioOcts   Counter64,
        sapIgQosPlcyPStatDrpLoPrioOctsL  Counter32,
        sapIgQosPlcyPStatDrpLoPrioOctsH  Counter32,
        sapIgQosPlcyPStatFwdInProfPkts   Counter64,
        sapIgQosPlcyPStatFwdInProfPktsL  Counter32,
        sapIgQosPlcyPStatFwdInProfPktsH  Counter32,
        sapIgQosPlcyPStatFwdOutProfPkts  Counter64,
        sapIgQosPlcyPStatFwdOutProfPktsL Counter32,
        sapIgQosPlcyPStatFwdOutProfPktsH Counter32,
        sapIgQosPlcyPStatFwdInProfOcts   Counter64,
        sapIgQosPlcyPStatFwdInProfOctsL  Counter32,
        sapIgQosPlcyPStatFwdInProfOctsH  Counter32,
        sapIgQosPlcyPStatFwdOutProfOcts  Counter64,
        sapIgQosPlcyPStatFwdOutProfOctsL Counter32,
        sapIgQosPlcyPStatFwdOutProfOctsH Counter32,
        sapIgQosPlcyPStatUncolPktsOff    Counter64,
        sapIgQosPlcyPStatUncolPktsOffL   Counter32,
        sapIgQosPlcyPStatUncolPktsOffH   Counter32,
        sapIgQosPlcyPStatUncolOctsOff    Counter64,
        sapIgQosPlcyPStatUncolOctsOffL   Counter32,
        sapIgQosPlcyPStatUncolOctsOffH   Counter32
    }

sapIgQosPlcyPStatPlcyId OBJECT-TYPE
    SYNTAX          TSapIngressPolicyID
    MAX-ACCESS      not-accessible
    STATUS          current
    DESCRIPTION     "The row index in the tSapIngressTable corresponding to this ingress QoS policy."
    ::= { sapIngQosPlcyPolicerStatsEntry 1 }

sapIgQosPlcyPStatPolId OBJECT-TYPE
    SYNTAX          TIngPolicerId
    MAX-ACCESS      not-accessible
    STATUS          current
    DESCRIPTION     "The index of the ingress QoS policer of this SAP used by the
                     policy indicated by sapIgQosPlcyPStatPlcyId."
    ::= { sapIngQosPlcyPolicerStatsEntry 2 }

sapIgQosPlcyPStatCustId OBJECT-TYPE
    SYNTAX          TmnxCustId
    MAX-ACCESS      read-only
    STATUS          current
    DESCRIPTION     "The value of the object sapIgQosPlcyPStatCustId
                     indicates the Customer ID for the associated service."
    ::= { sapIngQosPlcyPolicerStatsEntry 3 }

sapIgQosPlcyPStatMode OBJECT-TYPE
    SYNTAX      TmnxIngPolicerStatMode
    MAX-ACCESS  read-only
    STATUS      current
    DESCRIPTION
        "The value of sapIgQosPlcyPStatMode indicates the stat mode used by the policer."
    ::= { sapIngQosPlcyPolicerStatsEntry 4 }

sapIgQosPlcyPStatOffHiPrioPkts OBJECT-TYPE
    SYNTAX          Counter64
    MAX-ACCESS      read-only
    STATUS          current
    DESCRIPTION     "The value of sapIgQosPlcyPStatOffHiPrioPkts
                     indicates the number of high priority packets,
                     as determined by the SAP ingress QoS policy, offered by
                     the Pchip to the Qchip."
    ::= { sapIngQosPlcyPolicerStatsEntry 5 }

sapIgQosPlcyPStatOffHiPrioPktsL OBJECT-TYPE
    SYNTAX          Counter32
    MAX-ACCESS      read-only
    STATUS          current
    DESCRIPTION     "Lower 32 bits of sapIgQosPlcyPStatOffHiPrioPkts."
    ::= { sapIngQosPlcyPolicerStatsEntry 6 }

sapIgQosPlcyPStatOffHiPrioPktsH OBJECT-TYPE
    SYNTAX          Counter32
    MAX-ACCESS      read-only
    STATUS          current
    DESCRIPTION     "Upper 32 bits of sapIgQosPlcyPStatOffHiPrioPkts."
    ::= { sapIngQosPlcyPolicerStatsEntry 7 }

sapIgQosPlcyPStatDrpHiPrioPkts OBJECT-TYPE
    SYNTAX          Counter64
    MAX-ACCESS      read-only
    STATUS          current
    DESCRIPTION     "The value of sapIgQosPlcyPStatDrpHiPrioPkts
                     indicates the number of high priority packets,
                     as determined by the SAP ingress QoS policy, dropped by
                     the Pchip due to: MBS exceeded, buffer pool limit
                     exceeded, etc."
    ::= { sapIngQosPlcyPolicerStatsEntry 8 }

sapIgQosPlcyPStatDrpHiPrioPktsL OBJECT-TYPE
    SYNTAX          Counter32
    MAX-ACCESS      read-only
    STATUS          current
    DESCRIPTION     "Lower 32 bits of sapIgQosPlcyPStatDrpHiPrioPkts."
    ::= { sapIngQosPlcyPolicerStatsEntry 9 }

sapIgQosPlcyPStatDrpHiPrioPktsH OBJECT-TYPE
    SYNTAX          Counter32
    MAX-ACCESS      read-only
    STATUS          current
    DESCRIPTION     "Upper 32 bits of sapIgQosPlcyPStatDrpHiPrioPkts."
    ::= { sapIngQosPlcyPolicerStatsEntry 10 }

sapIgQosPlcyPStatOffLoPrioPkts OBJECT-TYPE
    SYNTAX          Counter64
    MAX-ACCESS      read-only
    STATUS          current
    DESCRIPTION     "The value of sapIgQosPlcyPStatOffLoPrioPkts
                     indicates the number of  low priority packets,
                     as determined by the SAP ingress QoS policy, offered by
                     the Pchip to the Qchip."
    ::= { sapIngQosPlcyPolicerStatsEntry 11 }

sapIgQosPlcyPStatOffLoPrioPktsL OBJECT-TYPE
    SYNTAX          Counter32
    MAX-ACCESS      read-only
    STATUS          current
    DESCRIPTION     "Lower 32 bits of sapIgQosPlcyPStatOffLoPrioPkts."
    ::= { sapIngQosPlcyPolicerStatsEntry 12 }

sapIgQosPlcyPStatOffLoPrioPktsH OBJECT-TYPE
    SYNTAX          Counter32
    MAX-ACCESS      read-only
    STATUS          current
    DESCRIPTION     "Upper 32 bits of sapIgQosPlcyPStatOffLoPrioPkts."
    ::= { sapIngQosPlcyPolicerStatsEntry 13 }

sapIgQosPlcyPStatDrpLoPrioPkts OBJECT-TYPE
    SYNTAX          Counter64
    MAX-ACCESS      read-only
    STATUS          current
    DESCRIPTION     "The value of sapIgQosPlcyPStatDrpLoPrioPkts
                     indicates the number of low priority packets,
                     as determined by the SAP ingress QoS policy, dropped by
                     the Pchip due to: MBS exceeded, buffer pool limit
                     exceeded, etc."
    ::= { sapIngQosPlcyPolicerStatsEntry 14 }

sapIgQosPlcyPStatDrpLoPrioPktsL OBJECT-TYPE
    SYNTAX          Counter32
    MAX-ACCESS      read-only
    STATUS          current
    DESCRIPTION     "Lower 32 bits of sapIgQosPlcyPStatDrpLoPrioPkts."
    ::= { sapIngQosPlcyPolicerStatsEntry 15 }

sapIgQosPlcyPStatDrpLoPrioPktsH OBJECT-TYPE
    SYNTAX          Counter32
    MAX-ACCESS      read-only
    STATUS          current
    DESCRIPTION     "Upper 32 bits of sapIgQosPlcyPStatDrpLoPrioPkts."
    ::= { sapIngQosPlcyPolicerStatsEntry 16 }

sapIgQosPlcyPStatOffHiPrioOcts OBJECT-TYPE
    SYNTAX          Counter64
    MAX-ACCESS      read-only
    STATUS          current
    DESCRIPTION     "The value of sapIgQosPlcyPStatOffHiPrioOcts
                     indicates the number of high priority octets,
                     as determined by the SAP ingress QoS policy, offered by
                     the Pchip to the Qchip."
    ::= { sapIngQosPlcyPolicerStatsEntry 17 }

sapIgQosPlcyPStatOffHiPrioOctsL OBJECT-TYPE
    SYNTAX          Counter32
    MAX-ACCESS      read-only
    STATUS          current
    DESCRIPTION     "Lower 32 bits of sapIgQosPlcyPStatOffHiPrioOcts."
    ::= { sapIngQosPlcyPolicerStatsEntry 18 }

sapIgQosPlcyPStatOffHiPrioOctsH OBJECT-TYPE
    SYNTAX          Counter32
    MAX-ACCESS      read-only
    STATUS          current
    DESCRIPTION     "Upper 32 bits of sapIgQosPlcyPStatOffHiPrioOcts."
    ::= { sapIngQosPlcyPolicerStatsEntry 19 }

sapIgQosPlcyPStatDrpHiPrioOcts OBJECT-TYPE
    SYNTAX          Counter64
    MAX-ACCESS      read-only
    STATUS          current
    DESCRIPTION     "The value of sapIgQosPlcyPStatDrpHiPrioOcts
                     indicates the number ofhigh priority octets,
                     as determined by the SAP ingress QoS policy, dropped by
                     the Pchip due to: MBS exceeded, buffer pool limit
                     exceeded, etc."
    ::= { sapIngQosPlcyPolicerStatsEntry 20 }

sapIgQosPlcyPStatDrpHiPrioOctsL OBJECT-TYPE
    SYNTAX          Counter32
    MAX-ACCESS      read-only
    STATUS          current
    DESCRIPTION     "Lower 32 bits of sapIgQosPlcyPStatDrpHiPrioOcts."
    ::= { sapIngQosPlcyPolicerStatsEntry 21 }

sapIgQosPlcyPStatDrpHiPrioOctsH OBJECT-TYPE
    SYNTAX          Counter32
    MAX-ACCESS      read-only
    STATUS          current
    DESCRIPTION     "Upper 32 bits of sapIgQosPlcyPStatDrpHiPrioOcts."
    ::= { sapIngQosPlcyPolicerStatsEntry 22 }

sapIgQosPlcyPStatOffLoPrioOcts OBJECT-TYPE
    SYNTAX          Counter64
    MAX-ACCESS      read-only
    STATUS          current
    DESCRIPTION     "The value of sapIgQosPlcyPStatOffLoPrioOcts
                     indicates the number of low priority octets,
                     as determined by the SAP ingress QoS policy, offered by
                     the Pchip to the Qchip."
    ::= { sapIngQosPlcyPolicerStatsEntry 23 }

sapIgQosPlcyPStatOffLoPrioOctsL OBJECT-TYPE
    SYNTAX          Counter32
    MAX-ACCESS      read-only
    STATUS          current
    DESCRIPTION     "Lower 32 bits of sapIgQosPlcyPStatOffLoPrioOcts."
    ::= { sapIngQosPlcyPolicerStatsEntry 24 }

sapIgQosPlcyPStatOffLoPrioOctsH OBJECT-TYPE
    SYNTAX          Counter32
    MAX-ACCESS      read-only
    STATUS          current
    DESCRIPTION     "Upper 32 bits of sapIgQosPlcyPStatOffLoPrioOcts."
    ::= { sapIngQosPlcyPolicerStatsEntry 25 }

sapIgQosPlcyPStatDrpLoPrioOcts OBJECT-TYPE
    SYNTAX          Counter64
    MAX-ACCESS      read-only
    STATUS          current
    DESCRIPTION     "The value of sapIgQosPlcyPStatDrpLoPrioOcts
                     indicates the number of low priority octets,
                     as determined by the SAP ingress QoS policy, dropped by
                     the Pchip due to: MBS exceeded, buffer pool limit
                     exceeded, etc."
    ::= { sapIngQosPlcyPolicerStatsEntry 26 }

sapIgQosPlcyPStatDrpLoPrioOctsL OBJECT-TYPE
    SYNTAX          Counter32
    MAX-ACCESS      read-only
    STATUS          current
    DESCRIPTION     "Lower 32 bits of sapIgQosPlcyPStatDrpLoPrioOcts."
    ::= { sapIngQosPlcyPolicerStatsEntry 27 }

sapIgQosPlcyPStatDrpLoPrioOctsH OBJECT-TYPE
    SYNTAX          Counter32
    MAX-ACCESS      read-only
    STATUS          current
    DESCRIPTION     "Upper 32 bits of sapIgQosPlcyPStatDrpLoPrioOcts."
    ::= { sapIngQosPlcyPolicerStatsEntry 28 }

sapIgQosPlcyPStatFwdInProfPkts OBJECT-TYPE
    SYNTAX          Counter64
    MAX-ACCESS      read-only
    STATUS          current
    DESCRIPTION     "The value of sapIgQosPlcyPStatFwdInProfPkts
                     indicates the number of in-profile packets
                     (rate below CIR) forwarded by the ingress Pchip."
    ::= { sapIngQosPlcyPolicerStatsEntry 29 }

sapIgQosPlcyPStatFwdInProfPktsL OBJECT-TYPE
    SYNTAX          Counter32
    MAX-ACCESS      read-only
    STATUS          current
    DESCRIPTION     "Lower 32 bits of sapIgQosPlcyPStatFwdInProfPkts."
    ::= { sapIngQosPlcyPolicerStatsEntry 30 }

sapIgQosPlcyPStatFwdInProfPktsH OBJECT-TYPE
    SYNTAX          Counter32
    MAX-ACCESS      read-only
    STATUS          current
    DESCRIPTION     "Upper 32 bits of sapIgQosPlcyPStatFwdInProfPkts."
    ::= { sapIngQosPlcyPolicerStatsEntry 31 }

sapIgQosPlcyPStatFwdOutProfPkts OBJECT-TYPE
    SYNTAX          Counter64
    MAX-ACCESS      read-only
    STATUS          current
    DESCRIPTION     "The value of sapIgQosPlcyPStatFwdOutProfPkts
                     indicates the number of out-of-profile packets
                     (rate above CIR) forwarded by the ingress Pchip."
    ::= { sapIngQosPlcyPolicerStatsEntry 32 }

sapIgQosPlcyPStatFwdOutProfPktsL OBJECT-TYPE
    SYNTAX          Counter32
    MAX-ACCESS      read-only
    STATUS          current
    DESCRIPTION     "Lower 32 bits of sapIgQosPlcyPStatFwdOutProfPkts."
    ::= { sapIngQosPlcyPolicerStatsEntry 33 }

sapIgQosPlcyPStatFwdOutProfPktsH OBJECT-TYPE
    SYNTAX          Counter32
    MAX-ACCESS      read-only
    STATUS          current
    DESCRIPTION     "Upper 32 bits of sapIgQosPlcyPStatFwdOutProfPkts."
    ::= { sapIngQosPlcyPolicerStatsEntry 34 }

sapIgQosPlcyPStatFwdInProfOcts OBJECT-TYPE
    SYNTAX          Counter64
    MAX-ACCESS      read-only
    STATUS          current
    DESCRIPTION     "The value of sapIgQosPlcyPStatFwdInProfOcts
                     indicates the number of in-profile octets
                     (rate below CIR) forwarded by the ingress Pchip."
    ::= { sapIngQosPlcyPolicerStatsEntry 35 }

sapIgQosPlcyPStatFwdInProfOctsL OBJECT-TYPE
    SYNTAX          Counter32
    MAX-ACCESS      read-only
    STATUS          current
    DESCRIPTION     "Lower 32 bits of sapIgQosPlcyPStatFwdInProfOcts."
    ::= { sapIngQosPlcyPolicerStatsEntry 36 }

sapIgQosPlcyPStatFwdInProfOctsH OBJECT-TYPE
    SYNTAX          Counter32
    MAX-ACCESS      read-only
    STATUS          current
    DESCRIPTION     "Upper 32 bits of sapIgQosPlcyPStatFwdInProfOcts."
    ::= { sapIngQosPlcyPolicerStatsEntry 37 }

sapIgQosPlcyPStatFwdOutProfOcts OBJECT-TYPE
    SYNTAX          Counter64
    MAX-ACCESS      read-only
    STATUS          current
    DESCRIPTION     "The value of sapIgQosPlcyPStatFwdOutProfOcts
                     indicates the number of  out-of-profile octets
                     (rate above CIR) forwarded by the ingress Pchip."
    ::= { sapIngQosPlcyPolicerStatsEntry 38 }

sapIgQosPlcyPStatFwdOutProfOctsL OBJECT-TYPE
    SYNTAX          Counter32
    MAX-ACCESS      read-only
    STATUS          current
    DESCRIPTION     "Lower 32 bits of sapIgQosPlcyPStatFwdOutProfOcts."
    ::= { sapIngQosPlcyPolicerStatsEntry 39 }

sapIgQosPlcyPStatFwdOutProfOctsH OBJECT-TYPE
    SYNTAX          Counter32
    MAX-ACCESS      read-only
    STATUS          current
    DESCRIPTION     "Upper 32 bits of sapIgQosPlcyPStatFwdOutProfOcts."
    ::= { sapIngQosPlcyPolicerStatsEntry 40 }

sapIgQosPlcyPStatUncolPktsOff OBJECT-TYPE
    SYNTAX          Counter64
    MAX-ACCESS      read-only
    STATUS          current
    DESCRIPTION     "The value of sapIgQosPlcyPStatUncolPktsOff
                     indicates the number of uncolored packets offered to
                     the ingress Pchip."
    ::= { sapIngQosPlcyPolicerStatsEntry 41 }

sapIgQosPlcyPStatUncolPktsOffL OBJECT-TYPE
    SYNTAX          Counter32
    MAX-ACCESS      read-only
    STATUS          current
    DESCRIPTION     "Lower 32 bits of sapIgQosPlcyPStatUncolPktsOff."
    ::= { sapIngQosPlcyPolicerStatsEntry 42 }

sapIgQosPlcyPStatUncolPktsOffH OBJECT-TYPE
    SYNTAX          Counter32
    MAX-ACCESS      read-only
    STATUS          current
    DESCRIPTION     "Upper 32 bits of sapIgQosPlcyPStatUncolPktsOff."
    ::= { sapIngQosPlcyPolicerStatsEntry 43 }

sapIgQosPlcyPStatUncolOctsOff OBJECT-TYPE
    SYNTAX          Counter64
    MAX-ACCESS      read-only
    STATUS          current
    DESCRIPTION     "The value of sapIgQosPlcyPStatUncolOctsOff
                     indicates the number of uncolored octets offered to
                     the ingress Pchip."
    ::= { sapIngQosPlcyPolicerStatsEntry 44 }

sapIgQosPlcyPStatUncolOctsOffL OBJECT-TYPE
    SYNTAX          Counter32
    MAX-ACCESS      read-only
    STATUS          current
    DESCRIPTION     "Lower 32 bits of sapIgQosPlcyPStatUncolOctsOff."
    ::= { sapIngQosPlcyPolicerStatsEntry 45 }

sapIgQosPlcyPStatUncolOctsOffH OBJECT-TYPE
    SYNTAX          Counter32
    MAX-ACCESS      read-only
    STATUS          current
    DESCRIPTION     "Upper 32 bits of sapIgQosPlcyPStatUncolOctsOff."
    ::= { sapIngQosPlcyPolicerStatsEntry 46 }

-- ------------------------------------------
-- Egress QoS Plcy Policer SAP Statistics Table
-- ------------------------------------------
sapEgrQosPlcyPolicerStatsTable OBJECT-TYPE
    SYNTAX          SEQUENCE OF SapEgrQosPlcyPolicerStatsEntry
    MAX-ACCESS      not-accessible
    STATUS          current
    DESCRIPTION     "A table that contains egress QoS policer SAP
                     statistics per Egress QoS Policy the policer was used by."
    ::= { tmnxSapObjs 99 }

sapEgrQosPlcyPolicerStatsEntry OBJECT-TYPE
    SYNTAX          SapEgrQosPlcyPolicerStatsEntry
    MAX-ACCESS      not-accessible
    STATUS          current
    DESCRIPTION     "Egress statistics about a specific SAP's QoS policer for a given Qos policy."
    INDEX           { svcId,
                      sapPortId,
                      sapEncapValue,
                      sapEgQosPlcyPStatPlcyId,
                      sapEgQosPlcyPStatPolId }
    ::= { sapEgrQosPlcyPolicerStatsTable 1 }

SapEgrQosPlcyPolicerStatsEntry ::=
    SEQUENCE {
        sapEgQosPlcyPStatPlcyId          TSapEgressPolicyID,
        sapEgQosPlcyPStatPolId           TEgrPolicerId,
        sapEgQosPlcyPStatCustId          TmnxCustId,
        sapEgQosPlcyPStatMode            TmnxEgrPolicerStatMode,
        
        sapEgQosPlcyPStatOffInProfPkts   Counter64,
        sapEgQosPlcyPStatOffInProfPktsL  Counter32,
        sapEgQosPlcyPStatOffInProfPktsH  Counter32,
        sapEgQosPlcyPStatFwdInProfPkts   Counter64,
        sapEgQosPlcyPStatFwdInProfPktsL  Counter32,
        sapEgQosPlcyPStatFwdInProfPktsH  Counter32,
        sapEgQosPlcyPStatDrpInProfPkts   Counter64,
        sapEgQosPlcyPStatDrpInProfPktsL  Counter32,
        sapEgQosPlcyPStatDrpInProfPktsH  Counter32,
        sapEgQosPlcyPStatOffOutProfPkts  Counter64,
        sapEgQosPlcyPStatOffOutProfPktsL Counter32,
        sapEgQosPlcyPStatOffOutProfPktsH Counter32,
        sapEgQosPlcyPStatFwdOutProfPkts  Counter64,
        sapEgQosPlcyPStatFwdOutProfPktsL Counter32,
        sapEgQosPlcyPStatFwdOutProfPktsH Counter32,
        sapEgQosPlcyPStatDrpOutProfPkts  Counter64,
        sapEgQosPlcyPStatDrpOutProfPktsL Counter32,
        sapEgQosPlcyPStatDrpOutProfPktsH Counter32,
        sapEgQosPlcyPStatOffInProfOcts   Counter64,
        sapEgQosPlcyPStatOffInProfOctsL  Counter32,
        sapEgQosPlcyPStatOffInProfOctsH  Counter32,
        sapEgQosPlcyPStatFwdInProfOcts   Counter64,
        sapEgQosPlcyPStatFwdInProfOctsL  Counter32,
        sapEgQosPlcyPStatFwdInProfOctsH  Counter32,
        sapEgQosPlcyPStatDrpInProfOcts   Counter64,
        sapEgQosPlcyPStatDrpInProfOctsL  Counter32,
        sapEgQosPlcyPStatDrpInProfOctsH  Counter32,
        sapEgQosPlcyPStatOffOutProfOcts  Counter64,
        sapEgQosPlcyPStatOffOutProfOctsL Counter32,
        sapEgQosPlcyPStatOffOutProfOctsH Counter32,
        sapEgQosPlcyPStatFwdOutProfOcts  Counter64,
        sapEgQosPlcyPStatFwdOutProfOctsL Counter32,
        sapEgQosPlcyPStatFwdOutProfOctsH Counter32,
        sapEgQosPlcyPStatDrpOutProfOcts  Counter64,
        sapEgQosPlcyPStatDrpOutProfOctsL Counter32,
        sapEgQosPlcyPStatDrpOutProfOctsH Counter32
    }

sapEgQosPlcyPStatPlcyId OBJECT-TYPE
    SYNTAX          TSapEgressPolicyID
    MAX-ACCESS      not-accessible
    STATUS          current
    DESCRIPTION     "The row index in the tSapEgressTable corresponding to this egress QoS policy."
    ::= { sapEgrQosPlcyPolicerStatsEntry 1 }

sapEgQosPlcyPStatPolId OBJECT-TYPE
    SYNTAX          TEgrPolicerId
    MAX-ACCESS      not-accessible
    STATUS          current
    DESCRIPTION     "The index of the egress QoS policer of this SAP used by the
                     policy indicated by sapEgQosPlcyPStatPlcyId."
    ::= { sapEgrQosPlcyPolicerStatsEntry 2 }

sapEgQosPlcyPStatCustId OBJECT-TYPE
    SYNTAX          TmnxCustId
    MAX-ACCESS      read-only
    STATUS          current
    DESCRIPTION     "The value of the object sapEgQosPlcyPStatCustId indicates
                     the Customer ID for the associated service."
    ::= { sapEgrQosPlcyPolicerStatsEntry 3 }

sapEgQosPlcyPStatMode OBJECT-TYPE
    SYNTAX      TmnxEgrPolicerStatMode
    MAX-ACCESS  read-only
    STATUS      current
    DESCRIPTION
        "The value of sapEgQosPlcyPStatMode indicates the stat mode used by the policer."
    ::= { sapEgrQosPlcyPolicerStatsEntry 4 }

sapEgQosPlcyPStatOffInProfPkts OBJECT-TYPE
    SYNTAX          Counter64
    MAX-ACCESS      read-only
    STATUS          current
    DESCRIPTION     "The value of sapEgQosPlcyPStatOffInProfPkts
                     indicates the number of in-profile packets (rate below
                     CIR) offered by the egress Qchip."
    ::= { sapEgrQosPlcyPolicerStatsEntry 5 }

sapEgQosPlcyPStatOffInProfPktsL OBJECT-TYPE
    SYNTAX          Counter32
    MAX-ACCESS      read-only
    STATUS          current
    DESCRIPTION     "Lower 32 bits of sapEgQosPlcyPStatOffInProfPkts."
    ::= { sapEgrQosPlcyPolicerStatsEntry 6 }

sapEgQosPlcyPStatOffInProfPktsH OBJECT-TYPE
    SYNTAX          Counter32
    MAX-ACCESS      read-only
    STATUS          current
    DESCRIPTION     "Upper 32 bits of sapEgQosPlcyPStatOffInProfPkts."
    ::= { sapEgrQosPlcyPolicerStatsEntry 7 }

sapEgQosPlcyPStatFwdInProfPkts OBJECT-TYPE
    SYNTAX          Counter64
    MAX-ACCESS      read-only
    STATUS          current
    DESCRIPTION     "The value of sapEgQosPlcyPStatFwdInProfPkts
                     indicates the number of in-profile packets (rate below
                     CIR) forwarded by the egress Qchip."
    ::= { sapEgrQosPlcyPolicerStatsEntry 8 }

sapEgQosPlcyPStatFwdInProfPktsL OBJECT-TYPE
    SYNTAX          Counter32
    MAX-ACCESS      read-only
    STATUS          current
    DESCRIPTION     "Lower 32 bits of sapEgQosPlcyPStatFwdInProfPkts."
    ::= { sapEgrQosPlcyPolicerStatsEntry 9 }

sapEgQosPlcyPStatFwdInProfPktsH OBJECT-TYPE
    SYNTAX          Counter32
    MAX-ACCESS      read-only
    STATUS          current
    DESCRIPTION     "Upper 32 bits of sapEgQosPlcyPStatFwdInProfPkts."
    ::= { sapEgrQosPlcyPolicerStatsEntry 10 }

sapEgQosPlcyPStatDrpInProfPkts OBJECT-TYPE
    SYNTAX          Counter64
    MAX-ACCESS      read-only
    STATUS          current
    DESCRIPTION     "The value of sapEgQosPlcyPStatDrpInProfPkts
                     indicates the number of in-profile packets discarded by
                     the egress Qchip due to: MBS exceeded, buffer pool limit
                     exceeded, etc."
    ::= { sapEgrQosPlcyPolicerStatsEntry 11 }

sapEgQosPlcyPStatDrpInProfPktsL OBJECT-TYPE
    SYNTAX          Counter32
    MAX-ACCESS      read-only
    STATUS          current
    DESCRIPTION     "Lower 32 bits of sapEgQosPlcyPStatDrpInProfPkts."
    ::= { sapEgrQosPlcyPolicerStatsEntry 12 }

sapEgQosPlcyPStatDrpInProfPktsH OBJECT-TYPE
    SYNTAX          Counter32
    MAX-ACCESS      read-only
    STATUS          current
    DESCRIPTION     "Upper 32 bits of sapEgQosPlcyPStatDrpInProfPkts."
    ::= { sapEgrQosPlcyPolicerStatsEntry 13 }

sapEgQosPlcyPStatOffOutProfPkts OBJECT-TYPE
    SYNTAX          Counter64
    MAX-ACCESS      read-only
    STATUS          current
    DESCRIPTION     "The value of sapEgQosPlcyPStatOffOutProfPkts
                     indicates the number of out-of-profile packets (rate
                     above CIR) offered by the egress Qchip."
    ::= { sapEgrQosPlcyPolicerStatsEntry 14 }

sapEgQosPlcyPStatOffOutProfPktsL OBJECT-TYPE
    SYNTAX          Counter32
    MAX-ACCESS      read-only
    STATUS          current
    DESCRIPTION     "Lower 32 bits of sapEgQosPlcyPStatOffOutProfPkts."
    ::= { sapEgrQosPlcyPolicerStatsEntry 15 }

sapEgQosPlcyPStatOffOutProfPktsH OBJECT-TYPE
    SYNTAX          Counter32
    MAX-ACCESS      read-only
    STATUS          current
    DESCRIPTION     "Upper 32 bits of sapEgQosPlcyPStatOffOutProfPkts."
    ::= { sapEgrQosPlcyPolicerStatsEntry 16 }

sapEgQosPlcyPStatFwdOutProfPkts OBJECT-TYPE
    SYNTAX          Counter64
    MAX-ACCESS      read-only
    STATUS          current
    DESCRIPTION     "The value of sapEgQosPlcyPStatFwdOutProfPkts
                     indicates the number of out-of-profile packets (rate
                     above CIR) forwarded by the egress Qchip."
    ::= { sapEgrQosPlcyPolicerStatsEntry 17 }

sapEgQosPlcyPStatFwdOutProfPktsL OBJECT-TYPE
    SYNTAX          Counter32
    MAX-ACCESS      read-only
    STATUS          current
    DESCRIPTION     "Lower 32 bits of sapEgQosPlcyPStatFwdOutProfPkts."
    ::= { sapEgrQosPlcyPolicerStatsEntry 18 }

sapEgQosPlcyPStatFwdOutProfPktsH OBJECT-TYPE
    SYNTAX          Counter32
    MAX-ACCESS      read-only
    STATUS          current
    DESCRIPTION     "Upper 32 bits of sapEgQosPlcyPStatFwdOutProfPkts."
    ::= { sapEgrQosPlcyPolicerStatsEntry 19 }

sapEgQosPlcyPStatDrpOutProfPkts OBJECT-TYPE
    SYNTAX          Counter64
    MAX-ACCESS      read-only
    STATUS          current
    DESCRIPTION     "The value of sapEgQosPlcyPStatDrpOutProfPkts
                     indicates the number out-of-profile packets discarded by
                     the egress Qchip due to: MBS exceeded, buffer pool limit
                     exceeded, etc."
    ::= { sapEgrQosPlcyPolicerStatsEntry 20 }

sapEgQosPlcyPStatDrpOutProfPktsL OBJECT-TYPE
    SYNTAX          Counter32
    MAX-ACCESS      read-only
    STATUS          current
    DESCRIPTION     "Lower 32 bits of sapEgQosPlcyPStatDrpOutProfPkts."
    ::= { sapEgrQosPlcyPolicerStatsEntry 21 }

sapEgQosPlcyPStatDrpOutProfPktsH OBJECT-TYPE
    SYNTAX          Counter32
    MAX-ACCESS      read-only
    STATUS          current
    DESCRIPTION     "Upper 32 bits of sapEgQosPlcyPStatDrpOutProfPkts."
    ::= { sapEgrQosPlcyPolicerStatsEntry 22 }

sapEgQosPlcyPStatOffInProfOcts OBJECT-TYPE
    SYNTAX          Counter64
    MAX-ACCESS      read-only
    STATUS          current
    DESCRIPTION     "The value of sapEgQosPlcyPStatOffInProfOcts
                     indicates the number ofin-profile octets (rate below CIR)
                     offered by the egress Qchip."
    ::= { sapEgrQosPlcyPolicerStatsEntry 23 }

sapEgQosPlcyPStatOffInProfOctsL OBJECT-TYPE
    SYNTAX          Counter32
    MAX-ACCESS      read-only
    STATUS          current
    DESCRIPTION     "Lower 32 bits of sapEgQosPlcyPStatOffInProfOcts."
    ::= { sapEgrQosPlcyPolicerStatsEntry 24 }

sapEgQosPlcyPStatOffInProfOctsH OBJECT-TYPE
    SYNTAX          Counter32
    MAX-ACCESS      read-only
    STATUS          current
    DESCRIPTION     "Upper 32 bits of sapEgQosPlcyPStatOffInProfOcts."
    ::= { sapEgrQosPlcyPolicerStatsEntry 25 }

sapEgQosPlcyPStatFwdInProfOcts OBJECT-TYPE
    SYNTAX          Counter64
    MAX-ACCESS      read-only
    STATUS          current
    DESCRIPTION     "The value of sapEgQosPlcyPStatFwdInProfOcts
                     indicates the number ofin-profile octets (rate below CIR)
                     forwarded by the egress Qchip."
    ::= { sapEgrQosPlcyPolicerStatsEntry 26 }

sapEgQosPlcyPStatFwdInProfOctsL OBJECT-TYPE
    SYNTAX          Counter32
    MAX-ACCESS      read-only
    STATUS          current
    DESCRIPTION     "Lower 32 bits of sapEgQosPlcyPStatFwdInProfOcts."
    ::= { sapEgrQosPlcyPolicerStatsEntry 27 }

sapEgQosPlcyPStatFwdInProfOctsH OBJECT-TYPE
    SYNTAX          Counter32
    MAX-ACCESS      read-only
    STATUS          current
    DESCRIPTION     "Upper 32 bits of sapEgQosPlcyPStatFwdInProfOcts."
    ::= { sapEgrQosPlcyPolicerStatsEntry 28 }

sapEgQosPlcyPStatDrpInProfOcts OBJECT-TYPE
    SYNTAX          Counter64
    MAX-ACCESS      read-only
    STATUS          current
    DESCRIPTION     "The value of sapEgQosPlcyPStatDrpInProfOcts
                     indicates the number in-profile octets discarded by the
                     egress Qchip due to: MBS exceeded, buffer pool limit
                     exceeded, etc."
    ::= { sapEgrQosPlcyPolicerStatsEntry 29 }

sapEgQosPlcyPStatDrpInProfOctsL OBJECT-TYPE
    SYNTAX          Counter32
    MAX-ACCESS      read-only
    STATUS          current
    DESCRIPTION     "Lower 32 bits of sapEgQosPlcyPStatDrpInProfOcts."
    ::= { sapEgrQosPlcyPolicerStatsEntry 30 }

sapEgQosPlcyPStatDrpInProfOctsH OBJECT-TYPE
    SYNTAX          Counter32
    MAX-ACCESS      read-only
    STATUS          current
    DESCRIPTION     "Upper 32 bits of sapEgQosPlcyPStatDrpInProfOcts."
    ::= { sapEgrQosPlcyPolicerStatsEntry 31 }

sapEgQosPlcyPStatOffOutProfOcts OBJECT-TYPE
    SYNTAX          Counter64
    MAX-ACCESS      read-only
    STATUS          current
    DESCRIPTION     "The value of sapEgQosPlcyPStatOffOutProfOcts
                     indicates the number of out-of-profile octets (rate
                     above CIR) offered by the egress Qchip."
    ::= { sapEgrQosPlcyPolicerStatsEntry 32 }

sapEgQosPlcyPStatOffOutProfOctsL OBJECT-TYPE
    SYNTAX          Counter32
    MAX-ACCESS      read-only
    STATUS          current
    DESCRIPTION     "Lower 32 bits of sapEgQosPlcyPStatOffOutProfOcts."
    ::= { sapEgrQosPlcyPolicerStatsEntry 33 }

sapEgQosPlcyPStatOffOutProfOctsH OBJECT-TYPE
    SYNTAX          Counter32
    MAX-ACCESS      read-only
    STATUS          current
    DESCRIPTION     "Upper 32 bits of sapEgQosPlcyPStatOffOutProfOcts."
    ::= { sapEgrQosPlcyPolicerStatsEntry 34 }

sapEgQosPlcyPStatFwdOutProfOcts OBJECT-TYPE
    SYNTAX          Counter64
    MAX-ACCESS      read-only
    STATUS          current
    DESCRIPTION     "The value of sapEgQosPlcyPStatFwdOutProfOcts
                     indicates the number of out-of-profile octets (rate
                     above CIR) forwarded by the egress Qchip."
    ::= { sapEgrQosPlcyPolicerStatsEntry 35 }

sapEgQosPlcyPStatFwdOutProfOctsL OBJECT-TYPE
    SYNTAX          Counter32
    MAX-ACCESS      read-only
    STATUS          current
    DESCRIPTION     "Lower 32 bits of sapEgQosPlcyPStatFwdOutProfOcts."
    ::= { sapEgrQosPlcyPolicerStatsEntry 36 }

sapEgQosPlcyPStatFwdOutProfOctsH OBJECT-TYPE
    SYNTAX          Counter32
    MAX-ACCESS      read-only
    STATUS          current
    DESCRIPTION     "Upper 32 bits of sapEgQosPlcyPStatFwdOutProfOcts."
    ::= { sapEgrQosPlcyPolicerStatsEntry 37 }

sapEgQosPlcyPStatDrpOutProfOcts OBJECT-TYPE
    SYNTAX          Counter64
    MAX-ACCESS      read-only
    STATUS          current
    DESCRIPTION     "The value of sapEgQosPlcyPStatDrpOutProfOcts
                     indicates the number out-of-profile octets discarded by
                     the egress Qchip due to: MBS exceeded, buffer pool limit
                     exceeded, etc."
    ::= { sapEgrQosPlcyPolicerStatsEntry 38 }

sapEgQosPlcyPStatDrpOutProfOctsL OBJECT-TYPE
    SYNTAX          Counter32
    MAX-ACCESS      read-only
    STATUS          current
    DESCRIPTION     "Lower 32 bits of sapEgQosPlcyPStatDrpOutProfOcts."
    ::= { sapEgrQosPlcyPolicerStatsEntry 39 }

sapEgQosPlcyPStatDrpOutProfOctsH OBJECT-TYPE
    SYNTAX          Counter32
    MAX-ACCESS      read-only
    STATUS          current
    DESCRIPTION     "Upper 32 bits of sapEgQosPlcyPStatDrpOutProfOcts."
    ::= { sapEgrQosPlcyPolicerStatsEntry 40 }

--
-- sapTmplTable
--

sapTmplTblLastChanged  OBJECT-TYPE
    SYNTAX          TimeStamp
    MAX-ACCESS      read-only
    STATUS          current
    DESCRIPTION
        "The value of sapTmplTblLastChanged indicates the sysUpTime
         at the time of the last modification of sapTmplTable.

         If no changes were made to the entry since the last re-initialization
         of the local network management subsystem, then this object contains a
         zero value."
    ::= { tmnxSapObjs 101 }

sapTmplTable OBJECT-TYPE
    SYNTAX          SEQUENCE OF SapTmplEntry
    MAX-ACCESS      not-accessible
    STATUS          current
    DESCRIPTION     "A table that contains basic SAP template information."
    ::= { tmnxSapObjs 102 }

sapTmplEntry OBJECT-TYPE
    SYNTAX          SapTmplEntry
    MAX-ACCESS      not-accessible
    STATUS          current
    DESCRIPTION     "Basic information about a specific SAP template."
    INDEX           { sapTmplName }
    ::= { sapTmplTable 1 }

SapTmplEntry ::=
    SEQUENCE {
        sapTmplName                         TNamedItem,
        sapTmplRowStatus                    RowStatus,
        sapTmplLastChanged                  TimeStamp,
        sapTmplSapCount                     Unsigned32,
        sapTmplType                         ServType,
        sapTmplIngressQosPolicyId           TTmplPolicyID,
        sapTmplIngressMacFilterId           TFilterID,
        sapTmplIngressIpFilterId            TFilterID,
        sapTmplEgressQosPolicyId            TTmplPolicyID,
        sapTmplEgressMacFilterId            TFilterID,
        sapTmplEgressIpFilterId             TFilterID,
        sapTmplCollectAcctStats             TruthValue,
        sapTmplIngressQosSchedulerPolicy    ServObjName,
        sapTmplEgressQosSchedulerPolicy     ServObjName,
        sapTmplIngressSharedQueuePolicy     ServObjName,
        sapTmplIngressMatchQinQDot1PBits    INTEGER,
        sapTmplIngressIpv6FilterId          TFilterID,
        sapTmplEgressIpv6FilterId           TFilterID,
        sapTmplIngUseMultipointShared       TruthValue,
        sapTmplEgressQinQMarkTopOnly        TruthValue,
        sapTmplEgressAggRateLimit           TPortSchedulerAggRateLimitPIR,
        sapTmplEgressFrameBasedAcctg        TruthValue,
        sapTmplIngressAggRateLimit          TPortSchedulerPIR,
        sapTmplIngPolicerPolicy             TNamedItemOrEmpty,
        sapTmplEgrPolicerPolicy             TNamedItemOrEmpty,
        sapTmplDot1agCfmMip                 TruthValue,
        sapTmplCpmProtPolicyId              TCpmProtPolicyIDOrDefault,
        sapTmplCpmProtMonitorMac            TruthValue,
        sapTmplCpmProtEthCfmMonitorFlags    BITS,
        sapTmplEgrAggRateLUB                TruthValue,
        sapTmplEthCfmSquelchIngress         BITS,
        sapTmplEgrAggRateLimit              Unsigned32
    }

sapTmplName OBJECT-TYPE
    SYNTAX      TNamedItem
    MAX-ACCESS  not-accessible
    STATUS      current
    DESCRIPTION
        "The value of the object sapTmplName specifies the
        SAP template name. This name should be unique within
        the SAP template domain."
    ::= { sapTmplEntry 1 }

sapTmplRowStatus OBJECT-TYPE
    SYNTAX          RowStatus
    MAX-ACCESS      read-create
    STATUS          current
    DESCRIPTION
        "This value of the object  sapTmplRowStatus specifies the
         status of this row."
    ::= { sapTmplEntry 2 }

sapTmplLastChanged OBJECT-TYPE
    SYNTAX       TimeStamp
    MAX-ACCESS   read-only
    STATUS       current
    DESCRIPTION  
        "The value of sapTmplLastChanged indicates the timestamp of last
        change to this row in sapTmplTable."
    ::= { sapTmplEntry 3 }  

sapTmplSapCount OBJECT-TYPE
    SYNTAX       Unsigned32
    MAX-ACCESS   read-only
    STATUS       current
    DESCRIPTION  
        "The value of sapTmplSapCount indicates the number of instantiated
        SAPs created using this template."
    ::= { sapTmplEntry 4 }  
    
sapTmplType OBJECT-TYPE
    SYNTAX          ServType
    MAX-ACCESS      read-create
    STATUS          current
    DESCRIPTION
        "This object indicates the type of service where this SAP is defined.

        An 'inconsistentValue' error is returned if an attempt is made to
        change the value of this object after row creation."
    ::= { sapTmplEntry 5 }  

sapTmplIngressQosPolicyId OBJECT-TYPE
    SYNTAX          TTmplPolicyID
    MAX-ACCESS      read-create
    STATUS          current
    DESCRIPTION     "The value of the object sapTmplIngressQosPolicyId specifies
                     the row index in the tSapIngressTable corresponding to this
                     ingress QoS policy, or one if no policy is specified.
                     The value 0 is needed for mirror SAPs that
                     cannot have a QoS policy assigned."
    DEFVAL          { 1 }
    ::= { sapTmplEntry 6 }

sapTmplIngressMacFilterId OBJECT-TYPE
    SYNTAX          TFilterID
    MAX-ACCESS      read-create
    STATUS          current
    DESCRIPTION     "The value of the object sapTmplIngressMacFilterId specifies
                     the row index in the tMacFilterTable corresponding to this
                     ingress filter, or zero if no filter is specified."
    DEFVAL          { 0 }
    ::= { sapTmplEntry 7 }

sapTmplIngressIpFilterId OBJECT-TYPE
    SYNTAX          TFilterID
    MAX-ACCESS      read-create
    STATUS          current
    DESCRIPTION     "The value of the object sapTmplIngressIpFilterId specifies
                     the row index in the tIPFilterTable corresponding to this
                     ingress filter, or zero if no filter is specified."
    DEFVAL          { 0 }
    ::= { sapTmplEntry 8 }

sapTmplEgressQosPolicyId OBJECT-TYPE
    SYNTAX          TTmplPolicyID
    MAX-ACCESS      read-create
    STATUS          current
    DESCRIPTION     "The row index in the tSapEgressTable
                     corresponding to this egress QoS policy,
                     or one if no policy is specified."
    DEFVAL          { 1 }
    ::= { sapTmplEntry 9 }

sapTmplEgressMacFilterId OBJECT-TYPE
    SYNTAX          TFilterID
    MAX-ACCESS      read-create
    STATUS          current
    DESCRIPTION     "The row index in the tMacFilterTable
                     corresponding to this egress filter,
                     or zero if no filter is specified."
    DEFVAL          { 0 }
    ::= { sapTmplEntry 10 }

sapTmplEgressIpFilterId OBJECT-TYPE
    SYNTAX          TFilterID
    MAX-ACCESS      read-create
    STATUS          current
    DESCRIPTION     "The row index in the tIPFilterTable
                     corresponding to this egress filter,
                     or zero if no filter is specified."
    DEFVAL          { 0 }
    ::= { sapTmplEntry 11 }

sapTmplCollectAcctStats OBJECT-TYPE
    SYNTAX          TruthValue
    MAX-ACCESS      read-create
    STATUS          current
    DESCRIPTION     "When the value of this object is 'true' the agent
                     collects accounting statistics on this SAP."
    DEFVAL          { false }
    ::= { sapTmplEntry 12 }

sapTmplIngressQosSchedulerPolicy OBJECT-TYPE
    SYNTAX          ServObjName
    MAX-ACCESS      read-create
    STATUS          current
    DESCRIPTION     "The value of sapTmplIngressQosSchedulerPolicy indicates
                     the ingress QoS scheduler for this SAP."
    DEFVAL          { "" }
    ::= { sapTmplEntry 13 }

sapTmplEgressQosSchedulerPolicy OBJECT-TYPE
    SYNTAX          ServObjName
    MAX-ACCESS      read-create
    STATUS          current
    DESCRIPTION     "The value of sapTmplEgressQosSchedulerPolicy indicates
                     the egress QoS scheduler for this SAP."
    DEFVAL          { "" }
    ::= { sapTmplEntry 14 }

sapTmplIngressSharedQueuePolicy OBJECT-TYPE
    SYNTAX          ServObjName
    MAX-ACCESS      read-create
    STATUS          current
    DESCRIPTION     "This object indicates the ingress shared queue policy
                     used by this SAP. When the value of this object is null
                     it means that the SAP will use individual ingress QoS
                     queues, instead of the shared ones."
    DEFVAL          { "" }
    ::= { sapTmplEntry 15 }

sapTmplIngressMatchQinQDot1PBits OBJECT-TYPE
    SYNTAX          INTEGER {
                        default (1),
                        top     (2),
                        bottom  (3)
                    }
    MAX-ACCESS      read-create
    STATUS          current
    DESCRIPTION     "This object applies only to SAP's defined on a port
                     configured for qinq service encapsulation. It indicates
                     which 802.1P bits will be used to match a QoS or a MAC
                     filter policy when a double-tagged frame is received on
                     this SAP."
    DEFVAL          { default }
    ::= { sapTmplEntry 16 }

sapTmplIngressIpv6FilterId OBJECT-TYPE
    SYNTAX          TFilterID
    MAX-ACCESS      read-create
    STATUS          current
    DESCRIPTION     "The value of the object sapTmplIngressIpv6FilterId
                     specifies the row index in the tIPv6FilterTable
                     corresponding to this ingress ipv6 filter, or zero if no
                     ipv6 filter is specified."
    DEFVAL          { 0 }
    ::= { sapTmplEntry 17 }

sapTmplEgressIpv6FilterId OBJECT-TYPE
    SYNTAX          TFilterID
    MAX-ACCESS      read-create
    STATUS          current
    DESCRIPTION     "The value of the object sapTmplEgressIpv6FilterId specifies
                     the row index in the tIPv6FilterTable corresponding to
                     this egress ipv6 filter, or zero if no ipv6 filter is
                     specified."
    DEFVAL          { 0 }
    ::= { sapTmplEntry 18 }

sapTmplIngUseMultipointShared       OBJECT-TYPE
    SYNTAX          TruthValue
    MAX-ACCESS      read-create
    STATUS          current
    DESCRIPTION     "When the value of sapIngressSharedQueuePolicy is not null,
                     the value of the object sapTmplIngUseMultipointShared
                     specifies whether this SAP uses the multipoint-shared
                     queues of the shared policy."
    DEFVAL          { false }
    ::= { sapTmplEntry 19 }
    
sapTmplEgressQinQMarkTopOnly OBJECT-TYPE
    SYNTAX          TruthValue
    MAX-ACCESS      read-create
    STATUS          current
    DESCRIPTION     "When the encapsulation type of the access port where
                     this SAP is defined is qinq, the value of the object
                     sapTmplEgressQinQMarkTopOnly specifies which P-bits to mark
                     during packet egress. When the value is false both set
                     of P-bits are marked. When the value is true, only the
                     P-bits in the top Q-tag are marked."
    DEFVAL          { false }
    ::= { sapTmplEntry 20 }

sapTmplEgressAggRateLimit   OBJECT-TYPE
    SYNTAX          TPortSchedulerAggRateLimitPIR
    UNITS           "kbps"
    MAX-ACCESS      read-create
    STATUS          obsolete
    DESCRIPTION     "The value of the object sapTmplEgressAggRateLimit
                     specifies the maximum total rate of all egress queues for
                     this SAP. The value '-1' means that there
                     is no limit.
                     
                     This object is obsoleted in 13.0 release and replaced by
                     sapTmplEgrAggRateLimit."
    DEFVAL          { -1 }
    ::= { sapTmplEntry 21 }

sapTmplEgressFrameBasedAcctg OBJECT-TYPE
    SYNTAX       TruthValue
    MAX-ACCESS   read-create
    STATUS       current
    DESCRIPTION
        "The value of sapTmplEgressFrameBasedAcctg specifies whether
         to use frame-based accounting when evaluating 
         sapTmplEgrAggRateLimit for all egress queues for this SAP.

         If the value is 'false', the default packet-based accounting
         method will be used."
    DEFVAL { false }
    ::= { sapTmplEntry 22 }

sapTmplIngressAggRateLimit   OBJECT-TYPE
    SYNTAX          TPortSchedulerPIR
    UNITS           "kbps"
    MAX-ACCESS      read-create
    STATUS          obsolete
    DESCRIPTION     "The value of the object sapTmplIngressAggRateLimit
                     specifies the maximum total rate of all ingress queues for
                     this SAP. The value '-1' means that there
                     is no limit.
                     
                     This object is obsoleted in 10.0 Release."
    DEFVAL          { -1 }
    ::= { sapTmplEntry 23 }

sapTmplIngPolicerPolicy OBJECT-TYPE
    SYNTAX      TNamedItemOrEmpty
    MAX-ACCESS  read-create
    STATUS      current
    DESCRIPTION
        "The value of sapTmplIngPolicerPolicy specifies the ingress
         policer control policy applicable."
    DEFVAL { ''H }
    ::= { sapTmplEntry 24 }

sapTmplEgrPolicerPolicy OBJECT-TYPE
    SYNTAX      TNamedItemOrEmpty
    MAX-ACCESS  read-create
    STATUS      current
    DESCRIPTION
        "The value of sapTmplEgrPolicerPolicy specifies the egress
         policer control policy applicable."
    DEFVAL { ''H }
    ::= { sapTmplEntry 25 }

sapTmplDot1agCfmMip OBJECT-TYPE
    SYNTAX       TruthValue
    MAX-ACCESS   read-create
    STATUS       current
    DESCRIPTION
        "The value of sapTmplDot1agCfmMip specifies whether Maintance 
        Intermediate Points (MIP) will be created."
    DEFVAL { false }
    ::= { sapTmplEntry 26 }

sapTmplCpmProtPolicyId  OBJECT-TYPE
    SYNTAX          TCpmProtPolicyIDOrDefault
    MAX-ACCESS      read-create
    STATUS          current
    DESCRIPTION
        "The value of sapTmplCpmProtPolicyId associates a CPM Protection
         policy with a SAP.

         A value of '-1' specifies that the system will determine the CPM
         Protection policy for this SAP."
    DEFVAL  { -1 }
    ::= { sapTmplEntry 27 }

sapTmplCpmProtMonitorMac OBJECT-TYPE
    SYNTAX          TruthValue
    MAX-ACCESS      read-create
    STATUS          current
    DESCRIPTION
        "The value of sapTmplCpmProtMonitorMac specifies whether the
         tmnxCpmProtPolPerSrcRateLimit of the CPM Protection policy
         must be applied.

         If the value of sapTmplCpmProtMonitorMac is 'true', the
         per-source rate limit must be applied.

         The sapTmplCpmProtMonitorMac will be ignored if the system derived
         CPM Protection Policy from sapTmplCpmProtPolicyId is set to 'zero'
         for the instantiated SAP.

         At most one of sapTmplCpmProtMonitorMac and the
         sapTmplCpmProtEthCfmMonitorFlags option 'ethCfmMonitor(0)' can be
         enabled for this template."
    DEFVAL          { false }
    ::= { sapTmplEntry 28 }

sapTmplCpmProtEthCfmMonitorFlags   OBJECT-TYPE
    SYNTAX      BITS {
        ethCfmMonitor(0),
        ethCfmMonitorAggregate(1),
        ethCfmMonitorCommittedAccessRate(2)
    }
    MAX-ACCESS  read-create
    STATUS      current
    DESCRIPTION
        "The value of sapTmplCpmProtEthCfmMonitorFlags specifies whether or not
         to apply rate limiting (using the tmnxCpmProtEthCfmPolTable
         configuration) to Ethernet Connectivity Fault Management (Eth-CFM)
         packets served by a SAP created using this template.  Two associated
         options are also specified.

         Five combinations of flag values are supported, as shown in the
         following table.

         Flag                                    Value (0=Disabled, 1=Enabled)
         -------------------------------------   -----------------------------
         'ethCfmMonitor(0)'                      0   0   0   0   1   1   1   1
         'ethCfmMonitorAggregate(1)'             0   0   1   1   0   0   1   1
         'ethCfmMonitorCommittedAccessRate(2)'   0   1   0   1   0   1   0   1
         -------------------------------------   -----------------------------
         Supported Combination?                  Y   N   N   N   Y   Y   Y   Y

         If 'ethCfmMonitor(0)' is disabled, Eth-CFM rate limiting is disabled on
         the SAP.

         If 'ethCfmMonitor(0)' is enabled, Eth-CFM rate limiting is enabled on
         the SAP.  Excess packets are discarded.  The configured information
         used to perform the Eth-CFM rate limiting (e.g. the rate limit(s))
         resides in the tmnxCpmProtEthCfmPolTable row(s) indexed by the
         template's sapTmplCpmProtPolicyId.

         At most one of 'ethCfmMonitor(0)' and sapTmplCpmProtMonitorMac can be
         enabled for this template.

         The flags 'ethCfmMonitorAggregate(1)' and
         'ethCfmMonitorCommittedAccessRate(2)' adjust the behavior of Eth-CFM
         rate limiting.  Therefore, they are only significant if Eth-CFM rate
         limiting is enabled (i.e. when 'ethCfmMonitor(0)' is enabled).  The
         remainder of this DESCRIPTION assumes 'ethCfmMonitor(0)' is enabled.

         If 'ethCfmMonitorAggregate(1)' is disabled, the applicable Eth-CFM
         packet rate limit (tmnxCpmProtEthCfmPolRateLimit) applies per peer
         (i.e. on a source MAC address basis).  For example, if the SAP's rate
         limit for all Eth-CFM packets is 100 packets/sec, and two peers are
         served by the SAP, then 100 Eth-CFM packets/sec from each peer is
         within the limit.

         If 'ethCfmMonitorAggregate(1)' is enabled, the applicable Eth-CFM
         packet rate limit (tmnxCpmProtEthCfmPolRateLimit) applies to the
         aggregated traffic flow.  For example, if the SAP's rate limit for all
         Eth-CFM packets is 100 packets/sec, and two peers are served by this
         SAP, then the combined rate of the two peers cannot exceed 100
         packets/sec.

         'ethCfmMonitorCommittedAccessRate(2)' controls the interaction
         between two features:  Eth-CFM rate limiting, and overall rate limiting
         (as configured using tmnxCpmProtPolOverallRateLimit).

         If 'ethCfmMonitorCommittedAccessRate(2)' is disabled, an Eth-CFM
         packet is subjected to two rate limits, in the following order.
         a) The applicable tmnxCpmProtEthCfmPolRateLimit is applied, as
            described above.  If the packet exceeds the limit, it is discarded.
            Otherwise...
         b) The SAP's tmnxCpmProtPolOverallRateLimit (which is applied
            to Eth-CFM packets, and the other rate limited packet types) is
            applied.

         If 'ethCfmMonitorCommittedAccessRate(2)' is enabled, an Eth-CFM packet
         is subjected to one rate limit:  the applicable
         tmnxCpmProtEthCfmPolRateLimit, as described above.  Eth-CFM packets
         are neither counted nor discarded when performing the
         tmnxCpmProtPolOverallRateLimit rate limiting."
    DEFVAL { {} }
    ::= { sapTmplEntry 29 }

sapTmplEgrAggRateLUB           OBJECT-TYPE
    SYNTAX      TruthValue
    MAX-ACCESS  read-create
    STATUS      current
    DESCRIPTION 
        "The value of sapTmplEgrAggRateLUB specifies whether to limit the unused
         bandwidth and allow a tighter control in allocation of bandwidth by
         HQos.

         When the value of sapTmplEgrAggRateLUB is set to 'true', HQos algorithm
         distributes any unused aggregate bandwidth between queues operating
         below their fair share rates. This allows a simplified aggregate rate
         protection while allocating bandwidth by HQos scheduling algorithm."
    DEFVAL { false }
    ::= { sapTmplEntry 30 }

sapTmplEthCfmSquelchIngress  OBJECT-TYPE
    SYNTAX      BITS {
                    level0 (0),
                    level1 (1),
                    level2 (2),
                    level3 (3),
                    level4 (4),
                    level5 (5),
                    level6 (6),
                    level7 (7)
                }
    MAX-ACCESS  read-create
    STATUS      current
    DESCRIPTION
        "The value of sapTmplEthCfmSquelchIngress specifies the ETH-CFM 
         level or levels that are silently discarded on ingress to the SAP. 
         Any received ETH-CFM PDU matching a level that has been set will be 
         dropped without regard for any other ETH-CFM criteria.
         
         No statistical information or drop count will be available for any 
         ETH-CFM PDU that is silently discarded by this option."
    DEFVAL { { } }
    ::= { sapTmplEntry 31 }



sapTmplEgrAggRateLimit              OBJECT-TYPE
    SYNTAX          Unsigned32 (1..3200000000 | 4294967295)
    UNITS           "kbps"
    MAX-ACCESS      read-create
    STATUS          current
    DESCRIPTION
        "The value of sapTmplEgrAggRateLimit specifies the maximum total rate
         of all egress queues for this SAP.
         The value of 4294967295 (0xFFFFFFFF) means that there is no limit."
    DEFVAL { 4294967295 }
    ::= { sapTmplEntry 34 }

--
-- sapTmplTlsTable
--

sapTmplTlsTblLastChanged  OBJECT-TYPE
    SYNTAX          TimeStamp
    MAX-ACCESS      read-only
    STATUS          current
    DESCRIPTION
        "The value of sapTmplTlsTblLastChanged indicates the sysUpTime
         at the time of the last modification of sapTmplTlsTable.

         If no changes were made to the entry since the last re-initialization
         of the local network management subsystem, then this object contains a
         zero value."
    ::= { tmnxSapObjs 103 }

sapTmplTlsTable OBJECT-TYPE
    SYNTAX          SEQUENCE OF SapTmplTlsEntry
    MAX-ACCESS      not-accessible
    STATUS          current
    DESCRIPTION
        "A table that contains VPLS SAP template information."
    ::= { tmnxSapObjs 104 }

sapTmplTlsEntry OBJECT-TYPE
    SYNTAX          SapTmplTlsEntry
    MAX-ACCESS      not-accessible
    STATUS          current
    DESCRIPTION
        "This table contains basic information about a specific VPLS SAP
        template. An entry in this table is created when an entry is
        created in the sapTmplTable with sapTmplType set to 'tls'.
        Entry is deleted when corresponding entry is deleted in
        sapTmplTable."
    INDEX           { sapTmplName }
    ::= { sapTmplTlsTable 1 }

SapTmplTlsEntry ::=
    SEQUENCE {
        sapTmplTlsLastChanged               TimeStamp,
        sapTmplTlsMacAgeing                 TmnxEnabledDisabled,
        sapTmplTlsStpAdminStatus            TmnxEnabledDisabled,
        sapTmplTlsStpPriority               INTEGER,
        sapTmplTlsStpPathCost               INTEGER,
        sapTmplTlsStpRapidStart             TmnxEnabledDisabled,
        sapTmplTlsStpBpduEncap              INTEGER,
        sapTmplTlsMacAddressLimit           Integer32,
        sapTmplTlsMacLearning               TmnxEnabledDisabled,
        sapTmplTlsStpAdminPointToPoint      INTEGER,
        sapTmplTlsStpAutoEdge               TmnxEnabledDisabled,
        sapTmplTlsDiscardUnknownSource      TmnxEnabledDisabled,
        sapTmplTlsL2ptTermination           TmnxEnabledDisabled,
        sapTmplTlsBpduTranslation           TlsBpduTranslation,
        sapTmplTlsStpRootGuard              TruthValue,
        sapTmplTlsL2ptProtocols             L2ptProtocols,
        sapTmplTlsLimitMacMove              TlsLimitMacMove,
        sapTmplTlsLimitMacMoveLevel         TlsLimitMacMoveLevel
    }

sapTmplTlsLastChanged OBJECT-TYPE
    SYNTAX       TimeStamp
    MAX-ACCESS   read-only
    STATUS       current
    DESCRIPTION  
        "The value of sapTmplTlsLastChanged indicates the timestamp of last
        change to this row in sapTmplTlsTable."
    ::= { sapTmplTlsEntry 1 }  
    
sapTmplTlsMacAgeing OBJECT-TYPE
    SYNTAX          TmnxEnabledDisabled
    MAX-ACCESS      read-write
    STATUS          current
    DESCRIPTION
        "The value of the object sapTmplTlsMacAgeing specifies whether
         the MAC aging process is enabled for this SAP template. The value
         will be ignored if MAC aging is disabled on service level."
    DEFVAL          { enabled }
    ::= { sapTmplTlsEntry 2 }

sapTmplTlsStpAdminStatus OBJECT-TYPE
    SYNTAX          TmnxEnabledDisabled
    MAX-ACCESS      read-write
    STATUS          current
    DESCRIPTION     "The value of the object sapTmplTlsStpAdminStatus specifies
                     whether this SAP participates in the TLS's Spanning Tree
                     Protocol."
    DEFVAL          { enabled }
    ::= { sapTmplTlsEntry 3 }

sapTmplTlsStpPriority OBJECT-TYPE
    SYNTAX          INTEGER (0..255)
    MAX-ACCESS      read-write
    STATUS          current
    DESCRIPTION     "The value of the object sapTmplTlsStpPriority specifies
                     the value of the port priority field which is contained in
                     the most significant 4 bits of the 16-bit Port ID
                     associated with this SAP. As only the most significant 4
                     bits of the value are used, the actual value of this object
                     is limited to multiples of 16: e.g. the agent rounds down
                     the value to one of: 0, 16, 32, .. , 224, 240."
    DEFVAL          { 128 }
    ::= { sapTmplTlsEntry 4 }

sapTmplTlsStpPathCost OBJECT-TYPE
    SYNTAX          INTEGER (1..200000000)
    MAX-ACCESS      read-write
    STATUS          current
    DESCRIPTION     "The value of the object  sapTmplTlsStpPathCost specifies the
                     contribution of this port to the path cost of paths
                     towards the spanning tree root which include this port."
    DEFVAL          { 10 }
    ::= { sapTmplTlsEntry 5 }

sapTmplTlsStpRapidStart OBJECT-TYPE
    SYNTAX          TmnxEnabledDisabled
    MAX-ACCESS      read-write
    STATUS          current
    DESCRIPTION     "The value of the object sapTmplTlsStpRapidStart specifies
                     whether Rapid Start is enabled on this SAP. When the value
                     is 'enabled' the Spanning Tree Protocol state transitions
                     on this SAP are driven by the value of the 'HelloTime'
                     instead of the value of 'ForwardDelay', thus allowing a
                     faster transition into the forwarding state. This
                     parameter is also referred to as 'adminEdge'. "
    DEFVAL          { disabled }
    ::= { sapTmplTlsEntry 6 }

sapTmplTlsStpBpduEncap OBJECT-TYPE
    SYNTAX          INTEGER {
                        dynamic (1),
                        dot1d   (2),
                        pvst    (3)
                    }
    MAX-ACCESS      read-write
    STATUS          current
    DESCRIPTION     "The value of the object sapTmplTlsStpBpduEncap specifies the
                     type of encapsulation used on BPDUs sent out and received
                     on this SAP."
    DEFVAL          { dynamic }
    ::= { sapTmplTlsEntry 7 }

sapTmplTlsMacAddressLimit OBJECT-TYPE
    SYNTAX          Integer32(0..511999)
    MAX-ACCESS      read-write
    STATUS          current
    DESCRIPTION     "The value of the object sapTmplTlsMacAddressLimit specifies
                     the maximum number of learned and static entries allowed
                     in the FDB of this SAP. The value 0 means: no limit for
                     this SAP."
    DEFVAL          { 0 }
    ::= { sapTmplTlsEntry 8 }


sapTmplTlsMacLearning OBJECT-TYPE
    SYNTAX          TmnxEnabledDisabled
    MAX-ACCESS      read-write
    STATUS          current
    DESCRIPTION     "The value of the object sapTmplTlsMacLearning specifies
                     whether the MAC learning process  is enabled for this SAP.
                     The value is ignored if MAC learning is disabled on
                     service level."
    DEFVAL          { enabled }
    ::= { sapTmplTlsEntry 9 }

sapTmplTlsStpAdminPointToPoint OBJECT-TYPE
    SYNTAX          INTEGER {
                        forceTrue  (0),
                        forceFalse (1)
                    }
    MAX-ACCESS      read-write
    STATUS          current
    DESCRIPTION     "The value of the object sapTmplTlsStpAdminPointToPoint
                     specifies the administrative point-to-point  status  of
                     the LAN segment attached to this  sap. The value
                     'forceTrue' means that this port should  always  be
                     treated as if it is connected to a point-to-point link.
                     The value of 'forceFalse' means that this port should
                     be treated as having a shared media connection."
    REFERENCE
                    "IEEE 802.1w clause 6.4.3, 6.5, 14.8.2"
    DEFVAL          { forceTrue }
    ::= { sapTmplTlsEntry 10 }

sapTmplTlsStpAutoEdge OBJECT-TYPE
    SYNTAX          TmnxEnabledDisabled
    MAX-ACCESS      read-write
    STATUS          current
    DESCRIPTION     "sapTmplTlsStpAutoEdge specifies whether this SAP
                     is enabled for auto-edge detection as defined by Rapid
                     Spanning Tree Protocol."
    DEFVAL          { enabled }
    ::= { sapTmplTlsEntry 11 }

sapTmplTlsDiscardUnknownSource OBJECT-TYPE
    SYNTAX          TmnxEnabledDisabled
    MAX-ACCESS      read-write
    STATUS          current
    DESCRIPTION     "with   the object sapTmplTlsMacAddressLimit a limit can be
                     configured  for  the  max number of MAC addresses that
                     will  be learned on this  SAP.  When  this limit is
                     reached, packets with unknown source MAC address are
                     forwarded by default. By setting
                     sapTmplTlsDiscardUnknownSource  to enabled, packets with
                     unknown source MAC will be dropped in stead."
    DEFVAL          { disabled }
    ::= { sapTmplTlsEntry 12 }

sapTmplTlsL2ptTermination OBJECT-TYPE
    SYNTAX          TmnxEnabledDisabled
    MAX-ACCESS      read-write
    STATUS          current
    DESCRIPTION     "The value of the object sapTmplTlsL2ptTermination specifies
                     whether received Layer 2 Protocol Tunnel (L2PT) pdu's 
                     are terminated on this port or sap."
    DEFVAL          { disabled }
    ::= { sapTmplTlsEntry 13 }

sapTmplTlsBpduTranslation OBJECT-TYPE
    SYNTAX          TlsBpduTranslation
    MAX-ACCESS      read-write
    STATUS          current
    DESCRIPTION     "The value of the object sapTmplTlsBpduTranslation specifies
                     whether received L2 Protocol Tunnel pdu's are
                     translated before being sent out on this port or sap."
    DEFVAL          { disabled }
    ::= { sapTmplTlsEntry 14 }

sapTmplTlsStpRootGuard OBJECT-TYPE
    SYNTAX          TruthValue
    MAX-ACCESS      read-write
    STATUS          current
    DESCRIPTION     "The value of the object sapTmplTlsStpRootGuard specifies
                     whether this port is allowed to become STP root port.
                     It corresponds to the parameter 'restrictedRole' in 802.1Q.
                     If set, it can cause lack of spanning tree connectivity."
    DEFVAL          { false }
    ::= { sapTmplTlsEntry 15 }

sapTmplTlsL2ptProtocols OBJECT-TYPE
    SYNTAX          L2ptProtocols
    MAX-ACCESS      read-write
    STATUS          current
    DESCRIPTION     "The value of the object sapTmplTlsL2ptTermination specifies
                     which L2 Protocol Tunnel pdu's are terminated
                     on this port or sap."
    DEFVAL          { { stp } }
    ::= { sapTmplTlsEntry 16 }

sapTmplTlsLimitMacMove OBJECT-TYPE
    SYNTAX          TlsLimitMacMove
    MAX-ACCESS      read-write
    STATUS          current
    DESCRIPTION     "When sapTmplTlsLimitMacMove value is set  to  'blockable'
                     the  agent will monitor the MAC relearn rate on this
                     SAP,  and it will  block  it  when the re-learn rate
                     specified  by  svcTlsMacMoveMaxRate  is exceeded. When
                     the  value is  'nonBlockable'  this  SAP will not be
                     blocked,  and  another  blockable  SAP will be blocked
                     instead."
    DEFVAL          { blockable }
    ::= { sapTmplTlsEntry 17 }

sapTmplTlsLimitMacMoveLevel OBJECT-TYPE
    SYNTAX          TlsLimitMacMoveLevel
    MAX-ACCESS      read-write
    STATUS          current
    DESCRIPTION     "The value of the object sapTmplTlsLimitMacMoveLevel
                     specifies the hierarchy in which SAPs are
                     blocked when a MAC-move limit is exceeded. When a MAC is
                     moving among multiple SAPs or spoke-SDPs, the SAP bind
                     or spoke-SDP bind with the lower level is blocked first.
                     (tertiary is the lowest)"
    DEFVAL          { tertiary }
    ::= { sapTmplTlsEntry 18 }


-- sap mvrp end-station vlan-id group

sapTlsEsVidGrpTblLastChanged  OBJECT-TYPE
    SYNTAX          TimeStamp
    MAX-ACCESS      read-only
    STATUS          current
    DESCRIPTION
        "The value of sapTlsEsVidGrpTblLastChanged indicates the sysUpTime
         at the time of the last modification of sapTlsEsVidGrpTable.

         If no changes were made to the entry since the last re-initialization
         of the local network management subsystem, then this object contains a
         zero value."
    ::= { tmnxSapObjs 105 }

sapTlsEsVidGrpTable OBJECT-TYPE
    SYNTAX          SEQUENCE OF SapTlsEsVidGrpEntry
    MAX-ACCESS      not-accessible
    STATUS          current
    DESCRIPTION
        "A table that contains TLS SAP specific Mutliple VLAN Registration
        Protocol (MVRP) end-station VLAN range group information."
    ::= { tmnxSapObjs 106 }

sapTlsEsVidGrpEntry OBJECT-TYPE
    SYNTAX          SapTlsEsVidGrpEntry
    MAX-ACCESS      not-accessible
    STATUS          current
    DESCRIPTION
        "A table that contains TLS SAP specific MVRP end-station VLAN range
        group information."
    INDEX           { svcId, sapPortId, sapEncapValue, sapTlsEsVidGrpId }
    ::= { sapTlsEsVidGrpTable 1 }

SapTlsEsVidGrpEntry ::=
    SEQUENCE {
        sapTlsEsVidGrpId                TmnxVlanGroupId,
        sapTlsEsVidGrpRowStatus         RowStatus,
        sapTlsEsVidGrpLastChgd          TimeStamp,
        sapTlsEsVidGrpStartVlanTag      QTag,
        sapTlsEsVidGrpEndVlanTag        QTag
    }

sapTlsEsVidGrpId OBJECT-TYPE
    SYNTAX          TmnxVlanGroupId
    MAX-ACCESS      not-accessible
    STATUS          current
    DESCRIPTION
        "The value of the object sapTlsEsVidGrpId specifies the MVRP
         end-station VLAN range group identfier. This identifiter should be
         unique within this SAP domain."
    ::= { sapTlsEsVidGrpEntry 1 }

sapTlsEsVidGrpRowStatus OBJECT-TYPE
    SYNTAX          RowStatus
    MAX-ACCESS      read-create
    STATUS          current
    DESCRIPTION
        "This value of the object sapTlsEsVidGrpRowStatus specifies the
         status of this row."
    ::= { sapTlsEsVidGrpEntry 2 }

sapTlsEsVidGrpLastChgd OBJECT-TYPE
    SYNTAX       TimeStamp
    MAX-ACCESS   read-only
    STATUS       current
    DESCRIPTION  
        "The value of sapTlsEsVidGrpLastChgd indicates the timestamp of last
        change to this row in sapTlsEsVidGrpTable."
    ::= { sapTlsEsVidGrpEntry 3 }  
    
sapTlsEsVidGrpStartVlanTag OBJECT-TYPE
    SYNTAX          QTag
    MAX-ACCESS      read-create
    STATUS          current
    DESCRIPTION
        "The value of the object sapTlsEsVidGrpStartVlanTag specifies the
        start of the VLAN tag range.

        An 'inconsistentValue' error is returned if value of this object is
        not specified at the time of row-creation."
    ::= { sapTlsEsVidGrpEntry 4 }

sapTlsEsVidGrpEndVlanTag OBJECT-TYPE
    SYNTAX          QTag
    MAX-ACCESS      read-create
    STATUS          current
    DESCRIPTION
        "The value of the object sapTlsEsVidGrpEndVlanTag specifies the
        end of the VLAN tag range.

        An 'inconsistentValue' error is returned if value of this object is
        not specified at the time of row-creation."
    ::= { sapTlsEsVidGrpEntry 5 }

-- SAP template users table

sapTmplUserTable OBJECT-TYPE
    SYNTAX          SEQUENCE OF SapTmplUserEntry
    MAX-ACCESS      not-accessible
    STATUS          current
    DESCRIPTION
        "A table that contains SAPs which are created using SAP templates."
    ::= { tmnxSapObjs 107 }

sapTmplUserEntry OBJECT-TYPE
    SYNTAX          SapTmplUserEntry
    MAX-ACCESS      not-accessible
    STATUS          current
    DESCRIPTION
        "This table provides information about SAP created using a SAP template.

        Entries are created and deleted by the system."
    INDEX   { sapTmplName, svcId, sapPortId, sapEncapValue }
    ::= { sapTmplUserTable 1 }

SapTmplUserEntry ::=
    SEQUENCE {
        sapTmplUserCreationOrigin    INTEGER,
        sapTmplUserCreatorSvcId      TmnxServId
    }

sapTmplUserCreationOrigin OBJECT-TYPE
    SYNTAX          INTEGER {
                         mVpls (1)
                         }
    MAX-ACCESS      read-only
    STATUS          current
    DESCRIPTION
        "The value sapTmplUserCreationOrigin indicates how this SAP was created
        using this specific SAP template."
    ::= { sapTmplUserEntry 1 }

sapTmplUserCreatorSvcId OBJECT-TYPE
    SYNTAX          TmnxServId
    MAX-ACCESS      read-only
    STATUS          current
    DESCRIPTION
        "The value sapTmplUserCreatorSvcId indicates the service identifier
        which created this particular SAP using this template.

        A value of zero indicates that the SAP is not created by a service."
    ::= { sapTmplUserEntry 2 }

-- ----------------------------------------
-- sapIngQosArbitStatsTable
-- ----------------------------------------
sapIngQosArbitStatsTable OBJECT-TYPE
    SYNTAX      SEQUENCE OF SapIngQosArbitStatsEntry
    MAX-ACCESS  not-accessible
    STATUS      current
    DESCRIPTION
        "The sapIngQosArbitStatsTable contains ingress QoS arbiter statistics
         about SAPs.

         In the descriptions below 'Pchip' refers to the Nokia SROS 
         series Packet Processing chip, while 'Qchip' refers to the 
         Nokia SROS series QoS Queueing Engine chip."
    ::= { tmnxSapObjs 108 }

sapIngQosArbitStatsEntry OBJECT-TYPE
    SYNTAX      SapIngQosArbitStatsEntry
    MAX-ACCESS  not-accessible
    STATUS      current
    DESCRIPTION
        "Each row entry contains ingress statistics about a particular
         SAP QoS arbiter."
    INDEX { svcId, sapPortId, sapEncapValue,
             sapIngQosArbitStatsName }
    ::= { sapIngQosArbitStatsTable 1 }

SapIngQosArbitStatsEntry ::=
    SEQUENCE {
        sapIngQosArbitStatsName      TNamedItem,
        sapIngQosArbitStatsFwdPkts   Counter64,
        sapIngQosArbitStatsFwdPktsLo Counter32,
        sapIngQosArbitStatsFwdPktsHi Counter32,
        sapIngQosArbitStatsFwdOcts   Counter64,
        sapIngQosArbitStatsFwdOctsLo Counter32,
        sapIngQosArbitStatsFwdOctsHi Counter32
    }

sapIngQosArbitStatsName OBJECT-TYPE
    SYNTAX      TNamedItem
    MAX-ACCESS  not-accessible
    STATUS      current
    DESCRIPTION
        "The value of sapIngQosArbitStatsName specifies the ingress QoS
         arbiter of this SAP."
    ::= { sapIngQosArbitStatsEntry 1 }

sapIngQosArbitStatsFwdPkts OBJECT-TYPE
    SYNTAX      Counter64
    MAX-ACCESS  read-only
    STATUS      current
    DESCRIPTION
        "The value of sapIngQosArbitStatsFwdPkts indicates the number of
         forwarded packets, as determined by the SAP ingress policer
         control policy, offered by the Pchip to the Qchip."
    ::= { sapIngQosArbitStatsEntry 2 }

sapIngQosArbitStatsFwdPktsLo OBJECT-TYPE
    SYNTAX          Counter32
    MAX-ACCESS      read-only
    STATUS          current
    DESCRIPTION
        "The value of sapIngQosArbitStatsFwdPktsLo indicates the lower 32
         bits of sapIngQosArbitStatsFwdPkts."
    ::= { sapIngQosArbitStatsEntry 3 }

sapIngQosArbitStatsFwdPktsHi OBJECT-TYPE
    SYNTAX          Counter32
    MAX-ACCESS      read-only
    STATUS          current
    DESCRIPTION
        "The value of sapIngQosArbitStatsFwdPktsHi indicates the upper 32
         bits of sapIngQosArbitStatsFwdPkts."
    ::= { sapIngQosArbitStatsEntry 4 }

sapIngQosArbitStatsFwdOcts OBJECT-TYPE
    SYNTAX      Counter64
    MAX-ACCESS  read-only
    STATUS      current
    DESCRIPTION
        "The value of sapIngQosArbitStatsFwdOcts indicates the number of
         forwarded octets, as determined by the SAP ingress policer
         control policy, offered by the Pchip to the Qchip."
    ::= { sapIngQosArbitStatsEntry 5 }

sapIngQosArbitStatsFwdOctsLo OBJECT-TYPE
    SYNTAX          Counter32
    MAX-ACCESS      read-only
    STATUS          current
    DESCRIPTION
        "The value of sapIngQosArbitStatsFwdOctsLo indicates the lower 32 bits
         of sapIngQosArbitStatsFwdOcts."
    ::= { sapIngQosArbitStatsEntry 6 }

sapIngQosArbitStatsFwdOctsHi OBJECT-TYPE
    SYNTAX          Counter32
    MAX-ACCESS      read-only
    STATUS          current
    DESCRIPTION
        "The value of sapIngQosArbitStatsFwdOctsHi indicates the upper 32 bits
         of sapIngQosArbitStatsFwdOcts."
    ::= { sapIngQosArbitStatsEntry 7 }

-- ----------------------------------------
-- sapEgrQosArbitStatsTable
-- ----------------------------------------
sapEgrQosArbitStatsTable OBJECT-TYPE
    SYNTAX      SEQUENCE OF SapEgrQosArbitStatsEntry
    MAX-ACCESS  not-accessible
    STATUS      current
    DESCRIPTION
        "The sapEgrQosArbitStatsTable contains egress QoS arbiter
         statistics about SAPs.
         In the descriptions below 'Pchip' refers to the Nokia SROS 
         series Packet Processing chip, while 'Qchip' refers to the 
         Nokia SROS series QoS Queueing Engine chip."
    ::= { tmnxSapObjs 109 }

sapEgrQosArbitStatsEntry OBJECT-TYPE
    SYNTAX      SapEgrQosArbitStatsEntry
    MAX-ACCESS  not-accessible
    STATUS      current
    DESCRIPTION
        "Each row entry contains egress statistics about a particular
         SAP QoS arbiter."
    INDEX { svcId, sapPortId, sapEncapValue,
             sapEgrQosArbitStatsName }
    ::= { sapEgrQosArbitStatsTable 1 }

SapEgrQosArbitStatsEntry ::=
    SEQUENCE {
        sapEgrQosArbitStatsName      TNamedItem,
        sapEgrQosArbitStatsFwdPkts   Counter64,
        sapEgrQosArbitStatsFwdPktsLo Counter32,
        sapEgrQosArbitStatsFwdPktsHi Counter32,
        sapEgrQosArbitStatsFwdOcts   Counter64,
        sapEgrQosArbitStatsFwdOctsLo Counter32,
        sapEgrQosArbitStatsFwdOctsHi Counter32
    }

sapEgrQosArbitStatsName OBJECT-TYPE
    SYNTAX      TNamedItem
    MAX-ACCESS  not-accessible
    STATUS      current
    DESCRIPTION
        "The value of sapEgrQosArbitStatsName specifies the egress QoS
         arbiter of this SAP."
    ::= { sapEgrQosArbitStatsEntry 1 }

sapEgrQosArbitStatsFwdPkts OBJECT-TYPE
    SYNTAX      Counter64
    MAX-ACCESS  read-only
    STATUS      current
    DESCRIPTION
        "The value of sapEgrQosArbitStatsFwdPkts indicates the number of
         forwarded packets, as determined by the SAP egress policer
         control policy, offered by the Pchip to the Qchip."
    ::= { sapEgrQosArbitStatsEntry 2 }

sapEgrQosArbitStatsFwdPktsLo OBJECT-TYPE
    SYNTAX          Counter32
    MAX-ACCESS      read-only
    STATUS          current
    DESCRIPTION
        "The value of sapEgrQosArbitStatsFwdPktsLo indicates the lower 32
         bits of sapEgrQosArbitStatsFwdPkts."
    ::= { sapEgrQosArbitStatsEntry 3 }

sapEgrQosArbitStatsFwdPktsHi OBJECT-TYPE
    SYNTAX          Counter32
    MAX-ACCESS      read-only
    STATUS          current
    DESCRIPTION
        "The value of sapEgrQosArbitStatsFwdPktsHi indicates the upper 32
         bits of sapEgrQosArbitStatsFwdPkts."
    ::= { sapEgrQosArbitStatsEntry 4 }

sapEgrQosArbitStatsFwdOcts OBJECT-TYPE
    SYNTAX      Counter64
    MAX-ACCESS  read-only
    STATUS      current
    DESCRIPTION
        "The value of sapEgrQosArbitStatsFwdOcts indicates the number of
         forwarded octets, as determined by the SAP egress policer
         control policy, offered by the Pchip to the Qchip."
    ::= { sapEgrQosArbitStatsEntry 5 }

sapEgrQosArbitStatsFwdOctsLo OBJECT-TYPE
    SYNTAX          Counter32
    MAX-ACCESS      read-only
    STATUS          current
    DESCRIPTION
        "The value of sapEgrQosArbitStatsFwdOctsLo indicates the lower 32 bits
         of sapEgrQosArbitStatsFwdOcts."
    ::= { sapEgrQosArbitStatsEntry 6 }

sapEgrQosArbitStatsFwdOctsHi OBJECT-TYPE
    SYNTAX          Counter32
    MAX-ACCESS      read-only
    STATUS          current
    DESCRIPTION
        "The value of sapEgrQosArbitStatsFwdOctsHi indicates the upper 32 bits
         of sapEgrQosArbitStatsFwdOcts."
    ::= { sapEgrQosArbitStatsEntry 7 }

-- --------------------------------------------------------------
-- Ingress QoS Scheduler SAP Statistics Table for Link mode SAPs
-- --------------------------------------------------------------
sapPortIdIngQosArbitStatsTable OBJECT-TYPE
    SYNTAX          SEQUENCE OF SapPortIdIngQosArbitStatsEntry
    MAX-ACCESS      not-accessible
    STATUS          current
    DESCRIPTION
        "The sapPortIdIngQosArbitStatsTable contains ingress QoS
         queue SAP statistics. This table is used when the SAP
         is  a CCAG or LAG in 'link' mode, or an APS."
    ::= { tmnxSapObjs 111 }

sapPortIdIngQosArbitStatsEntry OBJECT-TYPE
    SYNTAX          SapPortIdIngQosArbitStatsEntry
    MAX-ACCESS      not-accessible
    STATUS          current
    DESCRIPTION     
        "Each entry represents the ingress statistics about a
         specific SAP's QoS queue. Entries are created when
         a arbiter policy is applied to a SAP."
    INDEX           { svcId, sapPortId, sapEncapValue,
                      sapPortIdIngQosArbitName, sapPortIdIngPortId }
    ::= { sapPortIdIngQosArbitStatsTable 1 }

SapPortIdIngQosArbitStatsEntry ::=
    SEQUENCE {
        sapPortIdIngQosArbitName      TNamedItem,
        sapPortIdIngQosArbitFwdPkts   Counter64,
        sapPortIdIngQosArbitFwdOcts   Counter64,
        sapPortIdIngQosArbitFwdPktsLo Counter32,
        sapPortIdIngQosArbitFwdPktsHi Counter32,
        sapPortIdIngQosArbitFwdOctsLo Counter32,
        sapPortIdIngQosArbitFwdOctsHi Counter32
    }

sapPortIdIngQosArbitName OBJECT-TYPE
    SYNTAX          TNamedItem
    MAX-ACCESS      not-accessible
    STATUS          current
    DESCRIPTION     "The value of sapPortIdIngQosArbitName is used as an
                     index of the ingress QoS arbiter of this SAP."
    ::= { sapPortIdIngQosArbitStatsEntry 1 }

sapPortIdIngQosArbitFwdPkts OBJECT-TYPE
    SYNTAX          Counter64
    MAX-ACCESS      read-only
    STATUS          current
    DESCRIPTION     "The value of sapPortIdIngQosArbitFwdPkts indicates
                     the number of forwarded packets, as determined by the SAP
                     ingress arbiter policy, offered by the Pchip to the
                     Qchip."
    ::= { sapPortIdIngQosArbitStatsEntry 2 }

sapPortIdIngQosArbitFwdOcts OBJECT-TYPE
    SYNTAX          Counter64
    MAX-ACCESS      read-only
    STATUS          current
    DESCRIPTION     "The value of sapPortIdIngQosArbitFwdOcts indicates
                     the number of forwarded octets,as determined by the SAP
                     ingress arbiter policy, offered by the Pchip to the
                     Qchip."
    ::= { sapPortIdIngQosArbitStatsEntry 3 }

sapPortIdIngQosArbitFwdPktsLo OBJECT-TYPE
    SYNTAX          Counter32
    MAX-ACCESS      read-only
    STATUS          current
    DESCRIPTION     
        "The value of sapPortIdIngQosArbitFwdPktsLo indicates the lower 32
         bits of sapPortIdIngQosArbitFwdPkts."
    ::= { sapPortIdIngQosArbitStatsEntry 4 }

sapPortIdIngQosArbitFwdPktsHi OBJECT-TYPE
    SYNTAX          Counter32
    MAX-ACCESS      read-only
    STATUS          current
    DESCRIPTION
        "The value of sapPortIdIngQosArbitFwdPktsHi indicates the upper 32
         bits of sapPortIdIngQosArbitFwdPkts."
    ::= { sapPortIdIngQosArbitStatsEntry 5 }

sapPortIdIngQosArbitFwdOctsLo OBJECT-TYPE
    SYNTAX          Counter32
    MAX-ACCESS      read-only
    STATUS          current
    DESCRIPTION
        "The value of sapPortIdIngQosArbitFwdOctsLo indicates the lower 32 bits
         of sapPortIdIngQosArbitFwdOcts."
    ::= { sapPortIdIngQosArbitStatsEntry 6 }

sapPortIdIngQosArbitFwdOctsHi OBJECT-TYPE
    SYNTAX          Counter32
    MAX-ACCESS      read-only
    STATUS          current
    DESCRIPTION
        "The value of sapPortIdIngQosArbitFwdOctsHi indicates the upper 32 bits
         of sapPortIdIngQosArbitFwdOcts."
    ::= { sapPortIdIngQosArbitStatsEntry 7 }

-- --------------------------------------------------------------
-- Egress QoS Scheduler SAP Statistics Table for Link mode SAPs
-- --------------------------------------------------------------
sapPortIdEgrQosArbitStatsTable OBJECT-TYPE
    SYNTAX          SEQUENCE OF SapPortIdEgrQosArbitStatsEntry
    MAX-ACCESS      not-accessible
    STATUS          current
    DESCRIPTION
        "The sapPortIdEgrQosArbitStatsTable contains egress QoS
         queue SAP statistics. This table is used when the SAP
         is  a CCAG or LAG in 'link' mode, or an APS."
    ::= { tmnxSapObjs 112 }

sapPortIdEgrQosArbitStatsEntry OBJECT-TYPE
    SYNTAX          SapPortIdEgrQosArbitStatsEntry
    MAX-ACCESS      not-accessible
    STATUS          current
    DESCRIPTION     
        "Each entry represents the egress statistics about a
         specific SAP's QoS queue. Entries are created when
         a arbiter policy is applied to a SAP."
    INDEX           { svcId, sapPortId, sapEncapValue,
                      sapPortIdEgrQosArbitName, sapPortIdEgrPortId }
    ::= { sapPortIdEgrQosArbitStatsTable 1 }

SapPortIdEgrQosArbitStatsEntry ::=
    SEQUENCE {
        sapPortIdEgrQosArbitName      TNamedItem,
        sapPortIdEgrQosArbitFwdPkts   Counter64,
        sapPortIdEgrQosArbitFwdOcts   Counter64,
        sapPortIdEgrQosArbitFwdPktsLo Counter32,
        sapPortIdEgrQosArbitFwdPktsHi Counter32,
        sapPortIdEgrQosArbitFwdOctsLo Counter32,
        sapPortIdEgrQosArbitFwdOctsHi Counter32
    }

sapPortIdEgrQosArbitName OBJECT-TYPE
    SYNTAX          TNamedItem
    MAX-ACCESS      not-accessible
    STATUS          current
    DESCRIPTION     "The value of sapPortIdEgrQosArbitName is used as an
                     index of the egress QoS arbiter of this SAP."
    ::= { sapPortIdEgrQosArbitStatsEntry 1 }

sapPortIdEgrQosArbitFwdPkts OBJECT-TYPE
    SYNTAX          Counter64
    MAX-ACCESS      read-only
    STATUS          current
    DESCRIPTION     "The value of sapPortIdEgrQosArbitFwdPkts indicates
                     the number of forwarded packets, as determined by the SAP
                     egress arbiter policy, offered by the Pchip to the
                     Qchip."
    ::= { sapPortIdEgrQosArbitStatsEntry 2 }

sapPortIdEgrQosArbitFwdOcts OBJECT-TYPE
    SYNTAX          Counter64
    MAX-ACCESS      read-only
    STATUS          current
    DESCRIPTION     "The value of sapPortIdEgrQosArbitFwdOcts indicates
                     the number of forwarded octets,as determined by the SAP
                     egress arbiter policy, offered by the Pchip to the
                     Qchip."
    ::= { sapPortIdEgrQosArbitStatsEntry 3 }

sapPortIdEgrQosArbitFwdPktsLo OBJECT-TYPE
    SYNTAX          Counter32
    MAX-ACCESS      read-only
    STATUS          current
    DESCRIPTION     
        "The value of sapPortIdEgrQosArbitFwdPktsLo indicates the lower 32
         bits of sapPortIdEgrQosArbitFwdPkts."
    ::= { sapPortIdEgrQosArbitStatsEntry 4 }

sapPortIdEgrQosArbitFwdPktsHi OBJECT-TYPE
    SYNTAX          Counter32
    MAX-ACCESS      read-only
    STATUS          current
    DESCRIPTION
        "The value of sapPortIdEgrQosArbitFwdPktsHi indicates the upper 32
         bits of sapPortIdEgrQosArbitFwdPkts."
    ::= { sapPortIdEgrQosArbitStatsEntry 5 }

sapPortIdEgrQosArbitFwdOctsLo OBJECT-TYPE
    SYNTAX          Counter32
    MAX-ACCESS      read-only
    STATUS          current
    DESCRIPTION
        "The value of sapPortIdEgrQosArbitFwdOctsLo indicates the lower 32 bits
         of sapPortIdEgrQosArbitFwdOcts."
    ::= { sapPortIdEgrQosArbitStatsEntry 6 }

sapPortIdEgrQosArbitFwdOctsHi OBJECT-TYPE
    SYNTAX          Counter32
    MAX-ACCESS      read-only
    STATUS          current
    DESCRIPTION
        "The value of sapPortIdEgrQosArbitFwdOctsHi indicates the upper 32 bits
         of sapPortIdEgrQosArbitFwdOcts."
    ::= { sapPortIdEgrQosArbitStatsEntry 7 }


-- sap shortest path bridging (SPB) table

sapTlsSpbTblLastChanged  OBJECT-TYPE
    SYNTAX          TimeStamp
    MAX-ACCESS      read-only
    STATUS          current
    DESCRIPTION
        "The value of sapTlsSpbTblLastChanged indicates the sysUpTime
         at the time of the last modification of sapTlsSpbTable.

         If no changes were made to the entry since the last re-initialization
         of the local network management subsystem, then this object contains a
         zero value."
    ::= { tmnxSapObjs 139 }

sapTlsSpbTable OBJECT-TYPE
    SYNTAX          SEQUENCE OF SapTlsSpbEntry
    MAX-ACCESS      not-accessible
    STATUS          current
    DESCRIPTION
        "A table that contains TLS SAP specific Shortest Path Bridging
        (SPB) information."
    ::= { tmnxSapObjs 140 }

sapTlsSpbEntry OBJECT-TYPE
    SYNTAX          SapTlsSpbEntry
    MAX-ACCESS      not-accessible
    STATUS          current
    DESCRIPTION
        "A row-entry that contains TLS SAP specific SPB information."
    INDEX           { svcId, sapPortId, sapEncapValue }
    ::= { sapTlsSpbTable 1 }

SapTlsSpbEntry ::=
    SEQUENCE {
        sapTlsSpbRowStatus         RowStatus,
        sapTlsSpbLastChgd          TimeStamp,
        sapTlsSpbIfIndex           InterfaceIndexOrZero,
        sapTlsSpbAdminState        TmnxAdminState
    }

sapTlsSpbRowStatus OBJECT-TYPE
    SYNTAX          RowStatus
    MAX-ACCESS      read-create
    STATUS          current
    DESCRIPTION
        "This value of the object sapTlsSpbRowStatus specifies the
         status of this row."
    ::= { sapTlsSpbEntry 1 }

sapTlsSpbLastChgd OBJECT-TYPE
    SYNTAX       TimeStamp
    MAX-ACCESS   read-only
    STATUS       current
    DESCRIPTION  
        "The value of sapTlsSpbLastChgd indicates the timestamp of last
        change to this row in sapTlsSpbTable."
    ::= { sapTlsSpbEntry 2 }  

sapTlsSpbIfIndex OBJECT-TYPE
    SYNTAX       InterfaceIndexOrZero
    MAX-ACCESS   read-only
    STATUS       current
    DESCRIPTION  
        "The value of sapTlsSpbIfIndex indicates the interface index assigned
         to this SAP for Shortest Path Bridging."
    ::= { sapTlsSpbEntry 3 }  
     
sapTlsSpbAdminState OBJECT-TYPE
    SYNTAX      TmnxAdminState
    MAX-ACCESS  read-create
    STATUS      current
    DESCRIPTION
        "The sapTlsSpbAdminState indicates the  desired administrative state
         for Shortest Path Bridging on this sap."
    DEFVAL { outOfService }
    ::= { sapTlsSpbEntry 4 }

-- --------------------------------------
-- SAP Notification Objects
-- --------------------------------------
-- tmnxSapNotifyObjs       OBJECT IDENTIFIER ::= ( tmnxSapObjs 100 }

sapNotifyPortId OBJECT-TYPE
    SYNTAX          TmnxPortID
    MAX-ACCESS      accessible-for-notify
    STATUS          current
    DESCRIPTION     "The ID of the access port where a SAP is defined."
    ::= { tmnxSapNotifyObjs 1 }

msapStatus OBJECT-TYPE
    SYNTAX          ConfigStatus
    MAX-ACCESS      accessible-for-notify
    STATUS          current
    DESCRIPTION     "The status of the Managed SAP which is used 
                     by the msapStateChanged notification to indicate 
                     what state the Managed SAP has entered: 'created',
                     'modified', or 'deleted'."
    ::= { tmnxSapNotifyObjs 2 }

svcManagedSapCreationError OBJECT-TYPE
   SYNTAX         DisplayString
   MAX-ACCESS     accessible-for-notify
   STATUS         current
   DESCRIPTION    "The value of the object svcManagedSapCreationError
                   indicates the reason why the system was unable to create
                   the managed SAP."
   ::= { tmnxSapNotifyObjs 3 }

sapTlsNotifyMacAddr OBJECT-TYPE
    SYNTAX         MacAddress
    MAX-ACCESS     accessible-for-notify
    STATUS         current
    DESCRIPTION    "The value of the object sapTlsNotifyMacAddr
                    indicates the MAC address associated with
                    a VPLS SAP."
    ::= { tmnxSapNotifyObjs 4 }

sapBGPPeeringHostIpAddrType OBJECT-TYPE
    SYNTAX          InetAddressType
    MAX-ACCESS      accessible-for-notify
    STATUS          current
    DESCRIPTION     "The value of sapBGPPeeringHostIpAddrType indicates the
                     address type of sapBGPPeeringHostIpAddr."
    ::= { tmnxSapNotifyObjs 5 }

sapBGPPeeringHostIpAddr OBJECT-TYPE
    SYNTAX          InetAddress (SIZE(0|4|16))
    MAX-ACCESS      accessible-for-notify
    STATUS          current
    DESCRIPTION     "The value of sapBGPPeeringHostIpAddr indicates the IP
                     address of the host."
    ::= { tmnxSapNotifyObjs 6 }

sapBGPPeeringNotifDescription OBJECT-TYPE
    SYNTAX      DisplayString
    MAX-ACCESS  accessible-for-notify
    STATUS      current
    DESCRIPTION
        "The object sapBGPPeeringNotifDescription is a printable character 
        string."
    ::= { tmnxSapNotifyObjs 7 }
    
sapBGPPeeringAttrDiscarded OBJECT-TYPE
    SYNTAX      TruthValue
    MAX-ACCESS  accessible-for-notify
    STATUS      current
    DESCRIPTION
        "The value of the object sapBGPPeeringAttrDiscarded is equal to 'true'
         if the BGP Peering attributes have been discarded."
    ::= { tmnxSapNotifyObjs 8 }    
    
sapBGPPeeringVRtrID  OBJECT-TYPE
    SYNTAX      TmnxVRtrID
    MAX-ACCESS  accessible-for-notify
    STATUS      current
    DESCRIPTION
        "The  unique value that identifies a virtual router."
    ::= { tmnxSapNotifyObjs 9 }  

sapTunnelNotifyName  OBJECT-TYPE
    SYNTAX      TNamedItem
    MAX-ACCESS  accessible-for-notify
    STATUS      current
    DESCRIPTION
        "The value of sapTunnelNotifyName specifies the name of the IPsec
        or GRE tunnel." 
    ::= { tmnxSapNotifyObjs 10 }

sapTunnelNotifyReason  OBJECT-TYPE
    SYNTAX      DisplayString
    MAX-ACCESS  accessible-for-notify
    STATUS      current
    DESCRIPTION
        "The value of sapTunnelNotifyReason indicates the reason for the 
        tunnel notification."
    ::= { tmnxSapNotifyObjs 11 }

sapTunnelNotifyState  OBJECT-TYPE
    SYNTAX      ServiceOperStatus
    MAX-ACCESS  accessible-for-notify
    STATUS      current
    DESCRIPTION
        "The value of sapTunnelNotifyState indicates the operational state
        of the tunnel in the notification."
    ::= { tmnxSapNotifyObjs 12 }

sapNotifyReason  OBJECT-TYPE
    SYNTAX      DisplayString
    MAX-ACCESS  accessible-for-notify
    STATUS      current
    DESCRIPTION
        "The value of sapNotifyReason indicates the reason for the 
        SAP notification."
    ::= { tmnxSapNotifyObjs 13 }

 sapNotifyName  OBJECT-TYPE
     SYNTAX      TNamedItem
     MAX-ACCESS  accessible-for-notify
     STATUS      current
     DESCRIPTION
         "The value of sapNotifyName specifies a name." 
     ::= { tmnxSapNotifyObjs 14 }

 sapPppNcpFailureProtocol OBJECT-TYPE
     SYNTAX      INTEGER {
                     ipcp  (1),
                     ipv6cp (2)
                 }
     MAX-ACCESS  accessible-for-notify
     STATUS      current
     DESCRIPTION
         "The value of sapPppNcpFailureProtocol indicates the
          failing NCP protocol."
    ::= { tmnxSapNotifyObjs 15 }

sapIpipeCeIpAddrType OBJECT-TYPE
     SYNTAX      InetAddressType 
     MAX-ACCESS  accessible-for-notify
     STATUS      current
     DESCRIPTION
         "The value of sapIpipeCeIpAddrType indicates the
          type of CE IP address on an IPIPE SAP. The CE IP address
          is specified by sapIpipeCeIpAddress."
    ::= { tmnxSapNotifyObjs 16 }

sapIpipeCeIpAddress OBJECT-TYPE
     SYNTAX      InetAddress (SIZE(0|4|16))
     MAX-ACCESS  accessible-for-notify
     STATUS      current
     DESCRIPTION     
         "The value of sapIpipeCeIpAddress indicates the CE IP
          address of type sapIpipeCeIpAddrType on an IPIPE SAP."
    ::= { tmnxSapNotifyObjs 17 }

 sapNotifyEncapValue OBJECT-TYPE
     SYNTAX      TmnxEncapVal
     MAX-ACCESS  accessible-for-notify
     STATUS      current
     DESCRIPTION
        "The value of the label used to identify this
         SAP on the access port specified by sapNotifyPortId."
     ::= { tmnxSapNotifyObjs 18 }


sapTunnelNotifyConfigIpMtu OBJECT-TYPE
    SYNTAX         Unsigned32
    MAX-ACCESS     accessible-for-notify
    STATUS         current
    DESCRIPTION
        "The value of the object sapTunnelNotifyConfigIpMtu indicates the
         IP tunnel's configured IP MTU for packets entering the tunnel
         from the non-encapsulated side."
    ::= { tmnxSapNotifyObjs 19 }
 
sapTunnelNotifyEncapOverhead OBJECT-TYPE
    SYNTAX         Unsigned32
    MAX-ACCESS     accessible-for-notify
    STATUS         current
    DESCRIPTION
        "The value of the object sapTunnelNotifyEncapOverhead indicates the
         IP Tunnel's encapsulation overhead."
    ::= { tmnxSapNotifyObjs 20 }

sapTunnelNotifyConfigEncapIpMtu OBJECT-TYPE
    SYNTAX         Unsigned32
    MAX-ACCESS     accessible-for-notify
    STATUS         current
    DESCRIPTION
        "The value of the object sapTunnelNotifyConfigEncapIpMtu indicates
         the IP Tunnel's configured encapsulated IP MTU."
    ::= { tmnxSapNotifyObjs 21 }

sapRipListenerHostIpAddrType OBJECT-TYPE
    SYNTAX          InetAddressType
    MAX-ACCESS      accessible-for-notify
    STATUS          current
    DESCRIPTION     "The value of sapRipListenerHostIpAddrType indicates the
                     address type of sapRipListenerHostIpAddr."
    ::= { tmnxSapNotifyObjs 22 }

sapRipListenerHostIpAddr OBJECT-TYPE
    SYNTAX          InetAddress (SIZE(0|4))
    MAX-ACCESS      accessible-for-notify
    STATUS          current
    DESCRIPTION     "The value of sapRipListenerHostIpAddr indicates the IP
                     address of the host."
    ::= { tmnxSapNotifyObjs 23 }

sapRipListenerVRtrID  OBJECT-TYPE
    SYNTAX      TmnxVRtrID
    MAX-ACCESS  accessible-for-notify
    STATUS      current
    DESCRIPTION
        "The object sapRipListenerVRtrID uniquely identifies a virtual router."
    ::= { tmnxSapNotifyObjs 24 }  

sapRipListenerNotifDescription OBJECT-TYPE
    SYNTAX      DisplayString
    MAX-ACCESS  accessible-for-notify
    STATUS      current
    DESCRIPTION
        "The object sapRipListenerNotifDescription is a printable character 
        string."
    ::= { tmnxSapNotifyObjs 25 }
         
-- -------------------------------------
-- TLS SAP MVRP Table
-- -------------------------------------
sapTlsMvrpTable OBJECT-TYPE
    SYNTAX          SEQUENCE OF SapTlsMvrpEntry
    MAX-ACCESS      not-accessible
    STATUS          current
    DESCRIPTION     "This table contains an entry for each VLAN managed
                    by Multiple VLAN Registration Protocol (MVRP) on the SAP
                    for the TLS.  Entries are dynamically created and
                    destroyed by the system as the VLANs are registered
                    or declared in MVRP."
    ::= { tmnxSapObjs 110 }

sapTlsMvrpEntry OBJECT-TYPE
    SYNTAX          SapTlsMvrpEntry
    MAX-ACCESS      not-accessible
    STATUS          current
    DESCRIPTION     "MVRP specific information about a VLANs managed by
                    MVRP on a SAP in a TLS."
    INDEX           { svcId, sapPortId, sapEncapValue, sapTlsMvrpVlanId }
    ::= { sapTlsMvrpTable 1 }

SapTlsMvrpEntry ::=
    SEQUENCE {
        sapTlsMvrpVlanId               Unsigned32,
        sapTlsMvrpDeclared             TruthValue,
        sapTlsMvrpRegistered           TruthValue,
        sapTlsMvrpEndStation           TruthValue
    }

sapTlsMvrpVlanId OBJECT-TYPE
    SYNTAX        Unsigned32 (1..4095)
    MAX-ACCESS    not-accessible
    STATUS        current
    DESCRIPTION
        "The value of sapTlsMvrpVlanId indicates a VLAN which
        is being managed by MVRP on this SAP."
    ::= { sapTlsMvrpEntry 1 }

sapTlsMvrpDeclared OBJECT-TYPE
    SYNTAX        TruthValue
    MAX-ACCESS    read-only
    STATUS        current
    DESCRIPTION
        "The value of sapTlsMvrpDeclared indicates whether the MVRP applicant
        on this SAP is declaring this VLAN on behalf of MVRP."
    ::= { sapTlsMvrpEntry 2 }

sapTlsMvrpRegistered OBJECT-TYPE
    SYNTAX        TruthValue
    MAX-ACCESS    read-only
    STATUS        current
    DESCRIPTION
        "The value of sapTlsMvrpRegistered indicates whether the MVRP registrant
        on this SAP has notified MVRP of a registration of this VLAN."
    ::= { sapTlsMvrpEntry 3 }

sapTlsMvrpEndStation OBJECT-TYPE
    SYNTAX        TruthValue
    MAX-ACCESS    read-only
    STATUS        current
    DESCRIPTION
        "The value of sapTlsMvrpEndStation indicates whether the MVRP registrant
        on this SAP is registered per end station."
    ::= { sapTlsMvrpEntry 4 }

--
-- GRE Tunnel Table
--
tmnxGreTunnelTableLastChanged OBJECT-TYPE
    SYNTAX      TimeStamp
    MAX-ACCESS  read-only
    STATUS      obsolete
    DESCRIPTION
        "The value of tmnxGreTunnelTableLastChanged indicates the
         sysUpTime at the time of the last modification to 
         tmnxGreTunnelTable by adding, deleting an entry or change
         to a writable object in the table.

         If no changes were made to the table since the last 
         re-initialization of the local network management subsystem, 
         then this object contains a zero value."
    ::= { tmnxSapObjs 113 }

tmnxGreTunnelTable OBJECT-TYPE
    SYNTAX      SEQUENCE OF TmnxGreTunnelEntry
    MAX-ACCESS  not-accessible
    STATUS      obsolete
    DESCRIPTION
        "Table to store the GRE Tunnel entries."
    ::= { tmnxSapObjs 114 }

tmnxGreTunnelEntry OBJECT-TYPE
    SYNTAX      TmnxGreTunnelEntry
    MAX-ACCESS  not-accessible
    STATUS      obsolete
    DESCRIPTION
        "Information about a single GRE Tunnel entry."
    INDEX { svcId, 
            sapPortId, 
            sapEncapValue, 
            tmnxGreTunnelName 
          }
    ::= { tmnxGreTunnelTable 1 }

TmnxGreTunnelEntry ::= SEQUENCE {
    tmnxGreTunnelName                 TNamedItem, 
    tmnxGreTunnelRowStatus            RowStatus, 
    tmnxGreTunnelLastChanged          TimeStamp,
    tmnxGreTunnelDstIpAddrType        InetAddressType, 
    tmnxGreTunnelDstIpAddr            InetAddress,
    tmnxGreTunnelDescription          TItemDescription,
    tmnxGreTunnelLclIpAddrType        InetAddressType, 
    tmnxGreTunnelLclIpAddr            InetAddress,
    tmnxGreTunnelRemIpAddrType        InetAddressType, 
    tmnxGreTunnelRemIpAddr            InetAddress,
    tmnxGreTunnelBackupRemIpAddrType  InetAddressType, 
    tmnxGreTunnelBackupRemIpAddr      InetAddress,
    tmnxGreTunnelOperRemIpAddrType    InetAddressType, 
    tmnxGreTunnelOperRemIpAddr        InetAddress,
    tmnxGreTunnelDeliverySvcId        TmnxServId,
    tmnxGreTunnelAdminState           TmnxAdminState,
    tmnxGreTunnelOperState            TmnxOperState,
    tmnxGreTunnelOperFlags            BITS,
    tmnxGreTunnelDscp                 TDSCPNameOrEmpty,
    tmnxGreTunnelReassembly           Integer32,
    tmnxGreTunnelClearDfBit           TruthValue,
    tmnxGreTunnelIpMtu                Unsigned32,
    tmnxGreTunnelHostISA              TmnxHwIndexOrZero            
}

tmnxGreTunnelName  OBJECT-TYPE
    SYNTAX      TNamedItem
    MAX-ACCESS  not-accessible
    STATUS      obsolete
    DESCRIPTION
        "The value of tmnxGreTunnelName specifies the name of the tunnel 
         and is part of the index for the table tmnxGreTunnelTable."
    ::= { tmnxGreTunnelEntry 1 }

tmnxGreTunnelRowStatus OBJECT-TYPE
    SYNTAX      RowStatus
    MAX-ACCESS  read-create
    STATUS      obsolete
    DESCRIPTION
        "The tmnxGreTunnelRowStatus object is used to create and delete 
         rows in the tmnxGreTunnelTable."
    ::= { tmnxGreTunnelEntry 2 }

tmnxGreTunnelLastChanged  OBJECT-TYPE
    SYNTAX      TimeStamp
    MAX-ACCESS  read-only
    STATUS      obsolete
    DESCRIPTION
        "The value of tmnxGreTunnelLastChanged indicates the sysUpTime
         at the time of the last modification of this entry."
    ::= { tmnxGreTunnelEntry 3 }

tmnxGreTunnelDstIpAddrType  OBJECT-TYPE
    SYNTAX      InetAddressType
    MAX-ACCESS  read-create
    STATUS      obsolete
    DESCRIPTION
        "The value of tmnxGreTunnelDstIpAddrType specifies the address 
         type of address in tmnxGreTunnelDstIpAddr.
         
         This object must be set at the time of creation of an entry." 
    ::= { tmnxGreTunnelEntry 4 }

tmnxGreTunnelDstIpAddr  OBJECT-TYPE
    SYNTAX      InetAddress (SIZE (0|4|16|20))
    MAX-ACCESS  read-create
    STATUS      obsolete
    DESCRIPTION
        "The value of tmnxGreTunnelDstIpAddr specifies the address of the 
         destination of this GRE tunnel.

         This object must be set at the time of creation of an entry." 
    ::= { tmnxGreTunnelEntry 5 }

tmnxGreTunnelDescription  OBJECT-TYPE
    SYNTAX      TItemDescription
    MAX-ACCESS  read-create
    STATUS      obsolete
    DESCRIPTION
        "The value of tmnxGreTunnelDescription specifies the 
         user-provided description for each tmnxGreTunnelEntry in the 
         table tmnxGreTunnelTable."
    DEFVAL { "" }
    ::= { tmnxGreTunnelEntry 6 }

tmnxGreTunnelLclIpAddrType  OBJECT-TYPE
    SYNTAX      InetAddressType
    MAX-ACCESS  read-create
    STATUS      obsolete
    DESCRIPTION
        "The value of tmnxGreTunnelLclIpAddrType specifies the address 
         type of address in tmnxGreTunnelLclIpAddr." 
    DEFVAL { unknown }
    ::= { tmnxGreTunnelEntry 7 }

tmnxGreTunnelLclIpAddr  OBJECT-TYPE
    SYNTAX      InetAddress (SIZE (0|4|16|20))
    MAX-ACCESS  read-create
    STATUS      obsolete
    DESCRIPTION
        "The value of tmnxGreTunnelLclIpAddr specifies the address of the 
         local end-point of this GRE tunnel."
    DEFVAL { ''H }
    ::= { tmnxGreTunnelEntry 8 }

tmnxGreTunnelRemIpAddrType  OBJECT-TYPE
    SYNTAX      InetAddressType
    MAX-ACCESS  read-create
    STATUS      obsolete
    DESCRIPTION
        "The value of tmnxGreTunnelRemIpAddrType specifies the address
         type of address in tmnxGreTunnelRemIpAddr."
    DEFVAL { unknown }
    ::= { tmnxGreTunnelEntry 9 }

tmnxGreTunnelRemIpAddr  OBJECT-TYPE
    SYNTAX      InetAddress (SIZE (0|4|16|20))
    MAX-ACCESS  read-create
    STATUS      obsolete
    DESCRIPTION
        "The value of tmnxGreTunnelRemIpAddr specifies the address of the 
         remote end-point of this GRE tunnel."
    DEFVAL { ''H }
    ::= { tmnxGreTunnelEntry 10 }

tmnxGreTunnelBackupRemIpAddrType  OBJECT-TYPE
    SYNTAX      InetAddressType
    MAX-ACCESS  read-create
    STATUS      obsolete
    DESCRIPTION
        "The value of tmnxGreTunnelBackupRemIpAddrType specifies the address
         type of address in tmnxGreTunnelBackupRemIpAddr."
    DEFVAL { unknown }
    ::= { tmnxGreTunnelEntry 11 }

tmnxGreTunnelBackupRemIpAddr  OBJECT-TYPE
    SYNTAX      InetAddress (SIZE (0|4|16|20))
    MAX-ACCESS  read-create
    STATUS      obsolete
    DESCRIPTION
        "The value of tmnxGreTunnelBackupRemIpAddr specifies the address of the 
         backup remote end-point of this GRE tunnel."
    DEFVAL { ''H }
    ::= { tmnxGreTunnelEntry 12 }

tmnxGreTunnelOperRemIpAddrType  OBJECT-TYPE
    SYNTAX      InetAddressType
    MAX-ACCESS  read-only
    STATUS      obsolete
    DESCRIPTION
        "The value of tmnxGreTunnelOperRemIpAddrType indicates the address
         type of address in tmnxGreTunnelOperRemIpAddr."
    ::= { tmnxGreTunnelEntry 13 }

tmnxGreTunnelOperRemIpAddr  OBJECT-TYPE
    SYNTAX      InetAddress (SIZE (0|4|16|20))
    MAX-ACCESS  read-only
    STATUS      obsolete
    DESCRIPTION
        "The value of tmnxGreTunnelOperRemIpAddr indicates the address of the 
         operational remote end-point of this GRE tunnel."
    ::= { tmnxGreTunnelEntry 14 }

tmnxGreTunnelDeliverySvcId  OBJECT-TYPE
    SYNTAX      TmnxServId
    MAX-ACCESS  read-create
    STATUS      obsolete
    DESCRIPTION
        "The value of tmnxGreTunnelDeliverySvcId specifies the service-id 
         of the tunnel delivery service."
    DEFVAL { 0 }
    ::= { tmnxGreTunnelEntry 15 }

tmnxGreTunnelAdminState  OBJECT-TYPE
    SYNTAX      TmnxAdminState 
    MAX-ACCESS  read-create
    STATUS      obsolete
    DESCRIPTION
        "The value of tmnxGreTunnelAdminState specifies the administrative
         state of the tmnxGreTunnelEntry."
    DEFVAL { outOfService }
    ::= { tmnxGreTunnelEntry 16 }

tmnxGreTunnelOperState  OBJECT-TYPE
    SYNTAX      TmnxOperState 
    MAX-ACCESS  read-only
    STATUS      obsolete
    DESCRIPTION
        "The value of tmnxGreTunnelOperState indicates the operational 
         status of tmnxGreTunnelEntry."
    ::= { tmnxGreTunnelEntry 17 }

tmnxGreTunnelOperFlags  OBJECT-TYPE
    SYNTAX      BITS {
                    unresolvedLocalIp (0),  
                    tunnelAdminDown (1),
                    sapDown (2),
                    unresolvedDeliverySvc(3),
                    reserved(4),
                    remIpUnreachable(5),
                    unresolvedDstIp(6)
                }
    MAX-ACCESS  read-only
    STATUS      obsolete
    DESCRIPTION
        "The value of tmnxGreTunnelOperFlags indicates the reason why the
         tunnel is operationally down."
    ::= { tmnxGreTunnelEntry 18 }

tmnxGreTunnelDscp  OBJECT-TYPE
    SYNTAX      TDSCPNameOrEmpty
    MAX-ACCESS  read-create
    STATUS      obsolete
    DESCRIPTION 
        "The value of tmnxGreTunnelDscp specifies DSCP value which will be
         used in the GRE tunnel carrying IP header in the delivery service."
    DEFVAL { "" }
    ::= { tmnxGreTunnelEntry 19 }

tmnxGreTunnelReassembly  OBJECT-TYPE
    SYNTAX      Integer32 (-1|0..5000)
    UNITS       "milli-seconds"
    MAX-ACCESS  read-create
    STATUS      obsolete
    DESCRIPTION 
        "The value of tmnxGreTunnelReassembly specifies the maximum number
         of seconds to wait to receive all fragments of a particular IPSec
         or GRE packet for reassembly.

         The tmnxGreTunnelReassembly value set to zero indicates that
         reassembly is disabled.
         
         The tmnxGreTunnelReassembly value set default indicates that this
         value will be derived from the value of
         TIMETRA-CHASSIS-MIB::tmnxIPsecIsaGrpTunnelReassembly object.

         An 'inconsistentValue' error is retuned if the value is not a multiple
         of 100 milli-seconds."
    DEFVAL { -1 }
    ::= { tmnxGreTunnelEntry 20 }

tmnxGreTunnelClearDfBit  OBJECT-TYPE
    SYNTAX      TruthValue
    MAX-ACCESS  read-create
    STATUS      obsolete
    DESCRIPTION 
        "The value of tmnxGreTunnelClearDfBit specifies whether to clear
         Do not Fragment (DF) bit in the outgoing packets in this GRE tunnel."
    DEFVAL { false }
    ::= { tmnxGreTunnelEntry 21 }

tmnxGreTunnelIpMtu  OBJECT-TYPE
    SYNTAX      Unsigned32 (0|512..9000)
    MAX-ACCESS  read-create
    STATUS      obsolete
    DESCRIPTION 
        "The value of tmnxGreTunnelIpMtu specifies the MTU size for IP packets
         for this GRE tunnel.

         A value set to zero indicates maximum supported MTU size on the SAP
         for this GRE tunnel."
    DEFVAL { 0 }
    ::= { tmnxGreTunnelEntry 22 }

tmnxGreTunnelHostISA  OBJECT-TYPE
    SYNTAX      TmnxHwIndexOrZero
    MAX-ACCESS  read-only
    STATUS      obsolete
    DESCRIPTION
        "The value of tmnxGreTunnelHostISA indicates the active ISA
         that is being used to host this GRE tunnel.

         This object will have a value of zero when this tunnel is operationally
         down."
    ::= { tmnxGreTunnelEntry 23 }

--
-- GRE Tunnel Statistics Table
--

tmnxGreTunnelStatsTable OBJECT-TYPE
    SYNTAX      SEQUENCE OF TmnxGreTunnelStatsEntry
    MAX-ACCESS  not-accessible
    STATUS      obsolete
    DESCRIPTION
        "Table to store GRE Tunnel statistics"
    ::= { tmnxSapObjs 115 }

tmnxGreTunnelStatsEntry       OBJECT-TYPE
    SYNTAX      TmnxGreTunnelStatsEntry
    MAX-ACCESS  not-accessible
    STATUS      obsolete
    DESCRIPTION
        "Statistics for a single GRE Tunnel."
    INDEX { svcId, 
            sapPortId, 
            sapEncapValue, 
            tmnxGreTunnelName 
          }
    ::= { tmnxGreTunnelStatsTable 1 }

TmnxGreTunnelStatsEntry ::= SEQUENCE {
    tmnxGreTunnelPktsTx               Counter64,
    tmnxGreTunnelPktsTxLo             Counter32,
    tmnxGreTunnelPktsTxHi             Counter32,
    tmnxGreTunnelPktsRx               Counter64,
    tmnxGreTunnelPktsRxLo             Counter32,
    tmnxGreTunnelPktsRxHi             Counter32,
    tmnxGreTunnelBytesTx              Counter64,
    tmnxGreTunnelBytesTxLo            Counter32,
    tmnxGreTunnelBytesTxHi            Counter32,
    tmnxGreTunnelBytesRx              Counter64,
    tmnxGreTunnelBytesRxLo            Counter32,
    tmnxGreTunnelBytesRxHi            Counter32,
    tmnxGreTunnelTxErrors             Counter32,
    tmnxGreTunnelRxErrors             Counter32,
    tmnxGreTunnelKeyIgnoredRx         Counter64,
    tmnxGreTunnelKeyIgnoredRxLo       Counter32,
    tmnxGreTunnelKeyIgnoredRxHi       Counter32,
    tmnxGreTunnelSeqIgnoredRx         Counter64,
    tmnxGreTunnelSeqIgnoredRxLo       Counter32,
    tmnxGreTunnelSeqIgnoredRxHi       Counter32,
    tmnxGreTunnelVersUnsupRx          Counter64,
    tmnxGreTunnelVersUnsupRxLo        Counter32,
    tmnxGreTunnelVersUnsupRxHi        Counter32,
    tmnxGreTunnelInvalidChksumRx      Counter64,
    tmnxGreTunnelInvalidChksumRxLo    Counter32,
    tmnxGreTunnelInvalidChksumRxHi    Counter32,
    tmnxGreTunnelLoopsRx              Counter64,
    tmnxGreTunnelLoopsRxLo            Counter32,
    tmnxGreTunnelLoopsRxHi            Counter32,
    tmnxGreTunnelTooBigTx             Counter64,
    tmnxGreTunnelTooBigTxLo           Counter32,
    tmnxGreTunnelTooBigTxHi           Counter32
}

tmnxGreTunnelPktsTx        OBJECT-TYPE
    SYNTAX      Counter64
    MAX-ACCESS  read-only
    STATUS      obsolete
    DESCRIPTION
        "The value of tmnxGreTunnelPktsTx indicates the number of
         packets this GRE Tunnel has sent."
    ::= { tmnxGreTunnelStatsEntry 1 }

tmnxGreTunnelPktsTxLo        OBJECT-TYPE
    SYNTAX      Counter32
    MAX-ACCESS  read-only
    STATUS      obsolete
    DESCRIPTION
        "The value of tmnxGreTunnelPktsTxLo indicates lower 32 bits of the
        value of tmnxGreTunnelPktsTx object."
    ::= { tmnxGreTunnelStatsEntry 2 }

tmnxGreTunnelPktsTxHi        OBJECT-TYPE
    SYNTAX      Counter32
    MAX-ACCESS  read-only
    STATUS      obsolete
    DESCRIPTION
        "The value of tmnxGreTunnelPktsTxHi indicates higher 32 bits of the
        value of tmnxGreTunnelPktsTx object."
    ::= { tmnxGreTunnelStatsEntry 3 }

tmnxGreTunnelPktsRx        OBJECT-TYPE
    SYNTAX      Counter64
    MAX-ACCESS  read-only
    STATUS      obsolete
    DESCRIPTION
        "The value of tmnxGreTunnelPktsRx indicates the number of
         packets this GRE Tunnel has received."
    ::= { tmnxGreTunnelStatsEntry 4 }

tmnxGreTunnelPktsRxLo        OBJECT-TYPE
    SYNTAX      Counter32
    MAX-ACCESS  read-only
    STATUS      obsolete
    DESCRIPTION
        "The value of tmnxGreTunnelPktsRxLo indicates lower 32 bits of the
        value of tmnxGreTunnelPktsRx object."
    ::= { tmnxGreTunnelStatsEntry 5 }

tmnxGreTunnelPktsRxHi        OBJECT-TYPE
    SYNTAX      Counter32
    MAX-ACCESS  read-only
    STATUS      obsolete
    DESCRIPTION
        "The value of tmnxGreTunnelPktsRxHi indicates higher 32 bits of the
        value of tmnxGreTunnelPktsRx object."
    ::= { tmnxGreTunnelStatsEntry 6 }

tmnxGreTunnelBytesTx        OBJECT-TYPE
    SYNTAX      Counter64
    MAX-ACCESS  read-only
    STATUS      obsolete
    DESCRIPTION
        "The value of tmnxGreTunnelBytesTx indicates the number of
         bytes this GRE Tunnel has sent."
    ::= { tmnxGreTunnelStatsEntry 7 }

tmnxGreTunnelBytesTxLo        OBJECT-TYPE
    SYNTAX      Counter32
    MAX-ACCESS  read-only
    STATUS      obsolete
    DESCRIPTION
        "The value of tmnxGreTunnelBytesTxLo indicates lower 32 bits of the
        value of tmnxGreTunnelBytesTx object."
    ::= { tmnxGreTunnelStatsEntry 8 }

tmnxGreTunnelBytesTxHi        OBJECT-TYPE
    SYNTAX      Counter32
    MAX-ACCESS  read-only
    STATUS      obsolete
    DESCRIPTION
        "The value of tmnxGreTunnelBytesTxHi indicates higher 32 bits of the
        value of tmnxGreTunnelBytesTx object."
    ::= { tmnxGreTunnelStatsEntry 9 }

tmnxGreTunnelBytesRx        OBJECT-TYPE
    SYNTAX      Counter64
    MAX-ACCESS  read-only
    STATUS      obsolete
    DESCRIPTION
        "The value of tmnxGreTunnelBytesRx indicates the number of
         bytes this GRE Tunnel has received."
    ::= { tmnxGreTunnelStatsEntry 10 }

tmnxGreTunnelBytesRxLo        OBJECT-TYPE
    SYNTAX      Counter32
    MAX-ACCESS  read-only
    STATUS      obsolete
    DESCRIPTION
        "The value of tmnxGreTunnelBytesRxLo indicates lower 32 bits of the
        value of tmnxGreTunnelBytesRx object."
    ::= { tmnxGreTunnelStatsEntry 11 }

tmnxGreTunnelBytesRxHi        OBJECT-TYPE
    SYNTAX      Counter32
    MAX-ACCESS  read-only
    STATUS      obsolete
    DESCRIPTION
        "The value of tmnxGreTunnelBytesRxHi indicates higher 32 bits of the
        value of tmnxGreTunnelBytesRx object."
    ::= { tmnxGreTunnelStatsEntry 12 }

tmnxGreTunnelTxErrors        OBJECT-TYPE
    SYNTAX      Counter32
    MAX-ACCESS  read-only
    STATUS      obsolete
    DESCRIPTION
        "The value of tmnxGreTunnelTxErrors indicates the number of
         packet transmit errors."
    ::= { tmnxGreTunnelStatsEntry 13 }

tmnxGreTunnelRxErrors        OBJECT-TYPE
    SYNTAX      Counter32
    MAX-ACCESS  read-only
    STATUS      obsolete
    DESCRIPTION
        "The value of tmnxGreTunnelRxErrors indicates the number of
         packet receive errors."
    ::= { tmnxGreTunnelStatsEntry 14 }

tmnxGreTunnelKeyIgnoredRx        OBJECT-TYPE
    SYNTAX      Counter64
    MAX-ACCESS  read-only
    STATUS      obsolete
    DESCRIPTION
        "The value of tmnxGreTunnelKeyIgnoredRx indicates the number of
         packets this GRE Tunnel received and processed ignoring key field."
    ::= { tmnxGreTunnelStatsEntry 15 }

tmnxGreTunnelKeyIgnoredRxLo        OBJECT-TYPE
    SYNTAX      Counter32
    MAX-ACCESS  read-only
    STATUS      obsolete
    DESCRIPTION
        "The value of tmnxGreTunnelKeyIgnoredRxLo indicates lower 32 bits of the
        value of tmnxGreTunnelKeyIgnoredRx object."
    ::= { tmnxGreTunnelStatsEntry 16 }

tmnxGreTunnelKeyIgnoredRxHi        OBJECT-TYPE
    SYNTAX      Counter32
    MAX-ACCESS  read-only
    STATUS      obsolete
    DESCRIPTION
        "The value of tmnxGreTunnelKeyIgnoredRxHi indicates higher 32 bits of
        the value of tmnxGreTunnelKeyIgnoredRx object."
    ::= { tmnxGreTunnelStatsEntry 17 }

tmnxGreTunnelSeqIgnoredRx        OBJECT-TYPE
    SYNTAX      Counter64
    MAX-ACCESS  read-only
    STATUS      obsolete
    DESCRIPTION
        "The value of tmnxGreTunnelSeqIgnoredRx indicates the number of
         packets this GRE Tunnel and processed ignoring sequence field."
    ::= { tmnxGreTunnelStatsEntry 18 }

tmnxGreTunnelSeqIgnoredRxLo        OBJECT-TYPE
    SYNTAX      Counter32
    MAX-ACCESS  read-only
    STATUS      obsolete
    DESCRIPTION
        "The value of tmnxGreTunnelSeqIgnoredRxLo indicates lower 32 bits of the
        value of tmnxGreTunnelSeqIgnoredRx object."
    ::= { tmnxGreTunnelStatsEntry 19 }

tmnxGreTunnelSeqIgnoredRxHi        OBJECT-TYPE
    SYNTAX      Counter32
    MAX-ACCESS  read-only
    STATUS      obsolete
    DESCRIPTION
        "The value of tmnxGreTunnelSeqIgnoredRxHi indicates higher 32 bits of
        the value of tmnxGreTunnelSeqIgnoredRx object."
    ::= { tmnxGreTunnelStatsEntry 20 }

tmnxGreTunnelVersUnsupRx        OBJECT-TYPE
    SYNTAX      Counter64
    MAX-ACCESS  read-only
    STATUS      obsolete
    DESCRIPTION
        "The value of tmnxGreTunnelVersUnsupRx indicates the number of
         packets this GRE Tunnel received with unsupported GRE version and
         were dropped."
    ::= { tmnxGreTunnelStatsEntry 21 }

tmnxGreTunnelVersUnsupRxLo        OBJECT-TYPE
    SYNTAX      Counter32
    MAX-ACCESS  read-only
    STATUS      obsolete
    DESCRIPTION
        "The value of tmnxGreTunnelVersUnsupRxLo indicates lower 32 bits of the
        value of tmnxGreTunnelVersUnsupRx object."
    ::= { tmnxGreTunnelStatsEntry 22 }

tmnxGreTunnelVersUnsupRxHi        OBJECT-TYPE
    SYNTAX      Counter32
    MAX-ACCESS  read-only
    STATUS      obsolete
    DESCRIPTION
        "The value of tmnxGreTunnelVersUnsupRxHi indicates higher 32 bits of
        the value of tmnxGreTunnelVersUnsupRx object."
    ::= { tmnxGreTunnelStatsEntry 23 }

tmnxGreTunnelInvalidChksumRx        OBJECT-TYPE
    SYNTAX      Counter64
    MAX-ACCESS  read-only
    STATUS      obsolete
    DESCRIPTION
        "The value of tmnxGreTunnelInvalidChksumRx indicates the number of
         packets this GRE Tunnel received with invalid checksum and
         were dropped."
    ::= { tmnxGreTunnelStatsEntry 24 }

tmnxGreTunnelInvalidChksumRxLo        OBJECT-TYPE
    SYNTAX      Counter32
    MAX-ACCESS  read-only
    STATUS      obsolete
    DESCRIPTION
        "The value of tmnxGreTunnelInvalidChksumRxLo indicates lower 32 bits
        of the value of tmnxGreTunnelInvalidChksumRx object."
    ::= { tmnxGreTunnelStatsEntry 25 }

tmnxGreTunnelInvalidChksumRxHi        OBJECT-TYPE
    SYNTAX      Counter32
    MAX-ACCESS  read-only
    STATUS      obsolete
    DESCRIPTION
        "The value of tmnxGreTunnelInvalidChksumRxHi indicates higher 32 bits of
        the value of tmnxGreTunnelInvalidChksumRx object."
    ::= { tmnxGreTunnelStatsEntry 26 }

tmnxGreTunnelLoopsRx        OBJECT-TYPE
    SYNTAX      Counter64
    MAX-ACCESS  read-only
    STATUS      obsolete
    DESCRIPTION
        "The value of tmnxGreTunnelLoopsRx indicates the number of
         packets this GRE Tunnel received with payload with destination address
         which could result in a loop and were dropped."
    ::= { tmnxGreTunnelStatsEntry 27 }

tmnxGreTunnelLoopsRxLo        OBJECT-TYPE
    SYNTAX      Counter32
    MAX-ACCESS  read-only
    STATUS      obsolete
    DESCRIPTION
        "The value of tmnxGreTunnelLoopsRxLo indicates lower 32 bits of the
        value of tmnxGreTunnelLoopsRx object."
    ::= { tmnxGreTunnelStatsEntry 28 }

tmnxGreTunnelLoopsRxHi        OBJECT-TYPE
    SYNTAX      Counter32
    MAX-ACCESS  read-only
    STATUS      obsolete
    DESCRIPTION
        "The value of tmnxGreTunnelLoopsRxHi indicates higher 32 bits of
        the value of tmnxGreTunnelLoopsRx object."
    ::= { tmnxGreTunnelStatsEntry 29 }

tmnxGreTunnelTooBigTx        OBJECT-TYPE
    SYNTAX      Counter64
    MAX-ACCESS  read-only
    STATUS      obsolete
    DESCRIPTION
        "The value of tmnxGreTunnelTooBigTx indicates the number of
         packets this GRE Tunnel received which were too big to transmit."
    ::= { tmnxGreTunnelStatsEntry 30 }

tmnxGreTunnelTooBigTxLo        OBJECT-TYPE
    SYNTAX      Counter32
    MAX-ACCESS  read-only
    STATUS      obsolete
    DESCRIPTION
        "The value of tmnxGreTunnelTooBigTxLo indicates lower 32 bits of the
        value of tmnxGreTunnelTooBigTx object."
    ::= { tmnxGreTunnelStatsEntry 31 }

tmnxGreTunnelTooBigTxHi        OBJECT-TYPE
    SYNTAX      Counter32
    MAX-ACCESS  read-only
    STATUS      obsolete
    DESCRIPTION
        "The value of tmnxGreTunnelTooBigTxHi indicates higher 32 bits of
        the value of tmnxGreTunnelTooBigTx object."
    ::= { tmnxGreTunnelStatsEntry 32 }

-- ---------------------------------------------------------------------
-- SAP ATM Virtual Circuit Range Table
-- ---------------------------------------------------------------------
sapAtmVcRangeTable OBJECT-TYPE
    SYNTAX          SEQUENCE OF SapAtmVcRangeEntry
    MAX-ACCESS      not-accessible
    STATUS          current
    DESCRIPTION     
        "The  sapAtmVcRangeTable contains ATM Virtual Circuit ranges
         for ATM Capture SAP's.
         
         Entries in this table can be created or deleted via SNMP operations.
         
         For a given ATM Capture SAP, the maximum number of ATM VC ranges is
         limited to 5."
    ::= { tmnxSapObjs 116 }

sapAtmVcRangeEntry OBJECT-TYPE
    SYNTAX          SapAtmVcRangeEntry
    MAX-ACCESS      not-accessible
    STATUS          current
    DESCRIPTION     
        "Each conceptual row represents an ATM Virtual Circuit range."
    INDEX           { svcId, sapPortId, sapEncapValue,  sapAtmVcRangeIndex}
    ::= { sapAtmVcRangeTable 1 }

SapAtmVcRangeEntry ::=
    SEQUENCE {
        sapAtmVcRangeIndex              Unsigned32,
        sapAtmVcRangeRowStatus          RowStatus,
        sapAtmVcRangeLastMgmtChange     TimeStamp,
        sapAtmVcRangeVpiStart           AtmVpIdentifier,
        sapAtmVcRangeVpiEnd             AtmVpIdentifier,
        sapAtmVcRangeVciStart           AtmVcIdentifier,
        sapAtmVcRangeVciEnd             AtmVcIdentifier
  }

sapAtmVcRangeIndex OBJECT-TYPE
    SYNTAX      Unsigned32 (1..5) 
    MAX-ACCESS  not-accessible
    STATUS      current
    DESCRIPTION 
        "The value of sapAtmVcRangeIndex specifies the identifier of this
         ATM Virtual Circuit Range."
    ::= { sapAtmVcRangeEntry 1 }

sapAtmVcRangeRowStatus OBJECT-TYPE
    SYNTAX      RowStatus
    MAX-ACCESS  read-create
    STATUS      current
    DESCRIPTION
       "The value of sapAtmVcRangeRowStatus specifies 
        the row status of this row."
    ::= { sapAtmVcRangeEntry 2 }

sapAtmVcRangeLastMgmtChange OBJECT-TYPE
    SYNTAX      TimeStamp
    MAX-ACCESS  read-only
    STATUS      current
    DESCRIPTION
        "The value of sapAtmVcRangeLastMgmtChange indicates the sysUpTime at
         the time of the most recent management-initiated change to this
         table row."
    ::= { sapAtmVcRangeEntry 3 }

sapAtmVcRangeVpiStart OBJECT-TYPE
    SYNTAX      AtmVpIdentifier
    MAX-ACCESS  read-create
    STATUS      current
    DESCRIPTION
       "The value of sapAtmVcRangeVpiStart specifies the start
        Virtual Path Identifier (VPI) of this range." 
    ::= { sapAtmVcRangeEntry 4 }

sapAtmVcRangeVpiEnd OBJECT-TYPE
    SYNTAX      AtmVpIdentifier
    MAX-ACCESS  read-create
    STATUS      current
    DESCRIPTION
       "The value of sapAtmVcRangeVpiEnd specifies the end
        Virtual Path Identifier (VPI) of this range." 
    ::= { sapAtmVcRangeEntry 5 }

sapAtmVcRangeVciStart OBJECT-TYPE
    SYNTAX      AtmVcIdentifier (1..65535)
    MAX-ACCESS  read-create
    STATUS      current
    DESCRIPTION
       "The value of sapAtmVcRangeVciStart specifies the start
        Virtual Circuit Identifier (VCI) of this range." 
    ::= { sapAtmVcRangeEntry 6 }

sapAtmVcRangeVciEnd OBJECT-TYPE
    SYNTAX      AtmVcIdentifier (1..65535)
    MAX-ACCESS  read-create
    STATUS      current
    DESCRIPTION
       "The value of sapAtmVcRangeVciEnd specifies the end
        Virtual Circuit Identifier (VCI) of this range." 
    ::= { sapAtmVcRangeEntry 7 }

-- --------------------------------------------------------
-- msapAtmPlcyTable
-- --------------------------------------------------------
msapAtmPlcyTable OBJECT-TYPE
    SYNTAX      SEQUENCE OF MsapAtmPlcyEntry
    MAX-ACCESS  not-accessible
    STATUS      current
    DESCRIPTION
        "The msapAtmPlcyTable has an entry for each managed SAP (MSAP)
         policy configured in the system."
    ::= { tmnxSapObjs 117 }

msapAtmPlcyEntry OBJECT-TYPE
    SYNTAX      MsapAtmPlcyEntry
    MAX-ACCESS  not-accessible
    STATUS      current
    DESCRIPTION
        "Each entry represents the ATM-related configuration for a managed
         SAP (MSAP) policy.
         
         Entries in this table are created and destroyed automatically
         by the system."
    AUGMENTS { msapPlcyEntry }
    ::= { msapAtmPlcyTable 1}

MsapAtmPlcyEntry ::= SEQUENCE
    {
        msapAtmPlcyLastChanged          TimeStamp,
        msapAtmPlcyIngTrafficDescIndex  AtmTrafficDescrParamIndex,
        msapAtmPlcyEgrTrafficDescIndex  AtmTrafficDescrParamIndex,
        msapAtmPlcyOamAlarmCellHandling ServiceAdminStatus,
        msapAtmPlcyOamPeriodicLoopback  ServiceAdminStatus
    }

msapAtmPlcyLastChanged OBJECT-TYPE
    SYNTAX      TimeStamp
    MAX-ACCESS  read-only
    STATUS      current
    DESCRIPTION
        "The value of msapAtmPlcyLastChanged indicates the sysUpTime
         at the time of the last modification of this entry.

         If no changes were made to the entry since the last
         re-initialization of the local network management subsystem,
         then this object contains a zero value."
    ::= { msapAtmPlcyEntry 1 }

msapAtmPlcyIngTrafficDescIndex OBJECT-TYPE
    SYNTAX      AtmTrafficDescrParamIndex (1..1000)
    MAX-ACCESS  read-create
    STATUS      current
    DESCRIPTION
        "The value of msapAtmPlcyIngTrafficDescIndex specifies
         the index of the ATM traffic descriptor in the ATM traffic
         data encapsulation used for the ingress direction over
         the AAL5 SSCS layer.
         
         The definition references RFC 2684 Multiprotocol Encapsulation over
         ATM AAL5 and to the ATM Forum LAN Emulation specification."
    DEFVAL { 1 }
    ::= { msapAtmPlcyEntry 2 }

msapAtmPlcyEgrTrafficDescIndex OBJECT-TYPE
    SYNTAX      AtmTrafficDescrParamIndex (1..1000)
    MAX-ACCESS  read-create
    STATUS      current
    DESCRIPTION
        "The value of msapAtmPlcyEgrTrafficDescIndex specifies 
         the index of the ATM traffic descriptor in the ATM traffic 
         data encapsulation used for the egress direction over
         the AAL5 SSCS layer.
         
         The definition references RFC 2684 Multiprotocol Encapsulation over
         ATM AAL5 and to the ATM Forum LAN Emulation specification."
    DEFVAL { 1 }
    ::= { msapAtmPlcyEntry 3 }
    
msapAtmPlcyOamAlarmCellHandling OBJECT-TYPE
    SYNTAX      ServiceAdminStatus
    MAX-ACCESS  read-create
    STATUS      current
    DESCRIPTION     
        "The value of msapAtmPlcyOamAlarmCellHandling specifies the
         administrative state of the OAM Alarm Cell handling.
         
         A value of 'up' specifies that the OAM status of a  
         PVC (Permanent Virtual Circuit) affects the
         MSAP operational status and OAM AIS/RDI cell generation upon an
         MSAP operational status of down.
         
         A value of 'down' specifies that the OAM status of a PVC will not
         affect the operational status of the associated MSAP and no OAM 
         AIS/RDI cells are generated."
    DEFVAL { up }
    ::= { msapAtmPlcyEntry 4 }

msapAtmPlcyOamPeriodicLoopback OBJECT-TYPE
    SYNTAX      ServiceAdminStatus
    MAX-ACCESS  read-create
    STATUS      current
    DESCRIPTION
        "The value of msapAtmPlcyOamPeriodicLoopback specifies if the
         MSAP will run periodic OAM loopbacks. 
         
         If enabled, an ATM OAM loopback cell will be transmitted every period  
         as configured in tAtmSysOamLoopbackPeriod; if a response is not
         received and tAtmSysOamRetryDown consecutive retries also result
         in failure, the endpoint will transition to the eteAisLoc state;
         once in the eteAisLoc state, an ATM OAM loopback cell will be
         transmitted every period as configured in tAtmSysOamLoopbackPeriod;
         if a response is received for the periodic loopback and
         tAtmSysOamRetryUp consecutive retries also each receive a response,
         the endpoint will transition back to the up state."
    DEFVAL { down }
    ::= { msapAtmPlcyEntry 5 }

-- ---------------------------------------------------------------------
-- Ethernet CFM SAP Table
--
--
--  Sparse Dependent Extension of the sapBaseInfoTable.
--
--  The same indexes are used for both the base table, sapBaseInfoTable,
--  and the sparse dependent table, sapEthCfmTable.
--
--  This in effect extends the sapBaseInfoTable with additional columns.
--  Rows are created in the sapEthCfmTable only for those entries
--  in the sapBaseInfoTable that have an Ethernet encapsulation.
--
--  Deletion of a row in the sapBaseInfoTable results in the
--  same fate for the row in the sapEthCfmTable.
-- ---------------------------------------------------------------------
sapEthCfmTblLastChanged  OBJECT-TYPE
    SYNTAX      TimeStamp
    MAX-ACCESS  read-only
    STATUS      current
    DESCRIPTION
        "The value of sapEthCfmTblLastChanged indicates the sysUpTime
         at the time of the last modification of the sapEthCfmTable."
    ::= { tmnxSapObjs 119 }

sapEthCfmTable  OBJECT-TYPE
    SYNTAX      SEQUENCE OF SapEthCfmEntry
    MAX-ACCESS  not-accessible
    STATUS      current
    DESCRIPTION
        "The sapEthCfmTable consists of the information pertaining to Ethernet
         Connectivity Fault Management (CFM) for Service Access Points (SAPs).

         This table is a sparse dependent extension of the sapBaseInfoTable."
    ::= { tmnxSapObjs 120 }

sapEthCfmEntry  OBJECT-TYPE
    SYNTAX      SapEthCfmEntry
    MAX-ACCESS  not-accessible
    STATUS      current
    DESCRIPTION
        "The sapEthCfmEntry contains the Ethernet CFM information for a given
         Ethernet encapsulated SAP."
    INDEX       { svcId,
                  sapPortId,
                  sapEncapValue
                }
    ::= { sapEthCfmTable 1 }

SapEthCfmEntry                   ::= SEQUENCE {
    sapEthCfmRowLastChanged          TimeStamp,
    sapEthCfmTunnelFaultNotification INTEGER,
    sapEthCfmMcLagPropHoldTimeRemain Unsigned32,
    sapEthCfmAisEnable               TruthValue,
    sapEthCfmVMepFilter              TruthValue,
    sapEthCfmSquelchIngress          BITS,
    sapEthCfmCollectLmmStats         TruthValue
}

sapEthCfmRowLastChanged          OBJECT-TYPE
    SYNTAX      TimeStamp
    MAX-ACCESS  read-only
    STATUS      current
    DESCRIPTION
        "The value of sapEthCfmRowLastChanged indicates the sysUpTime at the
         time of the last modification to an object for this row.

         If no changes were made to the entry since the instantiation of the
         row, then this object contains a zero value."
    ::= { sapEthCfmEntry 1 }


sapEthCfmTunnelFaultNotification OBJECT-TYPE
    SYNTAX      INTEGER {
                    notApplicable (0),
                    accept        (1),
                    ignore        (2)
                }
    MAX-ACCESS  read-create
    STATUS      current
    DESCRIPTION
        "The value of sapEthCfmTunnelFaultNotification specifies whether the SAP
         will 'accept (1)' CFM fault notifications from a Tunnel MEP and process
         the notifications (i.e. do fault handling and/or fault propagation), or
         'ignore (2)' the notification.

         Both TIMETRA-SERV-MIB::svcEthCfmTunnelFaultNotification and this object
         MUST be set to 'accept (1)' for the SAP to process the notification.

         The value 'notApplicable (0)' is used by the system to represent a SAP
         which supports ETH-CFM, but not this object. An SNMP Set attempting to
         change this object to this value will result in an wrongValue error."
    DEFVAL { accept }
    ::= { sapEthCfmEntry 2 }

sapEthCfmMcLagPropHoldTimeRemain OBJECT-TYPE
    SYNTAX      Unsigned32
    UNITS       "seconds"
    MAX-ACCESS  read-only
    STATUS      current
    DESCRIPTION
        "The value of sapEthCfmMcLagPropHoldTimeRemain indicates the remaining
         time, in seconds, until MEPs on this SAP will react to a Multi-Chassis
         LAG protocol or port change. The value zero (0) indicates there are no
         pending events, or the SAP is not a MC-LAG SAP.

         This object corresponds to the global configuration timer:
            TIMETRA-IEEE8021-CFM-MIB::tmnxDot1agCfmMcLagPropHoldTime."
    ::= { sapEthCfmEntry 3 }

sapEthCfmAisEnable               OBJECT-TYPE
    SYNTAX      TruthValue
    MAX-ACCESS  read-create
    STATUS      current
    DESCRIPTION
        "The value of sapEthCfmAisEnable specifies whether or not AIS frames are
             generated for the SAP based on a facility fault."
    DEFVAL { false }
    ::= { sapEthCfmEntry 4 }

sapEthCfmVMepFilter              OBJECT-TYPE
    SYNTAX      TruthValue
    MAX-ACCESS  read-create
    STATUS      current
    DESCRIPTION
        "The value of sapEthCfmVMepFilter specifies whether ETH-CFM PDUs
         egressing the sap or sdp-binding at the same level or lower than
         that of the configured service MEP (the virtual MEP) should be
         discarded or continue to egress.

         Only PDUs that were originated from the virtual MEP or from the
         networks side of the service will be affected, local down MEP ETH-CFM
         transmission are not.  When set to 'true' ETH-CFM PDUs with the same or
         lower level as the virtual MEP will be discarded.  When set to 'false',
         egressing ETH-CFM PDUs will pass freely as per the existing ETH-CFM
         configuration."
   DEFVAL { false }
   ::= { sapEthCfmEntry 5 }

sapEthCfmSquelchIngress         OBJECT-TYPE
    SYNTAX      BITS {
                    level0 (0),
                    level1 (1),
                    level2 (2),
                    level3 (3),
                    level4 (4),
                    level5 (5),
                    level6 (6),
                    level7 (7)
                }

    MAX-ACCESS  read-create
    STATUS      current
    DESCRIPTION
        "The value of sapEthCfmSquelchIngress specifies the ETH-CFM level or
         levels that are silently discarded on ingress to the SAP. Any 
         received ETH-CFM PDU matching a level that has been set will be 
         dropped without regard for any other ETH-CFM criteria.
         
         No statistical information or drop count will be available for any 
         ETH-CFM PDU that is silently discarded by this option."
    DEFVAL { { } }
    ::= { sapEthCfmEntry 6 }

sapEthCfmCollectLmmStats         OBJECT-TYPE
    SYNTAX      TruthValue
    MAX-ACCESS  read-create
    STATUS      current
    DESCRIPTION
        "The value of sapEthCfmCollectLmmStats specifies whether or not to
         compute the Y.1731 Ethernet Loss Measurement (ETH-LM) 'RxFCl' and
         'TxFCl' service frame counters for the specified SAP.  The 'RxFCl' and
         'TxFCl' counters are used by ETH-LM tests.  An ETH-LM test is created
         using TIMETRA-OAM-PM-MIB::tmnxOamPmCfgLossLmmRowStatus."
    REFERENCE
        "ITU-T G.8013/Y.1731, 'OAM functions and mechanisms for Ethernet based
         networks', 11/2013, Section 8.1 'Frame loss measurement (ETH-LM)'."
    DEFVAL { false }
    ::= { sapEthCfmEntry 7 }

-- ------------------------------------
-- SAP egress encapsulation group table
-- ------------------------------------
sapEgrEncapGroupTblLastChgd OBJECT-TYPE
    SYNTAX       TimeStamp
    MAX-ACCESS   read-only
    STATUS       current
    DESCRIPTION
        "sapEgrEncapGroupTblLastChgd indicates the timestamp of last change to
        the sapEgrEncapGroupTable."
    ::= { tmnxSapObjs 121 }

sapEgrEncapGroupTable OBJECT-TYPE
    SYNTAX          SEQUENCE OF SapEgrEncapGroupEntry
    MAX-ACCESS      not-accessible
    STATUS          current
    DESCRIPTION
        "A table that contains SAP egress encapsulation group information."
    ::= { tmnxSapObjs 122 }

sapEgrEncapGroupEntry OBJECT-TYPE
    SYNTAX          SapEgrEncapGroupEntry
    MAX-ACCESS      not-accessible
    STATUS          current
    DESCRIPTION
        "Encapsulation group information about a specific group of the SAP on
         the egress side."
    INDEX           { svcId, sapPortId, sapEncapValue, sapEgrEncapGroupName }
    ::= { sapEgrEncapGroupTable 1 }

SapEgrEncapGroupEntry ::=
    SEQUENCE {
        sapEgrEncapGroupName            TNamedItem,
        sapEgrEncapGroupRowStatus       RowStatus,
        sapEgrEncapGroupLastChanged     TimeStamp,
        sapEgrEncapGroupType            TSapEgrEncapGroupType,
        sapEgrEncapGroupQosPerMember    TruthValue,
        sapEgrEncapGroupQosPolicyId     TSapEgrEncapGrpQosPolicyIdOrZero,
        sapEgrEncapGroupSchedulerPolicy TNamedItemOrEmpty,
        sapEgrEncapGroupAggRateLimit    TPortSchedulerAggRateLimitPIR,
        sapEgrEncapGrpFrameBasedAccnt   TruthValue,
        sapEgrEncapGroupAggRateLUB      TruthValue,
        sapEgrEncapGrpAggRateLimit      Unsigned32
    }

sapEgrEncapGroupName OBJECT-TYPE
    SYNTAX          TNamedItem
    MAX-ACCESS      not-accessible
    STATUS          current
    DESCRIPTION     
        "The sapEgrEncapGroupName indicates the encapsulation group name on this
         SAP."
    ::= { sapEgrEncapGroupEntry 1 }

sapEgrEncapGroupRowStatus OBJECT-TYPE
    SYNTAX       RowStatus
    MAX-ACCESS   read-create
    STATUS       current
    DESCRIPTION
        "This is the Row Status of the entry. This allows creation/deletion of 
         rows in this table. To create row entries in this table 
         sapEgrEncapGroupType MUST be specified in the same SNMP SET PDU request
         as sapEgrEncapGroupRowStatus or a 'noCreation' error is returned."
    ::= { sapEgrEncapGroupEntry 2 }

sapEgrEncapGroupLastChanged OBJECT-TYPE
    SYNTAX       TimeStamp
    MAX-ACCESS   read-only
    STATUS       current
    DESCRIPTION
        "sapEgrEncapGroupLastChanged indicates the timestamp of last change to
        this row in sapEgrEncapGroupTable."
    ::= { sapEgrEncapGroupEntry 3 }

sapEgrEncapGroupType OBJECT-TYPE
    SYNTAX       TSapEgrEncapGroupType
    MAX-ACCESS   read-create
    STATUS       current
    DESCRIPTION
        "The value of sapEgrEncapGroupType specifies the encapsulation
         group type configured on this SAP on egress side. To create row entries
         in this table sapEgrEncapGroupType MUST be specified in the same SNMP 
         SET PDU request as sapEgrEncapGroupRowStatus or a 'noCreation' error is
         returned."
    ::= { sapEgrEncapGroupEntry 4 }

sapEgrEncapGroupQosPerMember OBJECT-TYPE
    SYNTAX       TruthValue
    MAX-ACCESS   read-create
    STATUS       current
    DESCRIPTION
        "The value of sapEgrEncapGroupQosPerMember specifies how the QoS members
         will be added to or deleted from the encapsulation group.  If the value
         of sapEgrEncapGroupQosPerMember is set to 'true', members are added or 
         deleted one at a time. If the value of sapEgrEncapGroupQosPerMember is 
         set to 'false', members are added to the encapsulation group as a range
         of contiguous values."
    DEFVAL { false }
    ::= { sapEgrEncapGroupEntry 5 }

sapEgrEncapGroupQosPolicyId OBJECT-TYPE
    SYNTAX       TSapEgrEncapGrpQosPolicyIdOrZero
    MAX-ACCESS   read-create
    STATUS       current
    DESCRIPTION
        "The value of sapEgrEncapGroupQosPolicyId specifies the QoS policy id
         of the encapsulation group on this SAP on egress side.
         
         The value '0' for sapEgrEncapGroupQosPolicyId means that there is no
         QoS policy."  
    DEFVAL { 0 }
    ::= { sapEgrEncapGroupEntry 6 }

sapEgrEncapGroupSchedulerPolicy OBJECT-TYPE
    SYNTAX       TNamedItemOrEmpty
    MAX-ACCESS   read-create
    STATUS       current
    DESCRIPTION
        "The value of sapEgrEncapGroupSchedulerPolicy specifies the name of
         the encapsulation group scheduler policy on this SAP on egress side."
    DEFVAL { "" }
    ::= { sapEgrEncapGroupEntry 7 }

sapEgrEncapGroupAggRateLimit OBJECT-TYPE
    SYNTAX          TPortSchedulerAggRateLimitPIR
    UNITS           "kbps"
    MAX-ACCESS      read-create
    STATUS          obsolete
    DESCRIPTION
        "The value of the object sapEgrEncapGroupAggRateLimit specifies the 
         maximum total rate of all egress encapsulation groups for this SAP. 

         The value '-1' for sapEgrEncapGroupAggRateLimit means that there is no
         limit.

         This object is obsoleted in 13.0 release and replaced by
         sapEgrEncapGrpAggRateLimit."
    DEFVAL { -1 }
    ::= { sapEgrEncapGroupEntry 8 }

sapEgrEncapGrpFrameBasedAccnt OBJECT-TYPE
    SYNTAX       TruthValue
    MAX-ACCESS   read-create
    STATUS       current
    DESCRIPTION
        "The value of sapEgrEncapGrpFrameBasedAccnt specifies whether to use 
         frame-based accounting when evaluating sapEgrEncapGrpAggRateLimit for
         all egress queues for this SAP.

         If the value is 'false', the default packet-based accounting method 
         will be used."
    DEFVAL { false }
    ::= { sapEgrEncapGroupEntry 9 }

sapEgrEncapGroupAggRateLUB   OBJECT-TYPE
    SYNTAX      TruthValue
    MAX-ACCESS  read-create
    STATUS      current
    DESCRIPTION 
        "The value of sapEgrEncapGroupAggRateLUB specifies whether to limit the
         unused bandwidth and allow a tighter control in allocation of bandwidth
         by HQos.

         When the value of sapEgrEncapGroupAggRateLUB is set to 'true', HQos
         algorithm distributes any unused aggregate bandwidth between queues
         operating below their fair share rates. This allows a simplified
         aggregate rate protection while allocating bandwidth by HQos scheduling
         algorithm."
    DEFVAL { false }
    ::= { sapEgrEncapGroupEntry 10 }



sapEgrEncapGrpAggRateLimit          OBJECT-TYPE
    SYNTAX          Unsigned32 (1..3200000000 | 4294967295)
    UNITS           "kbps"
    MAX-ACCESS      read-create
    STATUS          current
    DESCRIPTION
        "The value of sapEgrEncapGrpAggRateLimit specifies the maximum total
         rate of all egress encapsulation groups for this SAP.

         The value of 4294967295 (0xFFFFFFFF) means that there is no limit."
    DEFVAL { 4294967295 }
    ::= { sapEgrEncapGroupEntry 13 }

-- --------------------------------------------------
-- SAP egress encapsulation group member action table
-- --------------------------------------------------
sapEgrEncapGrpMemActTblLastChgd OBJECT-TYPE
    SYNTAX       TimeStamp
    MAX-ACCESS   read-only
    STATUS       current
    DESCRIPTION
        "sapEgrEncapGrpMemActTblLastChgd indicates the timestamp of last
         change to the sapEgrEncapGrpMemberActTable."
    ::= { tmnxSapObjs 123 }
    
sapEgrEncapGrpMemberActTable OBJECT-TYPE
    SYNTAX          SEQUENCE OF SapEgrEncapGrpMemberActEntry
    MAX-ACCESS      not-accessible
    STATUS          current
    DESCRIPTION
        "sapEgrEncapGrpMemberActTable creates or deletes one or more SAP egress 
         encapsulation group member row entries in the sapEgrEncapGrpMemberTable
         by setting a single row in this table.  An SNMP GET on this table will 
         always return a 'noSuchInstance' error."
    ::= { tmnxSapObjs 124 }

sapEgrEncapGrpMemberActEntry OBJECT-TYPE
    SYNTAX          SapEgrEncapGrpMemberActEntry
    MAX-ACCESS      not-accessible
    STATUS          current
    DESCRIPTION
        "Encapsulation group member action information about a specific or 
         a range of groups of the SAP on the egress side.

        To create/delete row entries in the sapEgrEncapGrpMemberTable 
        objects sapEgrEncapGroupBeginMember, sapEgrEncapGroupEndMember
        and sapEgrEncapGroupMemberAction MUST all be specified in the same SNMP
        SET PDU request or a 'noCreation' error is returned.

        To create/delete a single row entry in the sapEgrEncapGrpMemberTable 
        sapEgrEncapGroupEndMember MUST be same as sapEgrEncapGroupBeginMember."
    INDEX           { svcId, sapPortId, sapEncapValue, sapEgrEncapGroupName }
    ::= { sapEgrEncapGrpMemberActTable 1 }

SapEgrEncapGrpMemberActEntry ::=
    SEQUENCE {
        sapEgrEncapGroupBeginMember      SvcISID,
        sapEgrEncapGroupEndMember        SvcISID,
        sapEgrEncapGroupMemberAction     TSapEgrEncapGroupActionType
    }

sapEgrEncapGroupBeginMember OBJECT-TYPE
    SYNTAX       SvcISID
    MAX-ACCESS   read-write
    STATUS       current
    DESCRIPTION
        "The value of sapEgrEncapGroupBeginMember specifies the single 
         encapsulation member identifier or the start value of encapsulation 
         member identifier range." 
    ::= { sapEgrEncapGrpMemberActEntry 1 }

sapEgrEncapGroupEndMember OBJECT-TYPE
    SYNTAX       SvcISID
    MAX-ACCESS   read-write
    STATUS       current
    DESCRIPTION
        "The value of sapEgrEncapGroupEndMember specifies the end value of 
         encapsulation member identifier range. The value of 
         sapEgrEncapGroupEndMember MUST be greater than that of 
         sapEgrEncapGroupBeginMember." 
    ::= { sapEgrEncapGrpMemberActEntry 2 }

sapEgrEncapGroupMemberAction OBJECT-TYPE
    SYNTAX       TSapEgrEncapGroupActionType
    MAX-ACCESS   read-write
    STATUS       current
    DESCRIPTION
        "The value of sapEgrEncapGroupMemberAction specifies whether members of
         encapsulation group are created or destroyed.
         
         An 'inconsistentValue' error is returned if 
         sapEgrEncapGroupMemberAction is set and sapEgrEncapGroupBeginMember or 
         sapEgrEncapGroupEndMember is not set.
         
         An 'inconsistentValue' error is returned if sapEgrEncapGroupEndMember 
         is set to a value smaller than sapEgrEncapGroupBeginMember."
    ::= { sapEgrEncapGrpMemberActEntry 3 }

-- --------------------------------------------------
-- SAP egress encapsulation group member table
-- --------------------------------------------------
sapEgrEncapGrpMemberTable OBJECT-TYPE
    SYNTAX          SEQUENCE OF SapEgrEncapGrpMemberEntry
    MAX-ACCESS      not-accessible
    STATUS          current
    DESCRIPTION
        "A table that contains SAP egress encapsulation group member entry
         information.
        
         The row entries in this table are created or destroyed by SNMP SET 
         operations on sapEgrEncapGrpMemberActTable." 
    ::= { tmnxSapObjs 126 }

sapEgrEncapGrpMemberEntry OBJECT-TYPE
    SYNTAX          SapEgrEncapGrpMemberEntry
    MAX-ACCESS      not-accessible
    STATUS          current
    DESCRIPTION
        "Encapsulation group member entry information about a specific group 
         of the SAP on the egress side."
    INDEX           { svcId, sapPortId, sapEncapValue, sapEgrEncapGroupName, 
                      sapEgrEncapGrpMember }
    ::= { sapEgrEncapGrpMemberTable 1 }

SapEgrEncapGrpMemberEntry ::=
    SEQUENCE {
        sapEgrEncapGrpMember                SvcISID,
        sapEgrEncapGrpRangeEndId            SvcISID,
        sapEgrEncapGrpMemberLastChanged     TimeStamp
    }

sapEgrEncapGrpMember OBJECT-TYPE
    SYNTAX       SvcISID (0..16777215)
    MAX-ACCESS   not-accessible
    STATUS       current
    DESCRIPTION
        "The value of sapEgrEncapGrpMember indicates the encapsulation member
         identifier of the SAP on the egress side." 
    ::= { sapEgrEncapGrpMemberEntry 1 }

sapEgrEncapGrpRangeEndId OBJECT-TYPE
    SYNTAX       SvcISID
    MAX-ACCESS   read-only
    STATUS       current
    DESCRIPTION
        "The value of sapEgrEncapGrpRangeEndId specifies the end value of 
         encapsulation member identifier range. When the encapsualtion group's
         qos-per-member object is set to true, the value of 
         sapEgrEncapGrpRangeEndId is always equal to the sapEgrEncapGrpMember.
         This is because member ranges are not supported when qos-per-member is
         enabled." 
    ::= { sapEgrEncapGrpMemberEntry 2 }

sapEgrEncapGrpMemberLastChanged OBJECT-TYPE
    SYNTAX      TimeStamp
    MAX-ACCESS  read-only
    STATUS      current
    DESCRIPTION
        "The value of sapEgrEncapGrpMemberLastChanged indicates the timestamp of
         last change to this row in sapEgrEncapGrpMemberEntry."
    ::= { sapEgrEncapGrpMemberEntry 3 }

-- ---------------------------------------------------------------------
-- ATM SAP PPP statistics Table
--
--
--  Sparse Dependent Extention of the sapBaseInfoTable.
--
--  The same indexes are used for both the base table, sapBaseInfoTable,
--  and the sparse dependent table, sapAtmPppStatsTable.
--
--  This in effect extends the sapBaseInfoTable with additional columns.
--  Rows are created in the sapAtmPppStatsTable only for those entries
--  in the sapBaseInfoTable that are created on a port that 'atmEncap' set
--- for port encapsulation.
--
--  Deletion of a row in the sapBaseInfoTable results in the
--  same fate for the row in the sapAtmPppStatsTable.
-- ---------------------------------------------------------------------
sapAtmPppStatsTable OBJECT-TYPE
    SYNTAX          SEQUENCE OF SapAtmPppStatsEntry
    MAX-ACCESS      not-accessible
    STATUS          current
    DESCRIPTION     "A table that contains ATM SAP PPP statistics information."
    ::= { tmnxSapObjs 127 }

sapAtmPppStatsEntry OBJECT-TYPE
    SYNTAX          SapAtmPppStatsEntry
    MAX-ACCESS      not-accessible
    STATUS          current
    DESCRIPTION     "PPP statistics about a specific ATM SAP."
    INDEX           { svcId, sapPortId, sapEncapValue }
    ::= { sapAtmPppStatsTable 1 }

SapAtmPppStatsEntry ::=
    SEQUENCE {
        sapAtmPppStatsRxPackets           Counter32,
        sapAtmPppStatsRxDropped          Counter32,
        sapAtmPppStatsTxPackets           Counter32
  }

sapAtmPppStatsRxPackets OBJECT-TYPE
    SYNTAX           Counter32
    MAX-ACCESS       read-only
    STATUS           current
    DESCRIPTION      "The value of sapAtmPppStatsRxPackets indicates
                      the number of PPP packets received on this ATM SAP   
                      since the last re-initialization of the local network 
                      management subsystem, or the last time the statistics were 
                      cleared."
    ::= { sapAtmPppStatsEntry 1 }

sapAtmPppStatsRxDropped OBJECT-TYPE
    SYNTAX           Counter32
    MAX-ACCESS       read-only
    STATUS           current
    DESCRIPTION      "The value of sapAtmPppStatsRxPackets indicates
                      the number of PPP packets dropped on this ATM SAP   
                      since the last re-initialization of the local network 
                      management subsystem, or the last time the statistics were 
                      cleared."
    ::= { sapAtmPppStatsEntry 2 }

sapAtmPppStatsTxPackets OBJECT-TYPE
    SYNTAX           Counter32
    MAX-ACCESS       read-only
    STATUS           current
    DESCRIPTION      "The value of sapAtmPppStatsRxPackets indicates
                      the number of PPP packets transmitted on this ATM SAP   
                      since the last re-initialization of the local network 
                      management subsystem, or the last time the statistics were 
                      cleared."
    ::= { sapAtmPppStatsEntry 3 }

-- ------------------------------
-- GRE Tunnel Count
-- ------------------------------
tmnxSapGlobalObjs   OBJECT IDENTIFIER ::= { tmnxSapObjs 128 }

tmnxSapGreTunnelCount OBJECT-TYPE
    SYNTAX      Gauge32
    MAX-ACCESS  read-only
    STATUS      current
    DESCRIPTION
        "The value of tmnxSapGreTunnelCount indicates the number of GRE tunnels
        operating in the system at this time."
    ::= { tmnxSapGlobalObjs 1 }

-- --------------------------------------------------
-- SAP egress encapsulation group base stats table
-- --------------------------------------------------
sapEgrEGBaseStTable OBJECT-TYPE
    SYNTAX          SEQUENCE OF SapEgrEGBaseStEntry
    MAX-ACCESS      not-accessible
    STATUS          current
    DESCRIPTION
        "The sapEgrEGBaseStTable contains egress Encap Group basic SAP 
         statistics at the Group level. This statistics table is valid for Encap
         Groups created without enabling sapEgrEncapGroupQosPerMember. In the 
         descriptions below 'Qchip' refers to the  Nokia SROS series 
         QoS Queueing Engine chip."    
    ::= { tmnxSapObjs 129 }

sapEgrEGBaseStEntry OBJECT-TYPE
    SYNTAX          SapEgrEGBaseStEntry
    MAX-ACCESS      not-accessible
    STATUS          current
    DESCRIPTION
        "Egress statistics about a specific Encap Group of a SAP."
    INDEX           { svcId, sapPortId, sapEncapValue, sapEgrEncapGroupName }
    ::= { sapEgrEGBaseStTable 1 }

SapEgrEGBaseStEntry ::=
    SEQUENCE {
        sapEgrEGBaseStLastClearedTime      TimeStamp,
        sapEgrEGBaseStCustId               TmnxCustId,
        sapEgrEGBaseStQcDpdInPfPkts        Counter64,
        sapEgrEGBaseStQcDpdInPfPktsL       Counter32,
        sapEgrEGBaseStQcDpdInPfPktsH       Counter32,
        sapEgrEGBaseStQcDpdInPfOcts        Counter64,
        sapEgrEGBaseStQcDpdInPfOctsL       Counter32,
        sapEgrEGBaseStQcDpdInPfOctsH       Counter32,
        sapEgrEGBaseStQcDpdOutPfPkts       Counter64,
        sapEgrEGBaseStQcDpdOutPfPktsL      Counter32,
        sapEgrEGBaseStQcDpdOutPfPktsH      Counter32,
        sapEgrEGBaseStQcDpdOutPfOcts       Counter64,
        sapEgrEGBaseStQcDpdOutPfOctsL      Counter32,
        sapEgrEGBaseStQcDpdOutPfOctsH      Counter32,
        sapEgrEGBaseStQcFwdInPfPkts        Counter64,
        sapEgrEGBaseStQcFwdInPfPktsL       Counter32,
        sapEgrEGBaseStQcFwdInPfPktsH       Counter32,
        sapEgrEGBaseStQcFwdInPfOcts        Counter64,
        sapEgrEGBaseStQcFwdInPfOctsL       Counter32,
        sapEgrEGBaseStQcFwdInPfOctsH       Counter32,
        sapEgrEGBaseStQcFwdOutPfPkts       Counter64,
        sapEgrEGBaseStQcFwdOutPfPktsL      Counter32,
        sapEgrEGBaseStQcFwdOutPfPktsH      Counter32,
        sapEgrEGBaseStQcFwdOutPfOcts       Counter64,
        sapEgrEGBaseStQcFwdOutPfOctsL      Counter32,
        sapEgrEGBaseStQcFwdOutPfOctsH      Counter32
    }

sapEgrEGBaseStLastClearedTime OBJECT-TYPE
    SYNTAX          TimeStamp
    MAX-ACCESS      read-only
    STATUS          current
    DESCRIPTION
        "The value of sapEgrEGBaseStLastClearedTime indicates the sysUpTime when
         the counters in this table were last cleared."
    ::= { sapEgrEGBaseStEntry 1 }

sapEgrEGBaseStCustId OBJECT-TYPE
    SYNTAX          TmnxCustId
    MAX-ACCESS      read-only
    STATUS          current
    DESCRIPTION
        "The value of sapEgrEGBaseStCustId indicates the Customer ID for the
         associated service."
    ::= { sapEgrEGBaseStEntry 2 }

sapEgrEGBaseStQcDpdInPfPkts OBJECT-TYPE
    SYNTAX          Counter64
    MAX-ACCESS      read-only
    STATUS          current
    DESCRIPTION
        "The value of sapEgrEGBaseStQcDpdInPfPkts indicates the number of 
         in-profile packets dropped by the egress Qchip due to: SAP state,egress
         MAC, IP or IPv6 filter, same segment discard,bad checksum, etc."
    ::= { sapEgrEGBaseStEntry 3 }

sapEgrEGBaseStQcDpdInPfPktsL OBJECT-TYPE
    SYNTAX          Counter32
    MAX-ACCESS      read-only
    STATUS          current
    DESCRIPTION
        "The value of sapEgrEGBaseStQcDpdInPfPktsL indicates the lower 32 bits
         of the value of sapEgrEGBaseStQcDpdInPfPkts."
    ::= { sapEgrEGBaseStEntry 4 }

sapEgrEGBaseStQcDpdInPfPktsH OBJECT-TYPE
    SYNTAX          Counter32
    MAX-ACCESS      read-only
    STATUS          current
    DESCRIPTION
        "The value of sapEgrEGBaseStQcDpdInPfPktsH indicates the higher 32 bits
         of the value of sapEgrEGBaseStQcDpdInPfPkts."
    ::= { sapEgrEGBaseStEntry 5 }

sapEgrEGBaseStQcDpdInPfOcts OBJECT-TYPE
    SYNTAX          Counter64
    MAX-ACCESS      read-only
    STATUS          current
    DESCRIPTION
        "The value of sapEgrEGBaseStQcDpdInPfOcts indicates the number of 
         in-profile octets dropped by the egress Qchip due to: SAP state, egress
         MAC, IP or IPv6 filter, same segment discard, bad checksum, etc."
    ::= { sapEgrEGBaseStEntry 6 }

sapEgrEGBaseStQcDpdInPfOctsL OBJECT-TYPE
    SYNTAX          Counter32
    MAX-ACCESS      read-only
    STATUS          current
    DESCRIPTION
        "The value of sapEgrEGBaseStQcDpdInPfOctsL indicates the lower 32 bits
         of the value of sapEgrEGBaseStQcDpdInPfOcts."
    ::= { sapEgrEGBaseStEntry 7 }

sapEgrEGBaseStQcDpdInPfOctsH OBJECT-TYPE
    SYNTAX          Counter32
    MAX-ACCESS      read-only
    STATUS          current
    DESCRIPTION
        "The value of sapEgrEGBaseStQcDpdInPfOctsH indicates the higher 32 bits
         of the value of sapEgrEGBaseStQcDpdInPfOcts."
    ::= { sapEgrEGBaseStEntry 8 }

sapEgrEGBaseStQcDpdOutPfPkts OBJECT-TYPE
    SYNTAX          Counter64
    MAX-ACCESS      read-only
    STATUS          current
    DESCRIPTION
        "The value of sapEgrEGBaseStQcDpdOutPfPkts indicates the number of  
         out-of-profile packets discarded by the egress Qchip due to:
         MBS exceeded, buffer pool limit exceeded, etc."
    ::= { sapEgrEGBaseStEntry 9 }

sapEgrEGBaseStQcDpdOutPfPktsL OBJECT-TYPE
    SYNTAX          Counter32
    MAX-ACCESS      read-only
    STATUS          current
    DESCRIPTION     
        "The value of sapEgrEGBaseStQcDpdOutPfPktsL indicates the lower 32 bits
         of the value of sapEgrEGBaseStQcDpdOutPfPkts."
    ::= { sapEgrEGBaseStEntry 10 }

sapEgrEGBaseStQcDpdOutPfPktsH OBJECT-TYPE
    SYNTAX          Counter32
    MAX-ACCESS      read-only
    STATUS          current
    DESCRIPTION
        "The value of sapEgrEGBaseStQcDpdOutPfPktsH indicates the higher 32 bits
         of the value of sapEgrEGBaseStQcDpdOutPfPkts."
    ::= { sapEgrEGBaseStEntry 11 }

sapEgrEGBaseStQcDpdOutPfOcts OBJECT-TYPE
    SYNTAX          Counter64
    MAX-ACCESS      read-only
    STATUS          current
    DESCRIPTION 
        "The value of sapEgrEGBaseStQcDpdOutPfOcts indicates the number of  
         out-of-profile octets discarded by the egress Qchip due to: 
         MBS exceeded, buffer pool limit exceeded, etc."
    ::= { sapEgrEGBaseStEntry 12 }

sapEgrEGBaseStQcDpdOutPfOctsL OBJECT-TYPE
    SYNTAX          Counter32
    MAX-ACCESS      read-only
    STATUS          current
    DESCRIPTION
        "The value of sapEgrEGBaseStQcDpdOutPfOctsL indicates the lower 32 bits
         of the value of sapEgrEGBaseStQcDpdOutPfOcts."
    ::= { sapEgrEGBaseStEntry 13 }

sapEgrEGBaseStQcDpdOutPfOctsH OBJECT-TYPE
    SYNTAX          Counter32
    MAX-ACCESS      read-only
    STATUS          current
    DESCRIPTION
        "The value of sapEgrEGBaseStQcDpdOutPfOctsH indicates the higher 32 bits
         of the value of sapEgrEGBaseStQcDpdOutPfOcts."
    ::= { sapEgrEGBaseStEntry 14 }

sapEgrEGBaseStQcFwdInPfPkts OBJECT-TYPE
    SYNTAX          Counter64
    MAX-ACCESS      read-only
    STATUS          current
    DESCRIPTION     
        "The value of sapEgrEGBaseStQcFwdInPfPkts indicates the number of 
         in-profile packets (rate below CIR) forwarded by the egress Qchip."
    ::= { sapEgrEGBaseStEntry 15 }

sapEgrEGBaseStQcFwdInPfPktsL OBJECT-TYPE
    SYNTAX          Counter32
    MAX-ACCESS      read-only
    STATUS          current
    DESCRIPTION
        "The value of sapEgrEGBaseStQcFwdInPfPktsL indicates the lower 32 bits 
         of the value of sapEgrEGBaseStQcFwdInPfPkts."
    ::= { sapEgrEGBaseStEntry 16 }

sapEgrEGBaseStQcFwdInPfPktsH OBJECT-TYPE
    SYNTAX          Counter32
    MAX-ACCESS      read-only
    STATUS          current
    DESCRIPTION
        "The value of sapEgrEGBaseStQcFwdInPfPktsH indicates the higher 32 bits
         of the value of sapEgrEGBaseStQcFwdInPfPkts."
    ::= { sapEgrEGBaseStEntry 17 }

sapEgrEGBaseStQcFwdInPfOcts OBJECT-TYPE
    SYNTAX          Counter64
    MAX-ACCESS      read-only
    STATUS          current
    DESCRIPTION
        "The value of sapEgrEGBaseStQcFwdInPfOcts indicates the number of 
         in-profile octets (rate below CIR) forwarded by the egress Qchip."
    ::= { sapEgrEGBaseStEntry 18 }

sapEgrEGBaseStQcFwdInPfOctsL OBJECT-TYPE
    SYNTAX          Counter32
    MAX-ACCESS      read-only
    STATUS          current
    DESCRIPTION
        "The value of sapEgrEGBaseStQcFwdInPfOctsL indicates the lower 32 bits
         of the value of sapEgrEGBaseStQcFwdInPfOcts."
    ::= { sapEgrEGBaseStEntry 19 }

sapEgrEGBaseStQcFwdInPfOctsH OBJECT-TYPE
    SYNTAX          Counter32
    MAX-ACCESS      read-only
    STATUS          current
    DESCRIPTION
        "The value of sapEgrEGBaseStQcFwdInPfOctsH indicates the higher 32 bits
         of the value of sapEgrEGBaseStQcFwdInPfOcts."
    ::= { sapEgrEGBaseStEntry 20 }

sapEgrEGBaseStQcFwdOutPfPkts OBJECT-TYPE
    SYNTAX          Counter64
    MAX-ACCESS      read-only
    STATUS          current
    DESCRIPTION
        "The value of sapEgrEGBaseStQcFwdOutPfPkts indicates the number of 
         out-of-profile packets (rate above CIR) forwarded by the egress Qchip."
    ::= { sapEgrEGBaseStEntry 21 }

sapEgrEGBaseStQcFwdOutPfPktsL OBJECT-TYPE
    SYNTAX          Counter32
    MAX-ACCESS      read-only
    STATUS          current
    DESCRIPTION
        "The value of sapEgrEGBaseStQcFwdOutPfPktsL indicates the lower 32 bits
         of the value of sapEgrEGBaseStQcFwdOutPfPkts."
    ::= { sapEgrEGBaseStEntry 22 }

sapEgrEGBaseStQcFwdOutPfPktsH OBJECT-TYPE
    SYNTAX          Counter32
    MAX-ACCESS      read-only
    STATUS          current
    DESCRIPTION
        "The value of sapEgrEGBaseStQcFwdOutPfPktsH indicates the higher 32 bits
         of the value of sapEgrEGBaseStQcFwdOutPfPkts."
    ::= { sapEgrEGBaseStEntry 23 }

sapEgrEGBaseStQcFwdOutPfOcts OBJECT-TYPE
    SYNTAX          Counter64
    MAX-ACCESS      read-only
    STATUS          current
    DESCRIPTION
        "The value of sapEgrEGBaseStQcFwdOutPfOcts indicates the number of
         out-of-profile octets (rate above CIR) forwarded by the egress Qchip."
    ::= { sapEgrEGBaseStEntry 24 }

sapEgrEGBaseStQcFwdOutPfOctsL OBJECT-TYPE
    SYNTAX          Counter32
    MAX-ACCESS      read-only
    STATUS          current
    DESCRIPTION
        "The value of sapEgrEGBaseStQcFwdOutPfOctsL indicates the lower 32 bits
         of the value of sapEgrEGBaseStQcFwdOutPfOcts."
    ::= { sapEgrEGBaseStEntry 25 }

sapEgrEGBaseStQcFwdOutPfOctsH OBJECT-TYPE
    SYNTAX          Counter32
    MAX-ACCESS      read-only
    STATUS          current
    DESCRIPTION
        "The value of sapEgrEGBaseStQcFwdOutPfOctsH indicates the higher 32 bits
         of the value of sapEgrEGBaseStQcFwdOutPfOcts."
    ::= { sapEgrEGBaseStEntry 26 }

-- --------------------------------------------------
-- Base Sap Egress Encap Group Member Statistics Table
-- --------------------------------------------------
sapEgrEGMbrBaseStTable OBJECT-TYPE
    SYNTAX          SEQUENCE OF SapEgrEGMbrBaseStEntry
    MAX-ACCESS      not-accessible
    STATUS          current
    DESCRIPTION
        "The sapEgrEGMbrBaseStTable that contains basic Encap Group statistics 
         per member. This statistics table is valid for Encap Groups created 
         by enabling sapEgrEncapGroupQosPerMember. In the descriptions below 
         'Qchip' refers to the Nokia SROS series QoS Queueing Engine 
         chip."
    ::= { tmnxSapObjs 130 }

sapEgrEGMbrBaseStEntry OBJECT-TYPE
    SYNTAX          SapEgrEGMbrBaseStEntry
    MAX-ACCESS      not-accessible
    STATUS          current
    DESCRIPTION
        "Egress statistics about a specific Encap Group member of a SAP."
    INDEX           { svcId, sapPortId, sapEncapValue, sapEgrEncapGroupName, 
                      sapEgrEncapGrpMember }
    ::= { sapEgrEGMbrBaseStTable 1 }

SapEgrEGMbrBaseStEntry ::=
    SEQUENCE {
        sapEgrEGMbrBaseStLstClearedTime    TimeStamp,
        sapEgrEGMbrBaseStCustId            TmnxCustId,
        sapEgrEGMbrBaseStQcDpdInPfPkts     Counter64,
        sapEgrEGMbrBaseStQcDpdInPfPktsL    Counter32,
        sapEgrEGMbrBaseStQcDpdInPfPktsH    Counter32,
        sapEgrEGMbrBaseStQcDpdInPfOcts     Counter64,
        sapEgrEGMbrBaseStQcDpdInPfOctsL    Counter32,
        sapEgrEGMbrBaseStQcDpdInPfOctsH    Counter32,
        sapEgrEGMbrBaseStQcDpdOutPfPkts    Counter64,
        sapEgrEGMbrBaseStQcDpdOutPfPktsL   Counter32,
        sapEgrEGMbrBaseStQcDpdOutPfPktsH   Counter32,
        sapEgrEGMbrBaseStQcDpdOutPfOcts    Counter64,
        sapEgrEGMbrBaseStQcDpdOutPfOctsL   Counter32,
        sapEgrEGMbrBaseStQcDpdOutPfOctsH   Counter32,
        sapEgrEGMbrBaseStQcFwdInPfPkts     Counter64,
        sapEgrEGMbrBaseStQcFwdInPfPktsL    Counter32,
        sapEgrEGMbrBaseStQcFwdInPfPktsH    Counter32,
        sapEgrEGMbrBaseStQcFwdInPfOcts     Counter64,
        sapEgrEGMbrBaseStQcFwdInPfOctsL    Counter32,
        sapEgrEGMbrBaseStQcFwdInPfOctsH    Counter32,
        sapEgrEGMbrBaseStQcFwdOutPfPkts    Counter64,
        sapEgrEGMbrBaseStQcFwdOutPfPktsL   Counter32,
        sapEgrEGMbrBaseStQcFwdOutPfPktsH   Counter32,
        sapEgrEGMbrBaseStQcFwdOutPfOcts    Counter64,
        sapEgrEGMbrBaseStQcFwdOutPfOctsL   Counter32,
        sapEgrEGMbrBaseStQcFwdOutPfOctsH   Counter32
    }

sapEgrEGMbrBaseStLstClearedTime OBJECT-TYPE
    SYNTAX          TimeStamp
    MAX-ACCESS      read-only
    STATUS          current
    DESCRIPTION
        "The value of sapEgrEGMbrBaseStLstClearedTime indicates the sysUpTime
         when the counters in this table were last cleared."
    ::= { sapEgrEGMbrBaseStEntry 1 }

sapEgrEGMbrBaseStCustId OBJECT-TYPE
    SYNTAX          TmnxCustId
    MAX-ACCESS      read-only
    STATUS          current
    DESCRIPTION
        "The value of sapEgrEGMbrBaseStCustId indicates the Customer ID for the
         associated service."
    ::= { sapEgrEGMbrBaseStEntry 2 }

sapEgrEGMbrBaseStQcDpdInPfPkts OBJECT-TYPE
    SYNTAX          Counter64
    MAX-ACCESS      read-only
    STATUS          current
    DESCRIPTION
        "The value of sapEgrEGMbrBaseStQcDpdInPfPkts indicates the number of 
         in-profile packets dropped by the egress Qchip due to: SAP state, 
         gress MAC, IP or IPv6 filter, same segment discard, bad checksum, etc."
    ::= { sapEgrEGMbrBaseStEntry 3 }

sapEgrEGMbrBaseStQcDpdInPfPktsL OBJECT-TYPE
    SYNTAX          Counter32
    MAX-ACCESS      read-only
    STATUS          current
    DESCRIPTION
        "The value of sapEgrEGMbrBaseStQcDpdInPfPktsL indicates the lower 32 
         bits of the value of sapEgrEGMbrBaseStQcDpdInPfPkts."
    ::= { sapEgrEGMbrBaseStEntry 4 }

sapEgrEGMbrBaseStQcDpdInPfPktsH OBJECT-TYPE
    SYNTAX          Counter32
    MAX-ACCESS      read-only
    STATUS          current
    DESCRIPTION
        "The value of sapEgrEGMbrBaseStQcDpdInPfPktsH indicates the higher 32 
         bits of the value of sapEgrEGMbrBaseStQcDpdInPfPkts."
    ::= { sapEgrEGMbrBaseStEntry 5 }

sapEgrEGMbrBaseStQcDpdInPfOcts OBJECT-TYPE
    SYNTAX          Counter64
    MAX-ACCESS      read-only
    STATUS          current
    DESCRIPTION     
        "The value of sapEgrEGMbrBaseStQcDpdInPfOcts indicates the number of 
         in-profile octets dropped by the egress Qchip due to: SAP state, egress
         MAC, IP or IPv6 filter, same segment discard, bad checksum, etc."
    ::= { sapEgrEGMbrBaseStEntry 6 }

sapEgrEGMbrBaseStQcDpdInPfOctsL OBJECT-TYPE
    SYNTAX          Counter32
    MAX-ACCESS      read-only
    STATUS          current
    DESCRIPTION
        "The value of sapEgrEGMbrBaseStQcDpdInPfOctsL indicates the lower 32 
         bits of the value of sapEgrEGMbrBaseStQcDpdInPfOcts."
    ::= { sapEgrEGMbrBaseStEntry 7 }

sapEgrEGMbrBaseStQcDpdInPfOctsH OBJECT-TYPE
    SYNTAX          Counter32
    MAX-ACCESS      read-only
    STATUS          current
    DESCRIPTION
        "The value of sapEgrEGMbrBaseStQcDpdInPfOctsH indicates the higher 32 
         bits of the value of sapEgrEGMbrBaseStQcDpdInPfOcts."
    ::= { sapEgrEGMbrBaseStEntry 8 }

sapEgrEGMbrBaseStQcDpdOutPfPkts OBJECT-TYPE
    SYNTAX          Counter64
    MAX-ACCESS      read-only
    STATUS          current
    DESCRIPTION
        "The value of sapEgrEGMbrBaseStQcDpdOutPfPkts indicates the number of 
         out-of-profile packets discarded by the egress Qchip due to: 
         MBS exceeded, buffer pool limit exceeded, etc."
    ::= { sapEgrEGMbrBaseStEntry 9 }

sapEgrEGMbrBaseStQcDpdOutPfPktsL OBJECT-TYPE
    SYNTAX          Counter32
    MAX-ACCESS      read-only
    STATUS          current
    DESCRIPTION
        "The value of sapEgrEGMbrBaseStQcDpdOutPfPktsL indicates the lower 32 
         bits of the value of sapEgrEGMbrBaseStQcDpdOutPfPkts."
    ::= { sapEgrEGMbrBaseStEntry 10 }

sapEgrEGMbrBaseStQcDpdOutPfPktsH OBJECT-TYPE
    SYNTAX          Counter32
    MAX-ACCESS      read-only
    STATUS          current
    DESCRIPTION
        "The value of sapEgrEGMbrBaseStQcDpdOutPfPktsH indicates the higher 32 
         bits of the value of sapEgrEGMbrBaseStQcDpdOutPfPkts."
    ::= { sapEgrEGMbrBaseStEntry 11 }

sapEgrEGMbrBaseStQcDpdOutPfOcts OBJECT-TYPE
    SYNTAX          Counter64
    MAX-ACCESS      read-only
    STATUS          current
    DESCRIPTION     
        "The value of sapEgrEGMbrBaseStQcDpdOutPfOcts indicates the number of 
         out-of-profile octets discarded by the egress Qchip due to: 
         MBS exceeded, buffer pool limit exceeded, etc."
    ::= { sapEgrEGMbrBaseStEntry 12 }

sapEgrEGMbrBaseStQcDpdOutPfOctsL OBJECT-TYPE
    SYNTAX          Counter32
    MAX-ACCESS      read-only
    STATUS          current
    DESCRIPTION
        "The value of sapEgrEGMbrBaseStQcDpdOutPfOctsL indicates the lower 32 
         bits of the value of sapEgrEGMbrBaseStQcDpdOutPfOcts."
    ::= { sapEgrEGMbrBaseStEntry 13 }

sapEgrEGMbrBaseStQcDpdOutPfOctsH OBJECT-TYPE
    SYNTAX          Counter32
    MAX-ACCESS      read-only
    STATUS          current
    DESCRIPTION
        "The value of sapEgrEGMbrBaseStQcDpdOutPfOctsL indicates the higher 32
         bits of the value of sapEgrEGMbrBaseStQcDpdOutPfOcts."
    ::= { sapEgrEGMbrBaseStEntry 14 }

sapEgrEGMbrBaseStQcFwdInPfPkts OBJECT-TYPE
    SYNTAX          Counter64
    MAX-ACCESS      read-only
    STATUS          current
    DESCRIPTION
        "The value of sapEgrEGMbrBaseStQcFwdInPfPkts indicates the number of 
         in-profile packets (rate below CIR) forwarded by the egress Qchip."
    ::= { sapEgrEGMbrBaseStEntry 15 }

sapEgrEGMbrBaseStQcFwdInPfPktsL OBJECT-TYPE
    SYNTAX          Counter32
    MAX-ACCESS      read-only
    STATUS          current
    DESCRIPTION
        "The value of sapEgrEGMbrBaseStQcFwdInPfPktsL indicates the lower 32 
         bits of the value of sapEgrEGMbrBaseStQcFwdInPfPkts."
    ::= { sapEgrEGMbrBaseStEntry 16 }

sapEgrEGMbrBaseStQcFwdInPfPktsH OBJECT-TYPE
    SYNTAX          Counter32
    MAX-ACCESS      read-only
    STATUS          current
    DESCRIPTION
        "The value of sapEgrEGMbrBaseStQcFwdInPfPktsH indicates the higher 32 
         bits of the value of sapEgrEGMbrBaseStQcFwdInPfPkts."
    ::= { sapEgrEGMbrBaseStEntry 17 }

sapEgrEGMbrBaseStQcFwdInPfOcts OBJECT-TYPE
    SYNTAX          Counter64
    MAX-ACCESS      read-only
    STATUS          current
    DESCRIPTION
        "The value of sapEgrEGMbrBaseStQcFwdInPfOcts indicates the number of 
         in-profile octets (rate below CIR) forwarded by the egress Qchip."
    ::= { sapEgrEGMbrBaseStEntry 18 }

sapEgrEGMbrBaseStQcFwdInPfOctsL OBJECT-TYPE
    SYNTAX          Counter32
    MAX-ACCESS      read-only
    STATUS          current
    DESCRIPTION
        "The value of sapEgrEGMbrBaseStQcFwdInPfOctsL indicates the lower 32 
         bits of the value of sapEgrEGMbrBaseStQcFwdInPfOcts."
    ::= { sapEgrEGMbrBaseStEntry 19 }

sapEgrEGMbrBaseStQcFwdInPfOctsH OBJECT-TYPE
    SYNTAX          Counter32
    MAX-ACCESS      read-only
    STATUS          current
    DESCRIPTION
        "The value of sapEgrEGMbrBaseStQcFwdInPfOctsH indicates the higher 32 
         bits of the value of sapEgrEGMbrBaseStQcFwdInPfOcts."
    ::= { sapEgrEGMbrBaseStEntry 20 }

sapEgrEGMbrBaseStQcFwdOutPfPkts OBJECT-TYPE
    SYNTAX          Counter64
    MAX-ACCESS      read-only
    STATUS          current
    DESCRIPTION
        "The value of sapEgrEGMbrBaseStQcFwdOutPfPkts indicates the number of 
         out-of-profile packets (rate above CIR) forwarded by the egress Qchip."
    ::= { sapEgrEGMbrBaseStEntry 21 }

sapEgrEGMbrBaseStQcFwdOutPfPktsL OBJECT-TYPE
    SYNTAX          Counter32
    MAX-ACCESS      read-only
    STATUS          current
    DESCRIPTION
        "The value of sapEgrEGMbrBaseStQcFwdOutPfPktsL indicates the lower 32
         bits of the value of sapEgrEGMbrBaseStQcFwdOutPfPkts."
    ::= { sapEgrEGMbrBaseStEntry 22 }

sapEgrEGMbrBaseStQcFwdOutPfPktsH OBJECT-TYPE
    SYNTAX          Counter32
    MAX-ACCESS      read-only
    STATUS          current
    DESCRIPTION
        "The value of sapEgrEGMbrBaseStQcFwdOutPfPktsH indicates the higher 32
         bits of the value of sapEgrEGMbrBaseStQcFwdOutPfPkts."
    ::= { sapEgrEGMbrBaseStEntry 23 }

sapEgrEGMbrBaseStQcFwdOutPfOcts OBJECT-TYPE
    SYNTAX          Counter64
    MAX-ACCESS      read-only
    STATUS          current
    DESCRIPTION     
        "The value of sapEgrEGMbrBaseStQcFwdOutPfOcts indicates the number of 
         out-of-profile octets (rate above CIR) forwarded by the egress Qchip."
    ::= { sapEgrEGMbrBaseStEntry 24 }

sapEgrEGMbrBaseStQcFwdOutPfOctsL OBJECT-TYPE
    SYNTAX          Counter32
    MAX-ACCESS      read-only
    STATUS          current
    DESCRIPTION     
        "The value of sapEgrEGMbrBaseStQcFwdOutPfOctsL indicates the lower 32
         bits of the value of sapEgrEGMbrBaseStQcFwdOutPfOcts."
    ::= { sapEgrEGMbrBaseStEntry 25 }

sapEgrEGMbrBaseStQcFwdOutPfOctsH OBJECT-TYPE
    SYNTAX          Counter32
    MAX-ACCESS      read-only
    STATUS          current
    DESCRIPTION
        "The value of sapEgrEGMbrBaseStQcFwdOutPfOctsH indicates the higher 32
         bits of the value of sapEgrEGMbrBaseStQcFwdOutPfOcts."
    ::= { sapEgrEGMbrBaseStEntry 26 }

-- --------------------------------------------------
-- SAP egress QOS encapsulation group queue stats table
-- --------------------------------------------------
sapEgrEGQueueStTable OBJECT-TYPE
    SYNTAX          SEQUENCE OF SapEgrEGQueueStEntry
    MAX-ACCESS      not-accessible
    STATUS          current
    DESCRIPTION
        "The sapEgrEGQueueStTable contains egress Encap Group queue statistics
         at the Group level. This statistics table is valid for Encap Groups 
         created without enabling sapEgrEncapGroupQosPerMember."
    ::= { tmnxSapObjs 131 }
        
sapEgrEGQueueStEntry OBJECT-TYPE
    SYNTAX          SapEgrEGQueueStEntry
    MAX-ACCESS      not-accessible
    STATUS          current
    DESCRIPTION
        "Egress QoS queue statistics about a specific Encap group of a SAP."
    INDEX           { svcId, sapPortId, sapEncapValue, sapEgrEncapGroupName,
                      sapEgrEGQueueId }
    ::= { sapEgrEGQueueStTable 1 }

SapEgrEGQueueStEntry ::=
    SEQUENCE {
        sapEgrEGQueueId                 TSapEgrQueueId,
        sapEgrEGCustId                  TmnxCustId,
        sapEgrEGQueueStFwdInPfPkts      Counter64,
        sapEgrEGQueueStFwdInPfPktsL     Counter32,
        sapEgrEGQueueStFwdInPfPktsH     Counter32,
        sapEgrEGQueueStDpdInPfPkts      Counter64,
        sapEgrEGQueueStDpdInPfPktsL     Counter32,
        sapEgrEGQueueStDpdInPfPktsH     Counter32,
        sapEgrEGQueueStFwdOutPfPkts     Counter64,
        sapEgrEGQueueStFwdOutPfPktsL    Counter32,
        sapEgrEGQueueStFwdOutPfPktsH    Counter32,
        sapEgrEGQueueStDpdOutPfPkts     Counter64,
        sapEgrEGQueueStDpdOutPfPktsL    Counter32,
        sapEgrEGQueueStDpdOutPfPktsH    Counter32,
        sapEgrEGQueueStFwdInPfOcts      Counter64,
        sapEgrEGQueueStFwdInPfOctsL     Counter32,
        sapEgrEGQueueStFwdInPfOctsH     Counter32,
        sapEgrEGQueueStDpdInPfOcts      Counter64,
        sapEgrEGQueueStDpdInPfOctsL     Counter32,
        sapEgrEGQueueStDpdInPfOctsH     Counter32,
        sapEgrEGQueueStFwdOutPfOcts     Counter64,
        sapEgrEGQueueStFwdOutPfOctsL    Counter32,
        sapEgrEGQueueStFwdOutPfOctsH    Counter32,
        sapEgrEGQueueStDpdOutPfOcts     Counter64,
        sapEgrEGQueueStDpdOutPfOctsL    Counter32,
        sapEgrEGQueueStDpdOutPfOctsH    Counter32
    }

sapEgrEGQueueId OBJECT-TYPE
    SYNTAX          TSapEgrQueueId
    MAX-ACCESS      not-accessible
    STATUS          current
    DESCRIPTION
        "The value of sapEgrEGQueueId indicates the index of the egress QoS 
         queue of this SAP."
    ::= { sapEgrEGQueueStEntry 1 }

sapEgrEGCustId OBJECT-TYPE
    SYNTAX          TmnxCustId
    MAX-ACCESS      read-only
    STATUS          current
    DESCRIPTION
        "The value of sapEgrEGCustId indicates the Customer ID for the 
         associated service."
    ::= { sapEgrEGQueueStEntry 2 }

sapEgrEGQueueStFwdInPfPkts OBJECT-TYPE
    SYNTAX          Counter64
    MAX-ACCESS      read-only
    STATUS          current
    DESCRIPTION     
        "The value of sapEgrEGQueueStFwdInPfPkts indicates the number of 
         in-profile packets (rate below CIR) forwarded by the egress queue."
    ::= { sapEgrEGQueueStEntry 3 }

sapEgrEGQueueStFwdInPfPktsL OBJECT-TYPE
    SYNTAX          Counter32
    MAX-ACCESS      read-only
    STATUS          current
    DESCRIPTION
        "The value of sapEgrEGQueueStFwdInPfPktsL indicates the lower 32 bits of
         the value of sapEgrEGQueueStFwdInPfPkts."
    ::= { sapEgrEGQueueStEntry 4 }

sapEgrEGQueueStFwdInPfPktsH OBJECT-TYPE
    SYNTAX          Counter32
    MAX-ACCESS      read-only
    STATUS          current
    DESCRIPTION
        "The value of sapEgrEGQueueStFwdInPfPktsL indicates the higher 32 bits 
         of the value of sapEgrEGQueueStFwdInPfPkts."
    ::= { sapEgrEGQueueStEntry 5 }

sapEgrEGQueueStDpdInPfPkts OBJECT-TYPE
    SYNTAX          Counter64
    MAX-ACCESS      read-only
    STATUS          current
    DESCRIPTION
        "The value of sapEgrEGQueueStDpdInPfPkts indicates the number of 
         in-profile packets discarded by the egress Queue due to: MBS exceeded,
         buffer pool limit exceeded etc."
    ::= { sapEgrEGQueueStEntry 6 }

sapEgrEGQueueStDpdInPfPktsL OBJECT-TYPE
    SYNTAX          Counter32
    MAX-ACCESS      read-only
    STATUS          current
    DESCRIPTION
        "The value of sapEgrEGQueueStDpdInPfPktsL indicates the lower 32 bits of
         the value of sapEgrEGQueueStDpdInPfPkts."
    ::= { sapEgrEGQueueStEntry 7 }

sapEgrEGQueueStDpdInPfPktsH OBJECT-TYPE
    SYNTAX          Counter32
    MAX-ACCESS      read-only
    STATUS          current
    DESCRIPTION
        "The value of sapEgrEGQueueStDpdInPfPktsH indicates the higher 32 bits
         of the value of sapEgrEGQueueStDpdInPfPkts."
    ::= { sapEgrEGQueueStEntry 8 }

sapEgrEGQueueStFwdOutPfPkts OBJECT-TYPE
    SYNTAX          Counter64
    MAX-ACCESS      read-only
    STATUS          current
    DESCRIPTION
        "The value of sapEgrEGQueueStFwdOutPfPkts indicates the number of 
         out-of-profile packets (rate above CIR) forwarded by the egress queue."
    ::= { sapEgrEGQueueStEntry 9 }

sapEgrEGQueueStFwdOutPfPktsL OBJECT-TYPE
    SYNTAX          Counter32
    MAX-ACCESS      read-only
    STATUS          current
    DESCRIPTION
        "The value of sapEgrEGQueueStFwdOutPfPktsL indicates the lower 32 bits
         of the value of sapEgrEGQueueStFwdOutPfPkts."
    ::= { sapEgrEGQueueStEntry 10 }

sapEgrEGQueueStFwdOutPfPktsH OBJECT-TYPE
    SYNTAX          Counter32
    MAX-ACCESS      read-only
    STATUS          current
    DESCRIPTION
        "The value of sapEgrEGQueueStFwdOutPfPktsH indicates the higher 32 bits
         of the value of sapEgrEGQueueStFwdOutPfPkts."
    ::= { sapEgrEGQueueStEntry 11 }

sapEgrEGQueueStDpdOutPfPkts OBJECT-TYPE
    SYNTAX          Counter64
    MAX-ACCESS      read-only
    STATUS          current
    DESCRIPTION
        "The value of sapEgrEGQueueStDpdOutPfPkts indicates the number of 
         out-of-profile packets discarded by the egress queue due to: 
         MBS exceeded, buffer pool limit exceeded etc."
    ::= { sapEgrEGQueueStEntry 12 }

sapEgrEGQueueStDpdOutPfPktsL OBJECT-TYPE
    SYNTAX          Counter32
    MAX-ACCESS      read-only
    STATUS          current
    DESCRIPTION
        "The value of sapEgrEGQueueStDpdOutPfPktsL indicates the lower 32 bits
         of the value of sapEgrEGQueueStDpdOutPfPkts."
    ::= { sapEgrEGQueueStEntry 13 }

sapEgrEGQueueStDpdOutPfPktsH OBJECT-TYPE
    SYNTAX          Counter32
    MAX-ACCESS      read-only
    STATUS          current
    DESCRIPTION
        "The value of sapEgrEGQueueStDpdOutPfPktsH indicates the higher 32 bits
         of the value of sapEgrEGQueueStDpdOutPfPkts."
    ::= { sapEgrEGQueueStEntry 14 }

sapEgrEGQueueStFwdInPfOcts OBJECT-TYPE
    SYNTAX          Counter64
    MAX-ACCESS      read-only
    STATUS          current
    DESCRIPTION
        "The value of sapEgrEGQueueStFwdInPfOcts indicates the number of 
         in-profile octets (rate below CIR) forwarded by the egress queue."
    ::= { sapEgrEGQueueStEntry 15 }

sapEgrEGQueueStFwdInPfOctsL OBJECT-TYPE
    SYNTAX          Counter32
    MAX-ACCESS      read-only
    STATUS          current
    DESCRIPTION
        "The value of sapEgrEGQueueStFwdInPfOctsL indicates the lower 32 bits of
         the value of sapEgrEGQueueStFwdInPfOcts."
    ::= { sapEgrEGQueueStEntry 16 }

sapEgrEGQueueStFwdInPfOctsH OBJECT-TYPE
    SYNTAX          Counter32
    MAX-ACCESS      read-only
    STATUS          current
    DESCRIPTION
        "The value of sapEgrEGQueueStFwdInPfOctsH indicates the higher 32 bits
         of the value of sapEgrEGQueueStFwdInPfOcts."
    ::= { sapEgrEGQueueStEntry 17 }

sapEgrEGQueueStDpdInPfOcts OBJECT-TYPE
    SYNTAX          Counter64
    MAX-ACCESS      read-only
    STATUS          current
    DESCRIPTION
        "The value of sapEgrEGQueueStDpdInPfOcts indicates the number of 
         in-profile octets discarded by the egress queue due to: MBS exceeded,
         buffer pool limit exceeded etc."
    ::= { sapEgrEGQueueStEntry 18 }

sapEgrEGQueueStDpdInPfOctsL OBJECT-TYPE
    SYNTAX          Counter32
    MAX-ACCESS      read-only
    STATUS          current
    DESCRIPTION
        "The value of sapEgrEGQueueStDpdInPfOctsL indicates the lower 32 bits of
         the value of sapEgrEGQueueStDpdInPfOcts."
    ::= { sapEgrEGQueueStEntry 19 }

sapEgrEGQueueStDpdInPfOctsH OBJECT-TYPE
    SYNTAX          Counter32
    MAX-ACCESS      read-only
    STATUS          current
    DESCRIPTION
        "The value of sapEgrEGQueueStDpdInPfOctsH indicates the higher 32 bits 
         of the value of sapEgrEGQueueStDpdInPfOcts."
    ::= { sapEgrEGQueueStEntry 20 }

sapEgrEGQueueStFwdOutPfOcts OBJECT-TYPE
    SYNTAX          Counter64
    MAX-ACCESS      read-only
    STATUS          current
    DESCRIPTION
        "The value of sapEgrEGQueueStFwdOutPfOcts indicates the number of 
         out-of-profile octets (rate above CIR) forwarded by the egress queue."
    ::= { sapEgrEGQueueStEntry 21 }

sapEgrEGQueueStFwdOutPfOctsL OBJECT-TYPE
    SYNTAX          Counter32
    MAX-ACCESS      read-only
    STATUS          current
    DESCRIPTION
        "The value of sapEgrEGQueueStFwdOutPfOctsL indicates the lower 32 bits
         of the value of sapEgrEGQueueStFwdOutPfOcts."
    ::= { sapEgrEGQueueStEntry 22 }

sapEgrEGQueueStFwdOutPfOctsH OBJECT-TYPE
    SYNTAX          Counter32
    MAX-ACCESS      read-only
    STATUS          current
    DESCRIPTION
        "The value of sapEgrEGQueueStFwdOutPfOctsH indicates the higher 32 bits
         of the value of sapEgrEGQueueStFwdOutPfOcts."
    ::= { sapEgrEGQueueStEntry 23 }

sapEgrEGQueueStDpdOutPfOcts OBJECT-TYPE
    SYNTAX          Counter64
    MAX-ACCESS      read-only
    STATUS          current
    DESCRIPTION
        "The value of sapEgrEGQueueStDpdOutPfOcts indicates the number of 
         out-of-profile octets discarded by the egress queue due to: 
         MBS exceeded, buffer pool limit exceeded, etc."
    ::= { sapEgrEGQueueStEntry 24 }

sapEgrEGQueueStDpdOutPfOctsL OBJECT-TYPE
    SYNTAX          Counter32
    MAX-ACCESS      read-only
    STATUS          current
    DESCRIPTION
        "The value of sapEgrEGQueueStDpdOutPfOctsL indicates the lower 32 bits 
         of the value of sapEgrEGQueueStDpdOutPfOcts."
    ::= { sapEgrEGQueueStEntry 25 }

sapEgrEGQueueStDpdOutPfOctsH OBJECT-TYPE
    SYNTAX          Counter32
    MAX-ACCESS      read-only
    STATUS          current
    DESCRIPTION
        "The value of sapEgrEGQueueStDpdOutPfOctsH indicates the higher 32 bits
         of the value of sapEgrEGQueueStDpdOutPfOcts."
    ::= { sapEgrEGQueueStEntry 26 }

-- --------------------------------------------------
-- SAP egress encapsulation group queue per member stats table
-- --------------------------------------------------
sapEgrEGMbrQueueStTable OBJECT-TYPE
    SYNTAX          SEQUENCE OF SapEgrEGMbrQueueStEntry
    MAX-ACCESS      not-accessible
    STATUS          current
    DESCRIPTION
        "The sapEgrEGMbrQueueStTable contains egress Encap Group member queue
         statistics per member. This statistics table is valid for Encap Groups
         created by enabling sapEgrEncapGroupQosPerMember."
    ::= { tmnxSapObjs 132 }

sapEgrEGMbrQueueStEntry OBJECT-TYPE
    SYNTAX          SapEgrEGMbrQueueStEntry
    MAX-ACCESS      not-accessible
    STATUS          current
    DESCRIPTION
        "Egress QoS queue statistics about a specific Encap group member of a
         SAP."
    INDEX           { svcId, sapPortId, sapEncapValue, sapEgrEncapGroupName, 
                      sapEgrEncapGrpMember, sapEgrEGMbrQueueId }
    ::= { sapEgrEGMbrQueueStTable 1 }

SapEgrEGMbrQueueStEntry ::=
    SEQUENCE {
        sapEgrEGMbrQueueId                  TSapEgrQueueId,
        sapEgrEGMbrQueueCustId              TmnxCustId,
        sapEgrEGMbrQueueStFwdInPfPkts       Counter64,
        sapEgrEGMbrQueueStFwdInPfPktsL      Counter32,
        sapEgrEGMbrQueueStFwdInPfPktsH      Counter32,
        sapEgrEGMbrQueueStDpdInPfPkts       Counter64,
        sapEgrEGMbrQueueStDpdInPfPktsL      Counter32,
        sapEgrEGMbrQueueStDpdInPfPktsH      Counter32,
        sapEgrEGMbrQueueStFwdOutPfPkts      Counter64,
        sapEgrEGMbrQueueStFwdOutPfPktsL     Counter32,
        sapEgrEGMbrQueueStFwdOutPfPktsH     Counter32,
        sapEgrEGMbrQueueStDpdOutPfPkts      Counter64,
        sapEgrEGMbrQueueStDpdOutPfPktsL     Counter32,
        sapEgrEGMbrQueueStDpdOutPfPktsH     Counter32,
        sapEgrEGMbrQueueStFwdInPfOcts       Counter64,
        sapEgrEGMbrQueueStFwdInPfOctsL      Counter32,
        sapEgrEGMbrQueueStFwdInPfOctsH      Counter32,
        sapEgrEGMbrQueueStDpdInPfOcts       Counter64,
        sapEgrEGMbrQueueStDpdInPfOctsL      Counter32,
        sapEgrEGMbrQueueStDpdInPfOctsH      Counter32,
        sapEgrEGMbrQueueStFwdOutPfOcts      Counter64,
        sapEgrEGMbrQueueStFwdOutPfOctsL     Counter32,
        sapEgrEGMbrQueueStFwdOutPfOctsH     Counter32,
        sapEgrEGMbrQueueStDpdOutPfOcts      Counter64,
        sapEgrEGMbrQueueStDpdOutPfOctsL     Counter32,
        sapEgrEGMbrQueueStDpdOutPfOctsH     Counter32
    }

sapEgrEGMbrQueueId OBJECT-TYPE
    SYNTAX          TSapEgrQueueId
    MAX-ACCESS      not-accessible
    STATUS          current
    DESCRIPTION
        "The value of sapEgrEGMbrQueueId indicates the index of the egress QoS
         queue of this SAP."
    ::= { sapEgrEGMbrQueueStEntry 1 }

sapEgrEGMbrQueueCustId OBJECT-TYPE
    SYNTAX          TmnxCustId
    MAX-ACCESS      read-only
    STATUS          current
    DESCRIPTION
        "The value of sapEgrEGMbrQueueCustId indicates the Customer ID for the
         associated service."
    ::= { sapEgrEGMbrQueueStEntry 2 }

sapEgrEGMbrQueueStFwdInPfPkts OBJECT-TYPE
    SYNTAX          Counter64
    MAX-ACCESS      read-only
    STATUS          current
    DESCRIPTION
        "The value of sapEgrEGMbrQueueStFwdInPfPkts indicates the number of 
         in-profile packets (rate below CIR) forwarded by the egress queue."
    ::= { sapEgrEGMbrQueueStEntry 3 }

sapEgrEGMbrQueueStFwdInPfPktsL OBJECT-TYPE
    SYNTAX          Counter32
    MAX-ACCESS      read-only
    STATUS          current
    DESCRIPTION
        "The value of sapEgrEGMbrQueueStFwdInPfPktsL indicates the lower 32 bits
         of the value of sapEgrEGMbrQueueStFwdInPfPkts."
    ::= { sapEgrEGMbrQueueStEntry 4 }

sapEgrEGMbrQueueStFwdInPfPktsH OBJECT-TYPE
    SYNTAX          Counter32
    MAX-ACCESS      read-only
    STATUS          current
    DESCRIPTION
        "The value of sapEgrEGMbrQueueStFwdInPfPktsH indicates the higher 32 
         bits of the value of sapEgrEGMbrQueueStFwdInPfPkts."
    ::= { sapEgrEGMbrQueueStEntry 5 }

sapEgrEGMbrQueueStDpdInPfPkts OBJECT-TYPE
    SYNTAX          Counter64
    MAX-ACCESS      read-only
    STATUS          current
    DESCRIPTION
        "The value of sapEgrEGMbrQueueStDpdInPfPkts indicates the number of 
         in-profile packets discarded by the egress queue due to: MBS exceeded,
         buffer pool limit exceeded, etc."
    ::= { sapEgrEGMbrQueueStEntry 6 }

sapEgrEGMbrQueueStDpdInPfPktsL OBJECT-TYPE
    SYNTAX          Counter32
    MAX-ACCESS      read-only
    STATUS          current
    DESCRIPTION
        "The value of sapEgrEGMbrQueueStDpdInPfPktsL indicates the lower 32 bits
         of the value of  sapEgrEGMbrQueueStDpdInPfPkts."
    ::= { sapEgrEGMbrQueueStEntry 7 }

sapEgrEGMbrQueueStDpdInPfPktsH OBJECT-TYPE
    SYNTAX          Counter32
    MAX-ACCESS      read-only
    STATUS          current
    DESCRIPTION
        "The value of sapEgrEGMbrQueueStDpdInPfPktsH indicates the higher 32
         bits of the value of sapEgrEGMbrQueueStDpdInPfPkts."
    ::= { sapEgrEGMbrQueueStEntry 8 }

sapEgrEGMbrQueueStFwdOutPfPkts OBJECT-TYPE
    SYNTAX          Counter64
    MAX-ACCESS      read-only
    STATUS          current
    DESCRIPTION
        "The value of sapEgrEGMbrQueueStFwdOutPfPkts indicates the number of 
         out-of-profile packets (rate above CIR) forwarded by the egress queue."
    ::= { sapEgrEGMbrQueueStEntry 9 }

sapEgrEGMbrQueueStFwdOutPfPktsL OBJECT-TYPE
    SYNTAX          Counter32
    MAX-ACCESS      read-only
    STATUS          current
    DESCRIPTION
        "The value of sapEgrEGMbrQueueStFwdOutPfPktsL indicates the lower 32 
         bits of the value of sapEgrEGMbrQueueStFwdOutPfPkts."
    ::= { sapEgrEGMbrQueueStEntry 10 }

sapEgrEGMbrQueueStFwdOutPfPktsH OBJECT-TYPE
    SYNTAX          Counter32
    MAX-ACCESS      read-only
    STATUS          current
    DESCRIPTION
        "The value of sapEgrEGMbrQueueStFwdOutPfPktsH indicates the higher 32
         bits of the value of sapEgrEGMbrQueueStFwdOutPfPkts."
    ::= { sapEgrEGMbrQueueStEntry 11 }

sapEgrEGMbrQueueStDpdOutPfPkts OBJECT-TYPE
    SYNTAX          Counter64
    MAX-ACCESS      read-only
    STATUS          current
    DESCRIPTION
        "The value of sapEgrEGMbrQueueStDpdOutPfPkts indicates the number of 
         out-of-profile packets discarded by the egress queue due to: 
         MBS exceeded, buffer pool limit exceeded, etc."
    ::= { sapEgrEGMbrQueueStEntry 12 }

sapEgrEGMbrQueueStDpdOutPfPktsL OBJECT-TYPE
    SYNTAX          Counter32
    MAX-ACCESS      read-only
    STATUS          current
    DESCRIPTION
        "The value of sapEgrEGMbrQueueStDpdOutPfPktsL indicates the lower 32 
         bits of the value of sapEgrEGMbrQueueStDpdOutPfPkts."
    ::= { sapEgrEGMbrQueueStEntry 13 }

sapEgrEGMbrQueueStDpdOutPfPktsH OBJECT-TYPE
    SYNTAX          Counter32
    MAX-ACCESS      read-only
    STATUS          current
    DESCRIPTION
        "The value of sapEgrEGMbrQueueStDpdOutPfPktsH indicates the higher 32
         bits of the value of sapEgrEGMbrQueueStDpdOutPfPkts."
    ::= { sapEgrEGMbrQueueStEntry 14 }

sapEgrEGMbrQueueStFwdInPfOcts OBJECT-TYPE
    SYNTAX          Counter64
    MAX-ACCESS      read-only
    STATUS          current
    DESCRIPTION
        "The value of sapEgrEGMbrQueueStFwdInPfOcts indicates the number of 
         in-profile octets (rate below CIR) forwarded by the egress queue."
    ::= { sapEgrEGMbrQueueStEntry 15 }

sapEgrEGMbrQueueStFwdInPfOctsL OBJECT-TYPE
    SYNTAX          Counter32
    MAX-ACCESS      read-only
    STATUS          current
    DESCRIPTION
        "The value of sapEgrEGMbrQueueStFwdInPfOctsL indicates the lower 32 bits
         of the value of sapEgrEGMbrQueueStFwdInPfOcts."
    ::= { sapEgrEGMbrQueueStEntry 16 }

sapEgrEGMbrQueueStFwdInPfOctsH OBJECT-TYPE
    SYNTAX          Counter32
    MAX-ACCESS      read-only
    STATUS          current
    DESCRIPTION
        "The value of sapEgrEGMbrQueueStFwdInPfOctsH indicates the higher 32 
         bits of the value of sapEgrEGMbrQueueStFwdInPfOcts."
    ::= { sapEgrEGMbrQueueStEntry 17 }

sapEgrEGMbrQueueStDpdInPfOcts OBJECT-TYPE
    SYNTAX          Counter64
    MAX-ACCESS      read-only
    STATUS          current
    DESCRIPTION
        "The value of sapEgrEGMbrQueueStDpdInPfOcts indicates the number of 
         in-profile octets discarded by the egress queue due to: MBS exceeded,
         buffer pool limit exceeded, etc."
    ::= { sapEgrEGMbrQueueStEntry 18 }

sapEgrEGMbrQueueStDpdInPfOctsL OBJECT-TYPE
    SYNTAX          Counter32
    MAX-ACCESS      read-only
    STATUS          current
    DESCRIPTION
        "The value of sapEgrEGMbrQueueStDpdInPfOctsL indicates the lower 32 bits
         of the value of sapEgrEGMbrQueueStDpdInPfOcts."
    ::= { sapEgrEGMbrQueueStEntry 19 }

sapEgrEGMbrQueueStDpdInPfOctsH OBJECT-TYPE
    SYNTAX          Counter32
    MAX-ACCESS      read-only
    STATUS          current
    DESCRIPTION
        "The value of sapEgrEGMbrQueueStDpdInPfOctsH indicates the higher 32 
         bits of the value of sapEgrEGMbrQueueStDpdInPfOcts."
    ::= { sapEgrEGMbrQueueStEntry 20 }

sapEgrEGMbrQueueStFwdOutPfOcts OBJECT-TYPE
    SYNTAX          Counter64
    MAX-ACCESS      read-only
    STATUS          current
    DESCRIPTION
        "The value of sapEgrEGMbrQueueStFwdOutPfOcts indicates the number of 
         out-of-profile octets (rate above CIR) forwarded by the egress queue."
    ::= { sapEgrEGMbrQueueStEntry 21 }

sapEgrEGMbrQueueStFwdOutPfOctsL OBJECT-TYPE
    SYNTAX          Counter32
    MAX-ACCESS      read-only
    STATUS          current
    DESCRIPTION
        "The value of sapEgrEGMbrQueueStFwdOutPfOctsL indicates the lower 32 
         bits of the value of sapEgrEGMbrQueueStFwdOutPfOcts."
    ::= { sapEgrEGMbrQueueStEntry 22 }

sapEgrEGMbrQueueStFwdOutPfOctsH OBJECT-TYPE
    SYNTAX          Counter32
    MAX-ACCESS      read-only
    STATUS          current
    DESCRIPTION
        "The value of sapEgrEGMbrQueueStFwdOutPfOctsH indicates the higher 32
         bits of the value of sapEgrEGMbrQueueStFwdOutPfOcts."
    ::= { sapEgrEGMbrQueueStEntry 23 }

sapEgrEGMbrQueueStDpdOutPfOcts OBJECT-TYPE
    SYNTAX          Counter64
    MAX-ACCESS      read-only
    STATUS          current
    DESCRIPTION
        "The value of sapEgrEGMbrQueueStDpdOutPfOcts indicates the number of 
         out-of-profile octets discarded by the egress queue due to: 
         MBS exceeded, buffer pool limit exceeded, etc."
    ::= { sapEgrEGMbrQueueStEntry 24 }

sapEgrEGMbrQueueStDpdOutPfOctsL OBJECT-TYPE
    SYNTAX          Counter32
    MAX-ACCESS      read-only
    STATUS          current
    DESCRIPTION
        "The value of sapEgrEGMbrQueueStDpdOutPfOctsL indicates the lower 32
         bits of the value of sapEgrEGMbrQueueStDpdOutPfOcts."
    ::= { sapEgrEGMbrQueueStEntry 25 }

sapEgrEGMbrQueueStDpdOutPfOctsH OBJECT-TYPE
    SYNTAX          Counter32
    MAX-ACCESS      read-only
    STATUS          current
    DESCRIPTION
        "The value of sapEgrEGMbrQueueStDpdOutPfOctsH indicates the higher 32 
         bits of the value of sapEgrEGMbrQueueStDpdOutPfOcts."
    ::= { sapEgrEGMbrQueueStEntry 26 }

-- --------------------------------------------------
-- SAP egress encapsulation group scheduler stats table
-- --------------------------------------------------
sapEgrEGSchedStTable OBJECT-TYPE
    SYNTAX          SEQUENCE OF SapEgrEGSchedStEntry
    MAX-ACCESS      not-accessible
    STATUS          current
    DESCRIPTION
        "The sapEgrEGSchedStTable contains egress encapsulation group QoS 
         scheduler SAP at the Group level. This statistics table is valid for
         Encap Groups created without enabling sapEgrEncapGroupQosPerMember."
    ::= { tmnxSapObjs 133 }

sapEgrEGSchedStEntry OBJECT-TYPE
    SYNTAX          SapEgrEGSchedStEntry
    MAX-ACCESS      not-accessible
    STATUS          current
    DESCRIPTION
        "Egress statistics about a specific QoS scheduler instantiated per
         encapsulation group of SAP."
    INDEX           { svcId, sapPortId, sapEncapValue, sapEgrEncapGroupName, 
                      sapEgrEGSchedStName }
    ::= { sapEgrEGSchedStTable 1 }

SapEgrEGSchedStEntry ::=
    SEQUENCE {
        sapEgrEGSchedStName         TNamedItem,
        sapEgrEGSchedCustId         TmnxCustId,
        sapEgrEGSchedStFwdPkts      Counter64,
        sapEgrEGSchedStFwdPktsL     Counter32,
        sapEgrEGSchedStFwdPktsH     Counter32,
        sapEgrEGSchedStFwdOcts      Counter64,
        sapEgrEGSchedStFwdOctsL     Counter32,
        sapEgrEGSchedStFwdOctsH     Counter32
    }

sapEgrEGSchedStName OBJECT-TYPE
    SYNTAX          TNamedItem
    MAX-ACCESS      not-accessible
    STATUS          current
    DESCRIPTION
        "The sapEgrEGSchedStName specifies the name of the egress QoS scheduler
         of this SAP."
    ::= { sapEgrEGSchedStEntry 1 }

sapEgrEGSchedCustId OBJECT-TYPE
    SYNTAX          TmnxCustId
    MAX-ACCESS      read-only
    STATUS          current
    DESCRIPTION
        "The value of sapEgrEGSchedCustId indicates the Customer ID for the 
         associated service."
    ::= { sapEgrEGSchedStEntry 2 }

sapEgrEGSchedStFwdPkts OBJECT-TYPE
    SYNTAX          Counter64
    MAX-ACCESS      read-only
    STATUS          current
    DESCRIPTION
        "The value of sapEgrEGSchedStFwdPkts indicates thee number of packets 
         forwarded by the egress QoS scheduler of this SAP."
    ::= { sapEgrEGSchedStEntry 3 }

sapEgrEGSchedStFwdPktsL OBJECT-TYPE
    SYNTAX          Counter32
    MAX-ACCESS      read-only
    STATUS          current
    DESCRIPTION
        "The value of sapEgrEGSchedStFwdPktsL indicates the lower 32 bits of the
         value of sapEgrEGSchedStFwdPkts."
    ::= { sapEgrEGSchedStEntry 4 }

sapEgrEGSchedStFwdPktsH OBJECT-TYPE
    SYNTAX          Counter32
    MAX-ACCESS      read-only
    STATUS          current
    DESCRIPTION
        "The value of sapEgrEGSchedStFwdPktsH indicates the higher 32 bits of 
         the value of sapEgrEGSchedStFwdPkts."
    ::= { sapEgrEGSchedStEntry 5 }

sapEgrEGSchedStFwdOcts OBJECT-TYPE
    SYNTAX          Counter64
    MAX-ACCESS      read-only
    STATUS          current
    DESCRIPTION
        "The value of sapEgrEGSchedStFwdOcts indicates the number of octets 
         forwarded by the egress QoS scheduler of this SAP."
    ::= { sapEgrEGSchedStEntry 6 }

sapEgrEGSchedStFwdOctsL OBJECT-TYPE
    SYNTAX          Counter32
    MAX-ACCESS      read-only
    STATUS          current
    DESCRIPTION
        "The value of sapEgrEGSchedStFwdOctsL indicates the lower 32 bits of the
         value of sapEgrEGSchedStFwdOcts."
    ::= { sapEgrEGSchedStEntry 7 }

sapEgrEGSchedStFwdOctsH OBJECT-TYPE
    SYNTAX          Counter32
    MAX-ACCESS      read-only
    STATUS          current
    DESCRIPTION
        "The value of sapEgrEGSchedStFwdOctsH indicates the higher 32 bits of
         the value of sapEgrEGSchedStFwdOcts."
    ::= { sapEgrEGSchedStEntry 8 }

-- --------------------------------------------------
-- SAP egress encapsulation group scheduler stats per member table
-- --------------------------------------------------
sapEgrEGMbrSchedStTable OBJECT-TYPE
    SYNTAX          SEQUENCE OF SapEgrEGMbrSchedStEntry
    MAX-ACCESS      not-accessible
    STATUS          current
    DESCRIPTION
        "The sapEgrEGMbrSchedStTable contains egress encapsulation group QoS 
         scheduler SAP per member. This statistics table is valid for Encap 
         Groups created by enabling sapEgrEncapGroupQosPerMember."
    ::= { tmnxSapObjs 134 }

sapEgrEGMbrSchedStEntry OBJECT-TYPE
    SYNTAX          SapEgrEGMbrSchedStEntry
    MAX-ACCESS      not-accessible
    STATUS          current
    DESCRIPTION
        "Egress statistics about a specific QoS scheduler instantiated per
         encapsulation group member of SAP."
    INDEX           { svcId, sapPortId, sapEncapValue, sapEgrEncapGroupName,    
                      sapEgrEncapGrpMember, sapEgrEGMbrSchedStName }
    ::= { sapEgrEGMbrSchedStTable 1 }

SapEgrEGMbrSchedStEntry ::=
    SEQUENCE {
        sapEgrEGMbrSchedStName                   TNamedItem,
        sapEgrEGMbrSchedCustId                   TmnxCustId,
        sapEgrEGMbrSchedStFwdPkts                Counter64,
        sapEgrEGMbrSchedStFwdPktsL               Counter32,
        sapEgrEGMbrSchedStFwdPktsH               Counter32,
        sapEgrEGMbrSchedStFwdOcts                Counter64,
        sapEgrEGMbrSchedStFwdOctsL               Counter32,
        sapEgrEGMbrSchedStFwdOctsH               Counter32
    }

sapEgrEGMbrSchedStName OBJECT-TYPE
    SYNTAX          TNamedItem
    MAX-ACCESS      not-accessible
    STATUS          current
    DESCRIPTION
        "The sapEgrEGMbrSchedStName specifies the name of the egress QoS 
         scheduler of this SAP."
    ::= { sapEgrEGMbrSchedStEntry 1 }

sapEgrEGMbrSchedCustId OBJECT-TYPE
    SYNTAX          TmnxCustId
    MAX-ACCESS      read-only
    STATUS          current
    DESCRIPTION
        "The value of sapEgrEGMbrSchedCustId indicates the Customer ID for the
         associated service."
    ::= { sapEgrEGMbrSchedStEntry 2 }

sapEgrEGMbrSchedStFwdPkts OBJECT-TYPE
    SYNTAX          Counter64
    MAX-ACCESS      read-only
    STATUS          current
    DESCRIPTION
        "The value of sapEgrEGMbrSchedStFwdPkts indicates the number of packets
         forwarded by the egress QoS scheduler of this SAP."
    ::= { sapEgrEGMbrSchedStEntry 3 }

sapEgrEGMbrSchedStFwdPktsL OBJECT-TYPE
    SYNTAX          Counter32
    MAX-ACCESS      read-only
    STATUS          current
    DESCRIPTION
        "The value of sapEgrEGMbrSchedStFwdPktsL indicates the lower 32 bits of 
         the value of sapEgrEGMbrSchedStFwdPkts."
    ::= { sapEgrEGMbrSchedStEntry 4 }

sapEgrEGMbrSchedStFwdPktsH OBJECT-TYPE
    SYNTAX          Counter32
    MAX-ACCESS      read-only
    STATUS          current
    DESCRIPTION
        "The value of sapEgrEGMbrSchedStFwdPktsH indicates the higher 32 bits of
         the value of sapEgrEGMbrSchedStFwdPkts."
    ::= { sapEgrEGMbrSchedStEntry 5 }

sapEgrEGMbrSchedStFwdOcts OBJECT-TYPE
    SYNTAX          Counter64
    MAX-ACCESS      read-only
    STATUS          current
    DESCRIPTION
        "The value of sapEgrEGMbrSchedStFwdOcts indicates the number of octets
         forwarded by the egress QoS scheduler of this SAP."
    ::= { sapEgrEGMbrSchedStEntry 6 }

sapEgrEGMbrSchedStFwdOctsL OBJECT-TYPE
    SYNTAX          Counter32
    MAX-ACCESS      read-only
    STATUS          current
    DESCRIPTION
        "The value of sapEgrEGMbrSchedStFwdOctsL indicates the lower 32 bits of
         the value of sapEgrEGMbrSchedStFwdOcts."
    ::= { sapEgrEGMbrSchedStEntry 7 }

sapEgrEGMbrSchedStFwdOctsH OBJECT-TYPE
    SYNTAX          Counter32
    MAX-ACCESS      read-only
    STATUS          current
    DESCRIPTION
        "The value of sapEgrEGMbrSchedStFwdOctsH indicates the higher 32 bits of
         the value of sapEgrEGMbrSchedStFwdOcts."
    ::= { sapEgrEGMbrSchedStEntry 8 }

-- --------------------------------------------------
-- Egress Encap Group QoS Scheduler Statistics Table per port
-- --------------------------------------------------
sapPortIdEgrEGSchedStTable OBJECT-TYPE
    SYNTAX          SEQUENCE OF SapPortIdEgrEGSchedStEntry
    MAX-ACCESS      not-accessible
    STATUS          current
    DESCRIPTION
        "The sapPortIdEgrEGSchedStTable contains egress QoS scheduler SAP 
         statistics per port at the Group level. This statistics table is valid 
         for Encap Groups created without enabling sapEgrEncapGroupQosPerMember.
         This table is used when the encap group's SAP is a CCAG or LAG in 
         'link' mode or an APS."
    ::= { tmnxSapObjs 135 }

sapPortIdEgrEGSchedStEntry OBJECT-TYPE
    SYNTAX          SapPortIdEgrEGSchedStEntry
    MAX-ACCESS      not-accessible
    STATUS          current
    DESCRIPTION
        "Egress statistics about a specific Encap Group's QoS scheduler port
         of a SAP. Entries are created when a scheduler policy is applied to an
         Encap Group."
    INDEX           { svcId, sapPortId, sapEncapValue, sapEgrEncapGroupName,
                      sapPortIdEgrEGSchedStName, sapPortIdEgrPortId  }
    ::= { sapPortIdEgrEGSchedStTable 1 }

SapPortIdEgrEGSchedStEntry  ::=
    SEQUENCE {
        sapPortIdEgrEGSchedStName        TNamedItem,
        sapPortIdEgrEGSchedCustId        TmnxCustId,
        sapPortIdEgrEGSchedFwdPkts       Counter64,
        sapPortIdEgrEGSchedFwdPktsL      Counter32,
        sapPortIdEgrEGSchedFwdPktsH      Counter32,
        sapPortIdEgrEGSchedFwdOcts       Counter64,
        sapPortIdEgrEGSchedFwdOctsL      Counter32,
        sapPortIdEgrEGSchedFwdOctsH      Counter32
    }

sapPortIdEgrEGSchedStName OBJECT-TYPE
    SYNTAX          TNamedItem
    MAX-ACCESS      not-accessible
    STATUS          current
    DESCRIPTION
        "The sapPortIdEgrEGSchedStName specifies the name of the egress 
         encapsulation group port scheduler of this SAP."
    ::= { sapPortIdEgrEGSchedStEntry 1 }

sapPortIdEgrEGSchedCustId OBJECT-TYPE
    SYNTAX          TmnxCustId
    MAX-ACCESS      read-only
    STATUS          current
    DESCRIPTION
        "The value of sapPortIdEgrEGSchedCustId indicates the Customer ID for 
         the associated service."
    ::= { sapPortIdEgrEGSchedStEntry 2 }

sapPortIdEgrEGSchedFwdPkts OBJECT-TYPE
    SYNTAX          Counter64
    MAX-ACCESS      read-only
    STATUS          current
    DESCRIPTION
        "The value of sapPortIdEgrEGSchedFwdPkts indicates the number of packets
         forwarded by the egress port scheduler of this SAP."
    ::= { sapPortIdEgrEGSchedStEntry 3 }

sapPortIdEgrEGSchedFwdPktsL OBJECT-TYPE
    SYNTAX          Counter32
    MAX-ACCESS      read-only
    STATUS          current
    DESCRIPTION
        "The value of sapPortIdEgrEGSchedFwdPktsL indicates the lower 32 bits of
         the value of sapPortIdEgrEGSchedFwdPkts."
    ::= { sapPortIdEgrEGSchedStEntry 4 }

sapPortIdEgrEGSchedFwdPktsH OBJECT-TYPE
    SYNTAX          Counter32
    MAX-ACCESS      read-only
    STATUS          current
    DESCRIPTION
        "The value sapPortIdEgrEGSchedFwdPktsH indicates the higher 32 bits of
         the value of sapPortIdEgrEGSchedFwdPkts."
    ::= { sapPortIdEgrEGSchedStEntry 5 }

sapPortIdEgrEGSchedFwdOcts OBJECT-TYPE
    SYNTAX          Counter64
    MAX-ACCESS      read-only
    STATUS          current
    DESCRIPTION
        "The value sapPortIdEgrEGSchedFwdOcts indicates the number of octets 
         forwarded by the egress port scheduler of this SAP."
    ::= { sapPortIdEgrEGSchedStEntry 6 }

sapPortIdEgrEGSchedFwdOctsL OBJECT-TYPE
    SYNTAX          Counter32
    MAX-ACCESS      read-only
    STATUS          current
    DESCRIPTION
        "The value of sapPortIdEgrEGSchedFwdOctsL indicates the lower 32 bits of
         the value of sapPortIdEgrEGSchedFwdOcts."
    ::= { sapPortIdEgrEGSchedStEntry 7 }

sapPortIdEgrEGSchedFwdOctsH OBJECT-TYPE
    SYNTAX          Counter32
    MAX-ACCESS      read-only
    STATUS          current
    DESCRIPTION
        "The value sapPortIdEgrEGSchedFwdOctsH indicates the higher 32 bits of 
         the value of sapPortIdEgrEGSchedFwdOcts."
    ::= { sapPortIdEgrEGSchedStEntry 8 }

-- --------------------------------------------------
-- Egress Encap Group Member QoS Scheduler Statistics Table per port
-- --------------------------------------------------
sapPortIdEgrEGMbrSchedStTable OBJECT-TYPE
    SYNTAX          SEQUENCE OF SapPortIdEgrEGMbrSchedStEntry 
    MAX-ACCESS      not-accessible
    STATUS          current
    DESCRIPTION
        "The sapPortIdEgrEGMbrSchedStTable contains egress QoS scheduler SAP 
         statistics per port. This statistics table is valid for Encap Groups 
         created by enabling sapEgrEncapGroupQosPerMember. This table fetches 
         statistics  per member. This table is used when the Encap Group's SAP
         is a CCAG or LAG in 'link' mode or an APS."
    ::= { tmnxSapObjs 136 }

sapPortIdEgrEGMbrSchedStEntry  OBJECT-TYPE
    SYNTAX          SapPortIdEgrEGMbrSchedStEntry 
    MAX-ACCESS      not-accessible
    STATUS          current
    DESCRIPTION
        "Egress statistics about a specific Encap Group member QoS scheduler 
         port of a SAP. Entries are created when a scheduler policy is applied
         to an Encap Group."
    INDEX           { svcId, sapPortId, sapEncapValue, sapEgrEncapGroupName,
                      sapEgrEncapGrpMember, sapPortIdEgrEGMbrSchedStName,
                      sapPortIdEgrPortId }
    ::= { sapPortIdEgrEGMbrSchedStTable 1 }

SapPortIdEgrEGMbrSchedStEntry   ::=
    SEQUENCE {
        sapPortIdEgrEGMbrSchedStName     TNamedItem,
        sapPortIdEgrEGMbrSchedCustId     TmnxCustId,
        sapPortIdEgrEGMbrSchedFwdPkts    Counter64,
        sapPortIdEgrEGMbrSchedFwdPktsL   Counter32,
        sapPortIdEgrEGMbrSchedFwdPktsH   Counter32,   
        sapPortIdEgrEGMbrSchedFwdOcts    Counter64,
        sapPortIdEgrEGMbrSchedFwdOctsL   Counter32,
        sapPortIdEgrEGMbrSchedFwdOctsH   Counter32
    }

sapPortIdEgrEGMbrSchedStName OBJECT-TYPE
    SYNTAX          TNamedItem
    MAX-ACCESS      not-accessible
    STATUS          current
    DESCRIPTION
        "The sapPortIdEgrEGMbrSchedStName specifies the name of the egress
         encapsulation group QOS port scheduler of this SAP."
    ::= { sapPortIdEgrEGMbrSchedStEntry 1 }

sapPortIdEgrEGMbrSchedCustId OBJECT-TYPE
    SYNTAX          TmnxCustId
    MAX-ACCESS      read-only
    STATUS          current
    DESCRIPTION
        "The value of sapPortIdEgrEGMbrSchedCustId indicates the Customer ID for
         the associated service."
    ::= { sapPortIdEgrEGMbrSchedStEntry 2 }

sapPortIdEgrEGMbrSchedFwdPkts OBJECT-TYPE
    SYNTAX          Counter64
    MAX-ACCESS      read-only
    STATUS          current
    DESCRIPTION
        "The value of sapPortIdEgrEGMbrSchedFwdPkts indicates the number of 
         packets forwarded by the egress port scheduler of this SAP."
    ::= { sapPortIdEgrEGMbrSchedStEntry 3 }

sapPortIdEgrEGMbrSchedFwdPktsL OBJECT-TYPE
    SYNTAX          Counter32
    MAX-ACCESS      read-only
    STATUS          current
    DESCRIPTION
        "The value of sapPortIdEgrEGMbrSchedFwdPktsL indicates the lower 32 bits
         of the value of sapPortIdEgrEGMbrSchedFwdPkts."
    ::= { sapPortIdEgrEGMbrSchedStEntry 4 }

sapPortIdEgrEGMbrSchedFwdPktsH OBJECT-TYPE
    SYNTAX          Counter32
    MAX-ACCESS      read-only
    STATUS          current
    DESCRIPTION
        "The value sapPortIdEgrEGMbrSchedFwdPktsH indicates the higher 32 bits
         of the value of sapPortIdEgrEGMbrSchedFwdPkts."
    ::= { sapPortIdEgrEGMbrSchedStEntry 5 }

sapPortIdEgrEGMbrSchedFwdOcts OBJECT-TYPE
    SYNTAX          Counter64
    MAX-ACCESS      read-only
    STATUS          current
    DESCRIPTION
        "The value sapPortIdEgrEGMbrSchedFwdOcts indicates the number of octets
         forwarded by the egress port scheduler of this SAP."
    ::= { sapPortIdEgrEGMbrSchedStEntry 6 }

sapPortIdEgrEGMbrSchedFwdOctsL OBJECT-TYPE
    SYNTAX          Counter32
    MAX-ACCESS      read-only
    STATUS          current
    DESCRIPTION
        "The value of sapPortIdEgrEGMbrSchedFwdOctsL indicates the lower 32 bits
         of the value of sapPortIdEgrEGMbrSchedFwdOcts."
    ::= { sapPortIdEgrEGMbrSchedStEntry 7 }

sapPortIdEgrEGMbrSchedFwdOctsH OBJECT-TYPE
    SYNTAX          Counter32
    MAX-ACCESS      read-only
    STATUS          current
    DESCRIPTION
        "The value sapPortIdEgrEGMbrSchedFwdOctsH indicates the higher 32 bits 
         of the value of sapPortIdEgrEGMbrSchedFwdOcts."
    ::= { sapPortIdEgrEGMbrSchedStEntry 8 }

-- --------------------------------------------------
-- Default host SAP table
-- --------------------------------------------------
sapDefHostTableLastChanged OBJECT-TYPE
    SYNTAX       TimeStamp
    MAX-ACCESS   read-only
    STATUS       current
    DESCRIPTION
        "The value of the object sapDefHostTableLastChanged indicates
         the value of sysUpTime at the time of the last modification of
         an conceptual row in the sapDefHostTable."
    ::= { tmnxSapObjs 137 }

sapDefHostTable OBJECT-TYPE
    SYNTAX          SEQUENCE OF SapDefHostEntry 
    MAX-ACCESS      not-accessible
    STATUS          current
    DESCRIPTION
        "A table that contains SAP default host information.
        
         Entries in this table can be created or deleted via SNMP operations.
    
         A row in this table can only be created for a SAP in a group interface, 
         that is each row in the sapBaseInfoTable where the value of 
         sapIesIfIndex corresponds to a row in the vRtrIfTable
         where the value of vRtrIfType is equal to 'serviceIesGroup' 
         or 'serviceVprnGroup'."
    ::= { tmnxSapObjs 138 }

sapDefHostEntry  OBJECT-TYPE
    SYNTAX          SapDefHostEntry 
    MAX-ACCESS      not-accessible
    STATUS          current
    DESCRIPTION
        "SAP default host specific information."
    INDEX           { svcId, 
                      sapPortId, 
                      sapEncapValue, 
                      sapDefHostIpv4SubnetAddr, 
                      sapDefHostIpv4SubnetMask }
    ::= { sapDefHostTable 1 }

SapDefHostEntry   ::=
    SEQUENCE {
        sapDefHostIpv4SubnetAddr         IpAddress,
        sapDefHostIpv4SubnetMask         IpAddress,
        sapDefHostLastChanged            TimeStamp,
        sapDefHostRowStatus              RowStatus,
        sapDefHostNextHopIpv4Addr        IpAddress
    }

sapDefHostIpv4SubnetAddr  OBJECT-TYPE
    SYNTAX      IpAddress
    MAX-ACCESS  not-accessible
    STATUS      current
    DESCRIPTION
        "The value of the object sapDefHostIpv4SubnetAddr specifies
         the IPv4 subnet address for this SAP default host.
         
         It must be equal to one of the addresses of the subscriber interface
         this SAP belongs to, that is one of its vRiaIpAddress values."
    DEFVAL { '00000000'H }
    ::= { sapDefHostEntry 1 }

sapDefHostIpv4SubnetMask  OBJECT-TYPE
    SYNTAX      IpAddress
    MAX-ACCESS  not-accessible
    STATUS      current
    DESCRIPTION
        "The value of sapDefHostIpv4SubnetMask specifies the subnet mask
         applicable to sapDefHostIpv4SubnetAddr.
         
         It must be equal to the netmask of the subscriber interface address
         associated with sapDefHostIpv4SubnetAddr, that is the vRiaNetMask of
         the same row in the vRtrIpAddrTable."
    DEFVAL { '00000000'H }  
    ::= { sapDefHostEntry 2 }

sapDefHostLastChanged  OBJECT-TYPE
    SYNTAX      TimeStamp
    MAX-ACCESS  read-only
    STATUS      current
    DESCRIPTION
        "The value of sapDefHostLastChanged indicates the sysUpTime at
         the time of the most recent management-initiated change to this
         conceptual row."
    ::= { sapDefHostEntry 3 }

sapDefHostRowStatus OBJECT-TYPE
    SYNTAX       RowStatus
    MAX-ACCESS   read-create
    STATUS       current
    DESCRIPTION
        "The value of sapDefHostRowStatus specifies the row status of this row."
    ::= { sapDefHostEntry 4 }

sapDefHostNextHopIpv4Addr OBJECT-TYPE
    SYNTAX       IpAddress
    MAX-ACCESS   read-create
    STATUS       current
    DESCRIPTION     
        "The value of sapDefHostNextHopIpv4Addr specifies
         the next-hop IP address for this SAP default host.
         
         The value all zeroes is not allowed.
         
         A value for sapDefHostNextHopIpv4Addr must be specified when a row
         is created and this value cannot be changed afterwards."
    ::= { sapDefHostEntry 5 }

--
-- IP Tunnel Table
--
tmnxIpTunnelTableLastChanged OBJECT-TYPE
    SYNTAX      TimeStamp
    MAX-ACCESS  read-only
    STATUS      current
    DESCRIPTION
        "The value of tmnxIpTunnelTableLastChanged indicates the
         sysUpTime at the time of the last modification to 
         tmnxIpTunnelTable by adding, deleting an entry or change
         to a writable object in the table.

         If no changes were made to the table since the last 
         re-initialization of the local network management subsystem, 
         then this object contains a zero value."
    ::= { tmnxSapObjs 141 }

tmnxIpTunnelTable OBJECT-TYPE
    SYNTAX      SEQUENCE OF TmnxIpTunnelEntry
    MAX-ACCESS  not-accessible
    STATUS      current
    DESCRIPTION
        "The tmnxIpTunnelTable contains IP Tunnel entries for each SAP.

         Entries are created/deleted by the user."
    ::= { tmnxSapObjs 142 }

tmnxIpTunnelEntry OBJECT-TYPE
    SYNTAX      TmnxIpTunnelEntry
    MAX-ACCESS  not-accessible
    STATUS      current
    DESCRIPTION
        "The tmnxIpTunnelEntry contains information about a single IP Tunnel
        entry."
    INDEX { svcId, 
            sapPortId, 
            sapEncapValue, 
            tmnxIpTunnelName 
          }
    ::= { tmnxIpTunnelTable 1 }

TmnxIpTunnelEntry ::= SEQUENCE {
    tmnxIpTunnelName                 TNamedItem, 
    tmnxIpTunnelRowStatus            RowStatus, 
    tmnxIpTunnelLastChanged          TimeStamp,
    tmnxIpTunnelGreHeader            TruthValue,
    tmnxIpTunnelDescription          TItemDescription,
    tmnxIpTunnelLclIpAddrType        InetAddressType, 
    tmnxIpTunnelLclIpAddr            InetAddress,
    tmnxIpTunnelRemIpAddrType        InetAddressType, 
    tmnxIpTunnelRemIpAddr            InetAddress,
    tmnxIpTunnelBackupRemIpAddrType  InetAddressType, 
    tmnxIpTunnelBackupRemIpAddr      InetAddress,
    tmnxIpTunnelOperRemIpAddrType    InetAddressType, 
    tmnxIpTunnelOperRemIpAddr        InetAddress,
    tmnxIpTunnelDeliverySvcId        TmnxServId,
    tmnxIpTunnelAdminState           TmnxAdminState,
    tmnxIpTunnelOperState            TmnxOperState,
    tmnxIpTunnelOperFlags            BITS,
    tmnxIpTunnelDscp                 TDSCPNameOrEmpty,
    tmnxIpTunnelReassembly           Integer32,
    tmnxIpTunnelClearDfBit           TruthValue,
    tmnxIpTunnelIpMtu                Unsigned32,
    tmnxIpTunnelHostISA              TmnxHwIndexOrZero,
    tmnxIpTunnelEncapIpMtu           Unsigned32,
    tmnxIpTunnelIcmp6Pkt2Big      TruthValue,
    tmnxIpTunnelIcmp6NumPkt2Big      Unsigned32,
    tmnxIpTunnelIcmp6Pkt2BigTime     Unsigned32,
    tmnxIpTunnelGreHeaderSendKey  Unsigned32,
    tmnxIpTunnelGreHeaderRcvKey  Unsigned32,
    tmnxIpTunnelGreHeaderKeysSet  TruthValue,
    tmnxIpTunnelOperChanged       TimeStamp
}

tmnxIpTunnelName  OBJECT-TYPE
    SYNTAX      TNamedItem
    MAX-ACCESS  not-accessible
    STATUS      current
    DESCRIPTION
        "The value of tmnxIpTunnelName specifies the name of the tunnel 
         and is part of the index for the table tmnxIpTunnelTable."
    ::= { tmnxIpTunnelEntry 1 }

tmnxIpTunnelRowStatus OBJECT-TYPE
    SYNTAX      RowStatus
    MAX-ACCESS  read-create
    STATUS      current
    DESCRIPTION
        "The tmnxIpTunnelRowStatus object is used to create and delete 
         rows in the tmnxIpTunnelTable."
    ::= { tmnxIpTunnelEntry 2 }

tmnxIpTunnelLastChanged  OBJECT-TYPE
    SYNTAX      TimeStamp
    MAX-ACCESS  read-only
    STATUS      current
    DESCRIPTION
        "The value of tmnxIpTunnelLastChanged indicates the sysUpTime
         at the time of the last modification of this entry."
    ::= { tmnxIpTunnelEntry 3 }

tmnxIpTunnelGreHeader  OBJECT-TYPE
    SYNTAX      TruthValue
    MAX-ACCESS  read-create
    STATUS      current
    DESCRIPTION
        "The value of tmnxIpTunnelGreHeader specifies whether the tunnel will
         include a GRE header in it."
    DEFVAL { false }
    ::= { tmnxIpTunnelEntry 4 }

tmnxIpTunnelDescription  OBJECT-TYPE
    SYNTAX      TItemDescription
    MAX-ACCESS  read-create
    STATUS      current
    DESCRIPTION
        "The value of tmnxIpTunnelDescription specifies the 
         user-provided description for each tmnxIpTunnelEntry in the 
         table tmnxIpTunnelTable."
    DEFVAL { "" }
    ::= { tmnxIpTunnelEntry 5 }

tmnxIpTunnelLclIpAddrType  OBJECT-TYPE
    SYNTAX      InetAddressType
    MAX-ACCESS  read-create
    STATUS      current
    DESCRIPTION
        "The value of tmnxIpTunnelLclIpAddrType specifies the address 
         type of address in tmnxIpTunnelLclIpAddr." 
    DEFVAL { unknown }
    ::= { tmnxIpTunnelEntry 6 }

tmnxIpTunnelLclIpAddr  OBJECT-TYPE
    SYNTAX      InetAddress (SIZE (0|4|16|20))
    MAX-ACCESS  read-create
    STATUS      current
    DESCRIPTION
        "The value of tmnxIpTunnelLclIpAddr specifies the address of the 
         local end-point of this IP tunnel."
    DEFVAL { ''H }
    ::= { tmnxIpTunnelEntry 7 }

tmnxIpTunnelRemIpAddrType  OBJECT-TYPE
    SYNTAX      InetAddressType
    MAX-ACCESS  read-create
    STATUS      current
    DESCRIPTION
        "The value of tmnxIpTunnelRemIpAddrType specifies the address
         type of address in tmnxIpTunnelRemIpAddr."
    DEFVAL { unknown }
    ::= { tmnxIpTunnelEntry 8 }

tmnxIpTunnelRemIpAddr  OBJECT-TYPE
    SYNTAX      InetAddress (SIZE (0|4|16|20))
    MAX-ACCESS  read-create
    STATUS      current
    DESCRIPTION
        "The value of tmnxIpTunnelRemIpAddr specifies the address of the 
         remote end-point of this IP tunnel."
    DEFVAL { ''H }
    ::= { tmnxIpTunnelEntry 9 }

tmnxIpTunnelBackupRemIpAddrType  OBJECT-TYPE
    SYNTAX      InetAddressType
    MAX-ACCESS  read-create
    STATUS      current
    DESCRIPTION
        "The value of tmnxIpTunnelBackupRemIpAddrType specifies the address
         type of address in tmnxIpTunnelBackupRemIpAddr."
    DEFVAL { unknown }
    ::= { tmnxIpTunnelEntry 10 }

tmnxIpTunnelBackupRemIpAddr  OBJECT-TYPE
    SYNTAX      InetAddress (SIZE (0|4|16|20))
    MAX-ACCESS  read-create
    STATUS      current
    DESCRIPTION
        "The value of tmnxIpTunnelBackupRemIpAddr specifies the address of the 
         backup remote end-point of this IP tunnel."
    DEFVAL { ''H }
    ::= { tmnxIpTunnelEntry 11 }

tmnxIpTunnelOperRemIpAddrType  OBJECT-TYPE
    SYNTAX      InetAddressType
    MAX-ACCESS  read-only
    STATUS      current
    DESCRIPTION
        "The value of tmnxIpTunnelOperRemIpAddrType indicates the address
         type of address in tmnxIpTunnelOperRemIpAddr."
    ::= { tmnxIpTunnelEntry 12 }

tmnxIpTunnelOperRemIpAddr  OBJECT-TYPE
    SYNTAX      InetAddress (SIZE (0|4|16|20))
    MAX-ACCESS  read-only
    STATUS      current
    DESCRIPTION
        "The value of tmnxIpTunnelOperRemIpAddr indicates the address of the 
         operational remote end-point of this IP tunnel."
    ::= { tmnxIpTunnelEntry 13 }

tmnxIpTunnelDeliverySvcId  OBJECT-TYPE
    SYNTAX      TmnxServId
    MAX-ACCESS  read-create
    STATUS      current
    DESCRIPTION
        "The value of tmnxIpTunnelDeliverySvcId specifies the service-id 
         of the tunnel delivery service."
    DEFVAL { 0 }
    ::= { tmnxIpTunnelEntry 14 }

tmnxIpTunnelAdminState  OBJECT-TYPE
    SYNTAX      TmnxAdminState 
    MAX-ACCESS  read-create
    STATUS      current
    DESCRIPTION
        "The value of tmnxIpTunnelAdminState specifies the administrative
         state of the tmnxIpTunnelEntry."
    DEFVAL { outOfService }
    ::= { tmnxIpTunnelEntry 15 }

tmnxIpTunnelOperState  OBJECT-TYPE
    SYNTAX      TmnxOperState 
    MAX-ACCESS  read-only
    STATUS      current
    DESCRIPTION
        "The value of tmnxIpTunnelOperState indicates the operational 
         status of tmnxIpTunnelEntry."
    ::= { tmnxIpTunnelEntry 16 }

tmnxIpTunnelOperFlags  OBJECT-TYPE
    SYNTAX      BITS {
                    unresolvedLocalIp (0),  
                    tunnelAdminDown (1),
                    sapDown (2),
                    unresolvedDeliverySvc(3),
                    reserved(4),
                    remIpUnreachable(5),
                    unresolvedDstIp(6)
                }
    MAX-ACCESS  read-only
    STATUS      current
    DESCRIPTION
        "The value of tmnxIpTunnelOperFlags indicates the reason why the
         tunnel is operationally down."
    ::= { tmnxIpTunnelEntry 17 }

tmnxIpTunnelDscp  OBJECT-TYPE
    SYNTAX      TDSCPNameOrEmpty
    MAX-ACCESS  read-create
    STATUS      current
    DESCRIPTION 
        "The value of tmnxIpTunnelDscp specifies DSCP value which will be
         used in the IP tunnel carrying IP header in the delivery service."
    DEFVAL { "" }
    ::= { tmnxIpTunnelEntry 18 }

tmnxIpTunnelReassembly  OBJECT-TYPE
    SYNTAX      Integer32 (-1|0..5000)
    UNITS       "milli-seconds"
    MAX-ACCESS  read-create
    STATUS      current
    DESCRIPTION 
        "The value of tmnxIpTunnelReassembly specifies the maximum number
         of seconds to wait to receive all fragments of a particular IPSec
         or IP packet for reassembly.

         The tmnxIpTunnelReassembly value set to zero indicates that
         reassembly is disabled.
         
         The tmnxIpTunnelReassembly value set default indicates that this
         value will be derived from the value of
         TIMETRA-CHASSIS-MIB::tmnxIPsecIsaGrpTunnelReassembly object.

         An 'inconsistentValue' error is retuned if the value is not a multiple
         of 100 milli-seconds."
    DEFVAL { -1 }
    ::= { tmnxIpTunnelEntry 19 }

tmnxIpTunnelClearDfBit  OBJECT-TYPE
    SYNTAX      TruthValue
    MAX-ACCESS  read-create
    STATUS      current
    DESCRIPTION 
        "The value of tmnxIpTunnelClearDfBit specifies whether to clear
         Do not Fragment (DF) bit in the outgoing packets in this IP tunnel."
    DEFVAL { false }
    ::= { tmnxIpTunnelEntry 20 }

tmnxIpTunnelIpMtu  OBJECT-TYPE
    SYNTAX      Unsigned32 (0|512..9000)
    MAX-ACCESS  read-create
    STATUS      current
    DESCRIPTION 
        "The value of tmnxIpTunnelIpMtu specifies the MTU size for IP packets
         for this IP tunnel.

         A value set to zero indicates maximum supported MTU size on the SAP
         for this IP tunnel."
    DEFVAL { 0 }
    ::= { tmnxIpTunnelEntry 21 }

tmnxIpTunnelHostISA  OBJECT-TYPE
    SYNTAX      TmnxHwIndexOrZero
    MAX-ACCESS  read-only
    STATUS      current
    DESCRIPTION
        "The value of tmnxIpTunnelHostISA indicates the active ISA
         that is being used to host this GRE tunnel.

         This object will have a value of zero when this tunnel is operationally
         down."
    ::= { tmnxIpTunnelEntry 22 }

tmnxIpTunnelEncapIpMtu  OBJECT-TYPE
    SYNTAX      Unsigned32 (0|512..9000)
    MAX-ACCESS  read-create
    STATUS      current
    DESCRIPTION
        "The value of tmnxIpTunnelEncapIpMtu specifies the MTU size for IP packets
         after tunnel encapsulation has been added.

         A value set to zero indicates maximum supported MTU size on the SAP
         for this tunnel."
    DEFVAL { 0 }
    ::= { tmnxIpTunnelEntry 23 }

tmnxIpTunnelIcmp6Pkt2Big  OBJECT-TYPE
    SYNTAX      TruthValue
    MAX-ACCESS  read-create
    STATUS      current
    DESCRIPTION
        "The value of tmnxIpTunnelIcmp6Pkt2Big specifies whether
         packet-too-big ICMP messages should be sent. When it is set to
         'true', ICMPv6 packet-too-big messages are generated by this ipsec
         tunnel. When tmnxIpTunnelIcmp6Pkt2Big is set to 'false', ICMPv6
         packet-too-big messages are not sent."
    DEFVAL { true }
    ::= { tmnxIpTunnelEntry 25 }

tmnxIpTunnelIcmp6NumPkt2Big  OBJECT-TYPE
    SYNTAX      Unsigned32 (10..1000)
    MAX-ACCESS  read-create
    STATUS      current
    DESCRIPTION
        "The value of tmnxIpTunnelIcmp6NumPkt2Big specifies how many
         packet-too-big ICMPv6 messages are issued in the time frame
         specified by tmnxIpTunnelIcmp6Pkt2BigTime."
    DEFVAL { 100 }
    ::= { tmnxIpTunnelEntry 26 }

tmnxIpTunnelIcmp6Pkt2BigTime  OBJECT-TYPE
    SYNTAX      Unsigned32 (1..60)
    UNITS       "seconds"
    MAX-ACCESS  read-create
    STATUS      current
    DESCRIPTION
        "The value of tmnxIpTunnelIcmp6Pkt2BigTime specifies the time frame
         in seconds that is used to limit the number of packet-too-big ICMPv6
         messages issued per time frame."
    DEFVAL { 10 }
    ::= { tmnxIpTunnelEntry 27 }

tmnxIpTunnelGreHeaderSendKey  OBJECT-TYPE
    SYNTAX      Unsigned32
    MAX-ACCESS  read-create
    STATUS      current
    DESCRIPTION
        "The value of tmnxIpTunnelGreHeaderSendKey specifies the send-key 
        value used while transmitting Gre Header. This value is 
        considered only when tmnxIpTunnelGreHeaderKeysSet is enabled."
    DEFVAL { 0 }
    ::= { tmnxIpTunnelEntry 28 }

tmnxIpTunnelGreHeaderRcvKey  OBJECT-TYPE
    SYNTAX      Unsigned32
    MAX-ACCESS  read-create
    STATUS      current
    DESCRIPTION
        "The value of tmnxIpTunnelGreHeaderRcvKey specifies the receive value 
        in Gre Header used to validate the received packets. This value is considered only when 
        tmnxIpTunnelGreHeaderKeysSet is enabled."
    DEFVAL { 0 }
    ::= { tmnxIpTunnelEntry 29 }

tmnxIpTunnelGreHeaderKeysSet  OBJECT-TYPE
    SYNTAX      TruthValue
    MAX-ACCESS  read-create
    STATUS      current
    DESCRIPTION
        "The value of tmnxIpTunnelGreHeaderKeysSet indicates whether to
         transmit the gre-header using the configured send-key, and whether
         to validate that the gre-headers of received packets contain the
         configured receive-key."
    DEFVAL { false }
    ::= { tmnxIpTunnelEntry 30 }

tmnxIpTunnelOperChanged  OBJECT-TYPE
    SYNTAX      TimeStamp
    MAX-ACCESS  read-only
    STATUS      current
    DESCRIPTION
        "The value of tmnxIpTunnelOperChanged indicates the sysUpTime
         at the time of the last operational status change of this entry."
    ::= { tmnxIpTunnelEntry 31 }

--
-- IP Tunnel Destination Address Table
--
tmnxIpTnlDstAddrTableLastChanged OBJECT-TYPE
    SYNTAX      TimeStamp
    MAX-ACCESS  read-only
    STATUS      current
    DESCRIPTION
        "The value of tmnxIpTnlDstAddrTableLastChanged indicates the
         sysUpTime at the time of the last modification to 
         tmnxIpTnlDstAddrTable by adding, deleting an entry or change
         to a writable object in the table.

         If no changes were made to the table since the last 
         re-initialization of the local network management subsystem, 
         then this object contains a zero value."
    ::= { tmnxSapObjs 143 }

tmnxIpTnlDstAddrTable OBJECT-TYPE
    SYNTAX      SEQUENCE OF TmnxIpTnlDstAddrEntry
    MAX-ACCESS  not-accessible
    STATUS      current
    DESCRIPTION
        "The tmnxIpTnlDstAddrTable contains destination addresses for each IP
         tunnel in the system.
         
         Entries are created and deleted by the user."
    ::= { tmnxSapObjs 144 }

tmnxIpTnlDstAddrEntry OBJECT-TYPE
    SYNTAX      TmnxIpTnlDstAddrEntry
    MAX-ACCESS  not-accessible
    STATUS      current
    DESCRIPTION
        "The tmnxIpTnlDstAddrEntry contains information about a single
         destination address in an IP Tunnel."
    INDEX { svcId, 
            sapPortId, 
            sapEncapValue, 
            tmnxIpTunnelName,
            tmnxIpTnlDstAddrType,
            tmnxIpTnlDstAddr
          }
    ::= { tmnxIpTnlDstAddrTable 1 }

TmnxIpTnlDstAddrEntry ::= SEQUENCE {
    tmnxIpTnlDstAddrType                 InetAddressType, 
    tmnxIpTnlDstAddr                     InetAddress,
    tmnxIpTnlDstAddrRowStatus            RowStatus, 
    tmnxIpTnlDstAddrLastChanged          TimeStamp,
    tmnxIpTnlDstAddrResolved             TruthValue
}

tmnxIpTnlDstAddrType  OBJECT-TYPE
    SYNTAX      InetAddressType
    MAX-ACCESS  not-accessible
    STATUS      current
    DESCRIPTION
        "The value of tmnxIpTnlDstAddrType specifies the address 
         type of address in tmnxIpTnlDstAddr."
    ::= { tmnxIpTnlDstAddrEntry 1 }

tmnxIpTnlDstAddr  OBJECT-TYPE
    SYNTAX      InetAddress (SIZE (4|16|20))
    MAX-ACCESS  not-accessible
    STATUS      current
    DESCRIPTION
        "The value of tmnxIpTnlDstAddr specifies the address of the 
         destination of this IP tunnel."
    ::= { tmnxIpTnlDstAddrEntry 2 }

tmnxIpTnlDstAddrRowStatus OBJECT-TYPE
    SYNTAX      RowStatus
    MAX-ACCESS  read-create
    STATUS      current
    DESCRIPTION
        "The tmnxIpTnlDstAddrRowStatus object is used to create and delete 
         rows in the tmnxIpTnlDstAddrTable."
    ::= { tmnxIpTnlDstAddrEntry 3 }

tmnxIpTnlDstAddrLastChanged  OBJECT-TYPE
    SYNTAX      TimeStamp
    MAX-ACCESS  read-only
    STATUS      current
    DESCRIPTION
        "The value of tmnxIpTnlDstAddrLastChanged indicates the sysUpTime
         at the time of the last modification of this entry."
    ::= { tmnxIpTnlDstAddrEntry 4 }

tmnxIpTnlDstAddrResolved  OBJECT-TYPE
    SYNTAX      TruthValue
    MAX-ACCESS  read-only
    STATUS      current
    DESCRIPTION
        "The value of tmnxIpTnlDstAddrResolved indicates whether or not this 
        IP tunnel destination address has been resolved as reachable by the
        virtual router."
    ::= { tmnxIpTnlDstAddrEntry 5 }
--
-- IP Tunnel Statistics Table
--

tmnxIpTunnelStatsTable OBJECT-TYPE
    SYNTAX      SEQUENCE OF TmnxIpTunnelStatsEntry
    MAX-ACCESS  not-accessible
    STATUS      current
    DESCRIPTION
        "The tmnxIpTunnelStatsTable contains statistics entries per IP tunnel."
    ::= { tmnxSapObjs 145 }

tmnxIpTunnelStatsEntry       OBJECT-TYPE
    SYNTAX      TmnxIpTunnelStatsEntry
    MAX-ACCESS  not-accessible
    STATUS      current
    DESCRIPTION
        "The tmnxIpTunnelStatsEntry contains statistics information for a
         single IP Tunnel."
    INDEX { svcId, 
            sapPortId, 
            sapEncapValue, 
            tmnxIpTunnelName 
          }
    ::= { tmnxIpTunnelStatsTable 1 }

TmnxIpTunnelStatsEntry ::= SEQUENCE {
    tmnxIpTunnelPktsTx               Counter64,
    tmnxIpTunnelPktsTxLo             Counter32,
    tmnxIpTunnelPktsTxHi             Counter32,
    tmnxIpTunnelPktsRx               Counter64,
    tmnxIpTunnelPktsRxLo             Counter32,
    tmnxIpTunnelPktsRxHi             Counter32,
    tmnxIpTunnelBytesTx              Counter64,
    tmnxIpTunnelBytesTxLo            Counter32,
    tmnxIpTunnelBytesTxHi            Counter32,
    tmnxIpTunnelBytesRx              Counter64,
    tmnxIpTunnelBytesRxLo            Counter32,
    tmnxIpTunnelBytesRxHi            Counter32,
    tmnxIpTunnelTxErrors             Counter32,
    tmnxIpTunnelRxErrors             Counter32,
    tmnxIpTunnelKeyIgnoredRx         Counter64,
    tmnxIpTunnelKeyIgnoredRxLo       Counter32,
    tmnxIpTunnelKeyIgnoredRxHi       Counter32,
    tmnxIpTunnelSeqIgnoredRx         Counter64,
    tmnxIpTunnelSeqIgnoredRxLo       Counter32,
    tmnxIpTunnelSeqIgnoredRxHi       Counter32,
    tmnxIpTunnelVersUnsupRx          Counter64,
    tmnxIpTunnelVersUnsupRxLo        Counter32,
    tmnxIpTunnelVersUnsupRxHi        Counter32,
    tmnxIpTunnelInvalidChksumRx      Counter64,
    tmnxIpTunnelInvalidChksumRxLo    Counter32,
    tmnxIpTunnelInvalidChksumRxHi    Counter32,
    tmnxIpTunnelLoopsRx              Counter64,
    tmnxIpTunnelLoopsRxLo            Counter32,
    tmnxIpTunnelLoopsRxHi            Counter32,
    tmnxIpTunnelTooBigTx             Counter64,
    tmnxIpTunnelTooBigTxLo           Counter32,
    tmnxIpTunnelTooBigTxHi           Counter32,
    tmnxIpTunnelKeyMismatchRx        Counter64,
    tmnxIpTunnelEncapOverhead        Unsigned32,
    tmnxIpTunnelPreEncapFragCount    Counter64,
    tmnxIpTunnelPreEncapFragLastSize Unsigned32,
    tmnxIpTunnelPostEncapFragCount   Counter64,
    tmnxIpTunnelPostEncapFragLstSize Unsigned32
}

tmnxIpTunnelPktsTx        OBJECT-TYPE
    SYNTAX      Counter64
    MAX-ACCESS  read-only
    STATUS      current
    DESCRIPTION
        "The value of tmnxIpTunnelPktsTx indicates the number of
         packets this IP Tunnel has sent."
    ::= { tmnxIpTunnelStatsEntry 1 }

tmnxIpTunnelPktsTxLo        OBJECT-TYPE
    SYNTAX      Counter32
    MAX-ACCESS  read-only
    STATUS      current
    DESCRIPTION
        "The value of tmnxIpTunnelPktsTxLo indicates lower 32 bits of the
        value of tmnxIpTunnelPktsTx object."
    ::= { tmnxIpTunnelStatsEntry 2 }

tmnxIpTunnelPktsTxHi        OBJECT-TYPE
    SYNTAX      Counter32
    MAX-ACCESS  read-only
    STATUS      current
    DESCRIPTION
        "The value of tmnxIpTunnelPktsTxHi indicates higher 32 bits of the
        value of tmnxIpTunnelPktsTx object."
    ::= { tmnxIpTunnelStatsEntry 3 }

tmnxIpTunnelPktsRx        OBJECT-TYPE
    SYNTAX      Counter64
    MAX-ACCESS  read-only
    STATUS      current
    DESCRIPTION
        "The value of tmnxIpTunnelPktsRx indicates the number of
         packets this IP Tunnel has received."
    ::= { tmnxIpTunnelStatsEntry 4 }

tmnxIpTunnelPktsRxLo        OBJECT-TYPE
    SYNTAX      Counter32
    MAX-ACCESS  read-only
    STATUS      current
    DESCRIPTION
        "The value of tmnxIpTunnelPktsRxLo indicates lower 32 bits of the
        value of tmnxIpTunnelPktsRx object."
    ::= { tmnxIpTunnelStatsEntry 5 }

tmnxIpTunnelPktsRxHi        OBJECT-TYPE
    SYNTAX      Counter32
    MAX-ACCESS  read-only
    STATUS      current
    DESCRIPTION
        "The value of tmnxIpTunnelPktsRxHi indicates higher 32 bits of the
        value of tmnxIpTunnelPktsRx object."
    ::= { tmnxIpTunnelStatsEntry 6 }

tmnxIpTunnelBytesTx        OBJECT-TYPE
    SYNTAX      Counter64
    MAX-ACCESS  read-only
    STATUS      current
    DESCRIPTION
        "The value of tmnxIpTunnelBytesTx indicates the number of
         bytes this IP Tunnel has sent."
    ::= { tmnxIpTunnelStatsEntry 7 }

tmnxIpTunnelBytesTxLo        OBJECT-TYPE
    SYNTAX      Counter32
    MAX-ACCESS  read-only
    STATUS      current
    DESCRIPTION
        "The value of tmnxIpTunnelBytesTxLo indicates lower 32 bits of the
        value of tmnxIpTunnelBytesTx object."
    ::= { tmnxIpTunnelStatsEntry 8 }

tmnxIpTunnelBytesTxHi        OBJECT-TYPE
    SYNTAX      Counter32
    MAX-ACCESS  read-only
    STATUS      current
    DESCRIPTION
        "The value of tmnxIpTunnelBytesTxHi indicates higher 32 bits of the
        value of tmnxIpTunnelBytesTx object."
    ::= { tmnxIpTunnelStatsEntry 9 }

tmnxIpTunnelBytesRx        OBJECT-TYPE
    SYNTAX      Counter64
    MAX-ACCESS  read-only
    STATUS      current
    DESCRIPTION
        "The value of tmnxIpTunnelBytesRx indicates the number of
         bytes this IP Tunnel has received."
    ::= { tmnxIpTunnelStatsEntry 10 }

tmnxIpTunnelBytesRxLo        OBJECT-TYPE
    SYNTAX      Counter32
    MAX-ACCESS  read-only
    STATUS      current
    DESCRIPTION
        "The value of tmnxIpTunnelBytesRxLo indicates lower 32 bits of the
        value of tmnxIpTunnelBytesRx object."
    ::= { tmnxIpTunnelStatsEntry 11 }

tmnxIpTunnelBytesRxHi        OBJECT-TYPE
    SYNTAX      Counter32
    MAX-ACCESS  read-only
    STATUS      current
    DESCRIPTION
        "The value of tmnxIpTunnelBytesRxHi indicates higher 32 bits of the
        value of tmnxIpTunnelBytesRx object."
    ::= { tmnxIpTunnelStatsEntry 12 }

tmnxIpTunnelTxErrors        OBJECT-TYPE
    SYNTAX      Counter32
    MAX-ACCESS  read-only
    STATUS      current
    DESCRIPTION
        "The value of tmnxIpTunnelTxErrors indicates the number of
         packet transmit errors."
    ::= { tmnxIpTunnelStatsEntry 13 }

tmnxIpTunnelRxErrors        OBJECT-TYPE
    SYNTAX      Counter32
    MAX-ACCESS  read-only
    STATUS      current
    DESCRIPTION
        "The value of tmnxIpTunnelRxErrors indicates the number of
         packet receive errors."
    ::= { tmnxIpTunnelStatsEntry 14 }

tmnxIpTunnelKeyIgnoredRx        OBJECT-TYPE
    SYNTAX      Counter64
    MAX-ACCESS  read-only
    STATUS      current
    DESCRIPTION
        "The value of tmnxIpTunnelKeyIgnoredRx indicates the number of
         packets this IP Tunnel received and processed ignoring key field."
    ::= { tmnxIpTunnelStatsEntry 15 }

tmnxIpTunnelKeyIgnoredRxLo        OBJECT-TYPE
    SYNTAX      Counter32
    MAX-ACCESS  read-only
    STATUS      current
    DESCRIPTION
        "The value of tmnxIpTunnelKeyIgnoredRxLo indicates lower 32 bits of the
        value of tmnxIpTunnelKeyIgnoredRx object."
    ::= { tmnxIpTunnelStatsEntry 16 }

tmnxIpTunnelKeyIgnoredRxHi        OBJECT-TYPE
    SYNTAX      Counter32
    MAX-ACCESS  read-only
    STATUS      current
    DESCRIPTION
        "The value of tmnxIpTunnelKeyIgnoredRxHi indicates higher 32 bits of
        the value of tmnxIpTunnelKeyIgnoredRx object."
    ::= { tmnxIpTunnelStatsEntry 17 }

tmnxIpTunnelSeqIgnoredRx        OBJECT-TYPE
    SYNTAX      Counter64
    MAX-ACCESS  read-only
    STATUS      current
    DESCRIPTION
        "The value of tmnxIpTunnelSeqIgnoredRx indicates the number of
         packets this IP Tunnel and processed ignoring sequence field."
    ::= { tmnxIpTunnelStatsEntry 18 }

tmnxIpTunnelSeqIgnoredRxLo        OBJECT-TYPE
    SYNTAX      Counter32
    MAX-ACCESS  read-only
    STATUS      current
    DESCRIPTION
        "The value of tmnxIpTunnelSeqIgnoredRxLo indicates lower 32 bits of the
        value of tmnxIpTunnelSeqIgnoredRx object."
    ::= { tmnxIpTunnelStatsEntry 19 }

tmnxIpTunnelSeqIgnoredRxHi        OBJECT-TYPE
    SYNTAX      Counter32
    MAX-ACCESS  read-only
    STATUS      current
    DESCRIPTION
        "The value of tmnxIpTunnelSeqIgnoredRxHi indicates higher 32 bits of
        the value of tmnxIpTunnelSeqIgnoredRx object."
    ::= { tmnxIpTunnelStatsEntry 20 }

tmnxIpTunnelVersUnsupRx        OBJECT-TYPE
    SYNTAX      Counter64
    MAX-ACCESS  read-only
    STATUS      current
    DESCRIPTION
        "The value of tmnxIpTunnelVersUnsupRx indicates the number of
         packets this IP Tunnel received with unsupported IP version and
         were dropped."
    ::= { tmnxIpTunnelStatsEntry 21 }

tmnxIpTunnelVersUnsupRxLo        OBJECT-TYPE
    SYNTAX      Counter32
    MAX-ACCESS  read-only
    STATUS      current
    DESCRIPTION
        "The value of tmnxIpTunnelVersUnsupRxLo indicates lower 32 bits of the
        value of tmnxIpTunnelVersUnsupRx object."
    ::= { tmnxIpTunnelStatsEntry 22 }

tmnxIpTunnelVersUnsupRxHi        OBJECT-TYPE
    SYNTAX      Counter32
    MAX-ACCESS  read-only
    STATUS      current
    DESCRIPTION
        "The value of tmnxIpTunnelVersUnsupRxHi indicates higher 32 bits of
        the value of tmnxIpTunnelVersUnsupRx object."
    ::= { tmnxIpTunnelStatsEntry 23 }

tmnxIpTunnelInvalidChksumRx        OBJECT-TYPE
    SYNTAX      Counter64
    MAX-ACCESS  read-only
    STATUS      current
    DESCRIPTION
        "The value of tmnxIpTunnelInvalidChksumRx indicates the number of
         packets this IP Tunnel received with invalid checksum and
         were dropped."
    ::= { tmnxIpTunnelStatsEntry 24 }

tmnxIpTunnelInvalidChksumRxLo        OBJECT-TYPE
    SYNTAX      Counter32
    MAX-ACCESS  read-only
    STATUS      current
    DESCRIPTION
        "The value of tmnxIpTunnelInvalidChksumRxLo indicates lower 32 bits
        of the value of tmnxIpTunnelInvalidChksumRx object."
    ::= { tmnxIpTunnelStatsEntry 25 }

tmnxIpTunnelInvalidChksumRxHi        OBJECT-TYPE
    SYNTAX      Counter32
    MAX-ACCESS  read-only
    STATUS      current
    DESCRIPTION
        "The value of tmnxIpTunnelInvalidChksumRxHi indicates higher 32 bits of
        the value of tmnxIpTunnelInvalidChksumRx object."
    ::= { tmnxIpTunnelStatsEntry 26 }

tmnxIpTunnelLoopsRx        OBJECT-TYPE
    SYNTAX      Counter64
    MAX-ACCESS  read-only
    STATUS      current
    DESCRIPTION
        "The value of tmnxIpTunnelLoopsRx indicates the number of
         packets this IP Tunnel received with payload with destination address
         which could result in a loop and were dropped."
    ::= { tmnxIpTunnelStatsEntry 27 }

tmnxIpTunnelLoopsRxLo        OBJECT-TYPE
    SYNTAX      Counter32
    MAX-ACCESS  read-only
    STATUS      current
    DESCRIPTION
        "The value of tmnxIpTunnelLoopsRxLo indicates lower 32 bits of the
        value of tmnxIpTunnelLoopsRx object."
    ::= { tmnxIpTunnelStatsEntry 28 }

tmnxIpTunnelLoopsRxHi        OBJECT-TYPE
    SYNTAX      Counter32
    MAX-ACCESS  read-only
    STATUS      current
    DESCRIPTION
        "The value of tmnxIpTunnelLoopsRxHi indicates higher 32 bits of
        the value of tmnxIpTunnelLoopsRx object."
    ::= { tmnxIpTunnelStatsEntry 29 }

tmnxIpTunnelTooBigTx        OBJECT-TYPE
    SYNTAX      Counter64
    MAX-ACCESS  read-only
    STATUS      current
    DESCRIPTION
        "The value of tmnxIpTunnelTooBigTx indicates the number of
         packets this IP Tunnel received which were too big to transmit."
    ::= { tmnxIpTunnelStatsEntry 30 }

tmnxIpTunnelTooBigTxLo        OBJECT-TYPE
    SYNTAX      Counter32
    MAX-ACCESS  read-only
    STATUS      current
    DESCRIPTION
        "The value of tmnxIpTunnelTooBigTxLo indicates lower 32 bits of the
        value of tmnxIpTunnelTooBigTx object."
    ::= { tmnxIpTunnelStatsEntry 31 }

tmnxIpTunnelTooBigTxHi        OBJECT-TYPE
    SYNTAX      Counter32
    MAX-ACCESS  read-only
    STATUS      current
    DESCRIPTION
        "The value of tmnxIpTunnelTooBigTxHi indicates higher 32 bits of
        the value of tmnxIpTunnelTooBigTx object."
    ::= { tmnxIpTunnelStatsEntry 32 }

tmnxIpTunnelKeyMismatchRx        OBJECT-TYPE
    SYNTAX      Counter64
    MAX-ACCESS  read-only
    STATUS      current
    DESCRIPTION
        "The value of tmnxIpTunnelKeyMismatchRx indicates the number of
         packets this IP Tunnel received with key mismatch."
    ::= { tmnxIpTunnelStatsEntry 33 }

    tmnxIpTunnelEncapOverhead       OBJECT-TYPE
    SYNTAX      Unsigned32
    MAX-ACCESS  read-only
    STATUS      current
    DESCRIPTION
        "The value of tmnxIpTunnelEncapOverhead indicates the encapsulation
         overhead for this IP Tunnel."
    ::= { tmnxIpTunnelStatsEntry 34 }

tmnxIpTunnelPreEncapFragCount   OBJECT-TYPE
    SYNTAX      Counter64
    MAX-ACCESS  read-only
    STATUS      current
    DESCRIPTION
        "The value of tmnxIpTunnelPreEncapFragCount indicates the number
         of fragmentations that occurred prior to encapsulation for this
         IP Tunnel. Pre-encapsulation fragmentation occurs for IPv4 packets
         whose size exceeds tmnxIpTunnelIpMtu."
    ::= { tmnxIpTunnelStatsEntry 35 }

tmnxIpTunnelPreEncapFragLastSize   OBJECT-TYPE
    SYNTAX      Unsigned32
    MAX-ACCESS  read-only
    STATUS      current
    DESCRIPTION
        "The value of tmnxIpTunnelPreEncapFragLastSize indicates the size
         of the last packet which caused a pre-encapsulation fragmentation
         to occur for this IP Tunnel."
    ::= { tmnxIpTunnelStatsEntry 36 }

tmnxIpTunnelPostEncapFragCount   OBJECT-TYPE
    SYNTAX      Counter64
    MAX-ACCESS  read-only
    STATUS      current
    DESCRIPTION
        "The value of tmnxIpTunnelPostEncapFragCount indicates the number
         of fragmentations that occurred after encapsulation for this IP
         Tunnel. Post-encapsulation fragmentation occurs when the encapsulated
         packet size exceeds tmnxIpTunnelEncapIpMtu."
    ::= { tmnxIpTunnelStatsEntry 37 }

tmnxIpTunnelPostEncapFragLstSize   OBJECT-TYPE
    SYNTAX      Unsigned32
    MAX-ACCESS  read-only
    STATUS      current
    DESCRIPTION
        "The value of tmnxIpTunnelPostEncapFragLstSize indicates the size
         of the last encapsulated packet which caused a post-encapsulation
         fragmentation to occur for this IP Tunnel."
    ::= { tmnxIpTunnelStatsEntry 38 }
--
-- Extension to Base SAP Table
--
sapExtTableLastChanged OBJECT-TYPE
    SYNTAX      TimeStamp
    MAX-ACCESS  read-only
    STATUS      current
    DESCRIPTION
        "The value of sapExtTableLastChanged indicates the
         sysUpTime at the time of the last modification to 
         sapExtTable by adding, deleting an entry or change
         to a writable object in the table.

         If no changes were made to the table since the last 
         re-initialization of the local network management subsystem, 
         then this object contains a zero value."
    ::= { tmnxSapObjs 146 }

sapExtTable OBJECT-TYPE
    SYNTAX      SEQUENCE OF SapExtEntry
    MAX-ACCESS  not-accessible
    STATUS      current
    DESCRIPTION
        "The sapExtTable contains additional entries specific to SAPs
         in the system."
    ::= { tmnxSapObjs 147 }

sapExtEntry OBJECT-TYPE
    SYNTAX      SapExtEntry
    MAX-ACCESS  not-accessible
    STATUS      current
    DESCRIPTION
        "The sapExtEntry contains additional information about a single SAP
         entry."
    AUGMENTS { sapBaseInfoEntry }
    ::= { sapExtTable 1 }

SapExtEntry ::= SEQUENCE {
    sapExtLastChanged             TimeStamp,
    sapExtLagActivePort           TmnxPortID,
    sapDCpuProtPolicy             TNamedItemOrEmpty,
    sapCflowd                     INTEGER,
    sapStatHostMacLearnOptions    BITS
}

sapExtLastChanged  OBJECT-TYPE
    SYNTAX      TimeStamp
    MAX-ACCESS  read-only
    STATUS      current
    DESCRIPTION
        "The value of sapExtLastChanged indicates the sysUpTime
         at the time of the last modification of this entry."
    ::= { sapExtEntry 1 }

sapExtLagActivePort  OBJECT-TYPE
    SYNTAX      TmnxPortID
    MAX-ACCESS  read-only
    STATUS      current
    DESCRIPTION
        "The value of sapExtLagActivePort indicates a port on the lag
         associated with this SAP, that is used when tLagPerLinkHash
         is enabled on the lag or when sapLagLinkMapProfile is
         configured on this SAP."
    ::= { sapExtEntry 2 }

sapDCpuProtPolicy OBJECT-TYPE
    SYNTAX          TNamedItemOrEmpty
    MAX-ACCESS      read-create
    STATUS          current
    DESCRIPTION     
        "The value of sapDCpuProtPolicy associates Distributed CPU Protection
         Policy with a SAP."
    DEFVAL { ''H }
    ::= { sapExtEntry 3 }

sapCflowd  OBJECT-TYPE
    SYNTAX      INTEGER {
                    none        (1),
                    ingressOnly (3)
                }
    MAX-ACCESS  read-create
    STATUS      current
    DESCRIPTION
        "The value of sapCflowd specifies the type and direction of Cflowd
         analysis applied to this SAP. A Cflowd profile controls the sampling
         and analysis of data flows through the service.  A value of 'none (1)'
         indicates that there is no Cflowd analysis associated with this SAP."
    DEFVAL { none }
    ::= { sapExtEntry 4 }

sapStatHostMacLearnOptions OBJECT-TYPE
    SYNTAX          BITS {
                        singleMac (0),
                        dataTriggered (1)
                    }
    MAX-ACCESS      read-create
    STATUS          current
    DESCRIPTION     
        "The value of sapStatHostMacLearnOptions applies to the
         static hosts of this SAP.
         
         When the 'singleMac' option is set, this system ensures that
         there is at any time only a single MAC address per SAP, learned through ICMPv6. 
         When the 'dataTriggered' option is set, MAC learning is also triggered
         by data packets, as opposed to only by subscriber control plane packets
         such as DHCP or ARP.

         A bit in this object can only be set for a SAP in a group interface,
         that is each row in the sapBaseInfoTable where the value of
         sapIesIfIndex corresponds to a row in the vRtrIfTable
         where the value of vRtrIfType is equal to 'serviceIesGroup'
         or 'serviceVprnGroup'."
    DEFVAL { { } }
    ::= { sapExtEntry 5 }
    
-- Sap Static-Policer Stats Table

sapDcpFpStaticStatTable OBJECT-TYPE
    SYNTAX      SEQUENCE OF SapDcpFpStaticStatEntry
    MAX-ACCESS  not-accessible
    STATUS      current
    DESCRIPTION
        "The sapDcpFpStaticStatTable has the statistics information of
         the static-policer configured on Distributed CPU Protection Policy
         per SAP per forwarding plane."
    ::= { tmnxSapObjs 148 }

sapDcpFpStaticStatEntry  OBJECT-TYPE
    SYNTAX      SapDcpFpStaticStatEntry
    MAX-ACCESS  not-accessible
    STATUS      current
    DESCRIPTION
        "The value of sapDcpFpStaticStatEntry represents statistics 
         information per SAP per forwarding plane for the static-policer 
         configured on Distributed CPU Protection Policy."
    INDEX { svcId, sapPortId, sapEncapValue, tmnxChassisIndex, tmnxCardSlotNum,
            tmnxFPNum, sapDcpFpStaticPlcrName }
    ::= { sapDcpFpStaticStatTable 1 }

SapDcpFpStaticStatEntry ::= SEQUENCE {
    sapDcpFpStaticPlcrName           TNamedItem,
    sapDcpFpStaticState              TmnxDistCpuProtState,
    sapDcpFpStaticExcdCount          Counter64,
    sapDcpFpStaticExcdCountHi        Counter32,
    sapDcpFpStaticExcdCountLo        Counter32,
    sapDcpFpStaticHoldDown           TmnxDistCpuProtActionDuration,
    sapDcpFpStaticDetectionTime      Unsigned32
}

sapDcpFpStaticPlcrName  OBJECT-TYPE
    SYNTAX      TNamedItem
    MAX-ACCESS  not-accessible
    STATUS      current
    DESCRIPTION
        "The value of sapDcpFpStaticPlcrName specifies the 
         static-policer name for Distributed CPU Protection Policy."
    ::= { sapDcpFpStaticStatEntry 1 }

sapDcpFpStaticState  OBJECT-TYPE
    SYNTAX      TmnxDistCpuProtState
    MAX-ACCESS  read-only
    STATUS      current
    DESCRIPTION
        "The value of sapDcpFpStaticState indicates the state of the
         static-policer configured on Distributed CPU Protection Policy."
    ::= { sapDcpFpStaticStatEntry 2 }

sapDcpFpStaticExcdCount  OBJECT-TYPE
    SYNTAX      Counter64
    MAX-ACCESS  read-only
    STATUS      current
    DESCRIPTION
        "The value of sapDcpFpStaticExcdCount indicates number of packets
         exceeding the policing parameters since the given static-policer was 
         previously declared as conformant or newly instantiated."
    ::= { sapDcpFpStaticStatEntry 3 }

sapDcpFpStaticExcdCountHi  OBJECT-TYPE
    SYNTAX      Counter32
    MAX-ACCESS  read-only
    STATUS      current
    DESCRIPTION
        "The value of sapDcpFpStaticExcdCountHi indicates upper 32-bits of 
         sapDcpFpStaticExcdCount."
    ::= { sapDcpFpStaticStatEntry 4 }

sapDcpFpStaticExcdCountLo  OBJECT-TYPE
    SYNTAX      Counter32
    MAX-ACCESS  read-only
    STATUS      current
    DESCRIPTION
    "The value of sapDcpFpStaticExcdCountLo indicates lower 32-bits of 
     sapDcpFpStaticExcdCount."
    ::= { sapDcpFpStaticStatEntry 5 }

sapDcpFpStaticHoldDown  OBJECT-TYPE
    SYNTAX      TmnxDistCpuProtActionDuration
    UNITS       "seconds"
    MAX-ACCESS  read-only
    STATUS      current
    DESCRIPTION
        "The value of sapDcpFpStaticHoldDown indicates the remaining
         hold-down period for a given static-policer."
    ::= { sapDcpFpStaticStatEntry 6 }

sapDcpFpStaticDetectionTime  OBJECT-TYPE
    SYNTAX      Unsigned32
    UNITS       "seconds"
    MAX-ACCESS  read-only
    STATUS      current
    DESCRIPTION
        "The value of sapDcpFpStaticDetectionTime indicates the detection
         time remaining for a given static-policer."
    ::= { sapDcpFpStaticStatEntry 7 }

-- Sap Dynamic Policer (protocol)  Stats Table

sapDcpFpDynStatTable OBJECT-TYPE
    SYNTAX      SEQUENCE OF TmnxSapDcpFpDynStatEntry
    MAX-ACCESS  not-accessible
    STATUS      current
    DESCRIPTION
        "The sapDcpFpDynStatTable has the statistics information of the
         dynamic policer for a particular protocol configured on Distributed
         CPU Protection Policy per SAP per forwarding plane."
    ::= { tmnxSapObjs 149 }

sapDcpFpDynStatEntry  OBJECT-TYPE
    SYNTAX      TmnxSapDcpFpDynStatEntry
    MAX-ACCESS  not-accessible
    STATUS      current
    DESCRIPTION
        "The value of sapDcpFpDynStatEntry represents statistics 
         information per SAP per forwarding plane for the dynamic policer for a
         particular protocol configured on Distributed CPU Protection Policy."
    INDEX { svcId, sapPortId, sapEncapValue, tmnxChassisIndex, tmnxCardSlotNum,
            tmnxFPNum, sapDcpFpProtocol }
    ::= { sapDcpFpDynStatTable 1 }

TmnxSapDcpFpDynStatEntry ::= SEQUENCE {
    sapDcpFpProtocol              TmnxDistCpuProtProtocolId,
    sapDcpFpDynState              TmnxDistCpuProtState,
    sapDcpFpDynExcdCount          Counter64,
    sapDcpFpDynExcdCountHi        Counter32,
    sapDcpFpDynExcdCountLo        Counter32,
    sapDcpFpDynHoldDown           TmnxDistCpuProtActionDuration,
    sapDcpFpDynDetectionTime      Unsigned32,
    sapDcpFpDynAllocated          TruthValue
}

sapDcpFpProtocol  OBJECT-TYPE
    SYNTAX      TmnxDistCpuProtProtocolId
    MAX-ACCESS  not-accessible
    STATUS      current
    DESCRIPTION
        "The value of sapDcpFpProtocol specifies the protocol name to be 
         monitored by Distributed CPU Protection Policy."
    ::= { sapDcpFpDynStatEntry 1 }

sapDcpFpDynState  OBJECT-TYPE
    SYNTAX      TmnxDistCpuProtState
    MAX-ACCESS  read-only
    STATUS      current
    DESCRIPTION
        "The value of sapDcpFpDynState indicates the state of the dynamic 
         policer for a particular protocol configured on Distributed CPU
         Protection Policy."
    ::= { sapDcpFpDynStatEntry 2 }

sapDcpFpDynExcdCount  OBJECT-TYPE
    SYNTAX      Counter64
    MAX-ACCESS  read-only
   STATUS      current
    DESCRIPTION
        "The value of sapDcpFpDynExcdCount indicates number of packets
         exceeding the policing parameters since the dynamic policer for the 
         given protocol was previously declared as conformant or newly
         instantiated."
    ::= { sapDcpFpDynStatEntry 3 }

sapDcpFpDynExcdCountHi  OBJECT-TYPE
    SYNTAX      Counter32
    MAX-ACCESS  read-only
   STATUS      current
    DESCRIPTION
        "The value of sapDcpFpDynExcdCountHi indicates upper 32-bits of 
         sapDcpFpDynExcdCount."
    ::= { sapDcpFpDynStatEntry 4 }

sapDcpFpDynExcdCountLo  OBJECT-TYPE
    SYNTAX      Counter32
    MAX-ACCESS  read-only
   STATUS      current
    DESCRIPTION
        "The value of sapDcpFpDynExcdCountLo indicates lower 32-bits of 
         sapDcpFpDynExcdCount."
    ::= { sapDcpFpDynStatEntry 5 }

sapDcpFpDynHoldDown  OBJECT-TYPE
    SYNTAX      TmnxDistCpuProtActionDuration
    UNITS       "seconds"
    MAX-ACCESS  read-only
    STATUS      current
    DESCRIPTION
        "The value of sapDcpFpDynHoldDown indicates the remaining
         hold-down period for the dynamic policer for a given protocol."
    ::= { sapDcpFpDynStatEntry 6 }

sapDcpFpDynDetectionTime  OBJECT-TYPE
    SYNTAX      Unsigned32
    UNITS       "seconds"
    MAX-ACCESS  read-only
    STATUS      current
    DESCRIPTION
        "The value of sapDcpFpDynDetectionTime indicates the detection
         time remaining for the dynamic policer for a given protocol."
    ::= { sapDcpFpDynStatEntry 7 }

sapDcpFpDynAllocated  OBJECT-TYPE
    SYNTAX      TruthValue
    MAX-ACCESS  read-only
    STATUS      current
    DESCRIPTION
        "The value of sapDcpFpDynAllocated indicates whether dynamic 
         policer has been allocated for this protocol."
    ::= { sapDcpFpDynStatEntry 8 }

-- Sap Local-Mon-Policer Stats Table

sapDcpFpLocMonStatTable OBJECT-TYPE
    SYNTAX      SEQUENCE OF SapDcpFpLocMonStatEntry
    MAX-ACCESS  not-accessible
    STATUS      current
    DESCRIPTION
        "The sapDcpFpLocMonStatTable has the statistics information of
         the local-monitoring policer configured on Distributed CPU Protection
         Policy per SAP per forwarding plane."
    ::= { tmnxSapObjs 150 }

sapDcpFpLocMonStatEntry  OBJECT-TYPE
    SYNTAX      SapDcpFpLocMonStatEntry
    MAX-ACCESS  not-accessible
    STATUS      current
    DESCRIPTION
        "The value of sapDcpFpLocMonStatTable represents statistics 
         information per SAP per forwarding plane for the local-monitoring 
         policer configured on Distributed CPU Protection Policy."
    INDEX { svcId, sapPortId, sapEncapValue, tmnxChassisIndex, tmnxCardSlotNum,
            tmnxFPNum, sapDcpFpLocMonPlcrName }
    ::= { sapDcpFpLocMonStatTable 1 }

SapDcpFpLocMonStatEntry ::= SEQUENCE {
    sapDcpFpLocMonPlcrName           TNamedItem,
    sapDcpFpLocMonState              TmnxDistCpuProtState,
    sapDcpFpLocMonExcdCount          Counter64,
    sapDcpFpLocMonExcdCountHi        Counter32,
    sapDcpFpLocMonExcdCountLo        Counter32,
    sapDcpFpLocMonAllDynAlloc        TruthValue
}

sapDcpFpLocMonPlcrName  OBJECT-TYPE
    SYNTAX      TNamedItem
    MAX-ACCESS  not-accessible
    STATUS      current
    DESCRIPTION
        "The value of sapDcpFpLocMonPlcrName specifies the local monitoring
         policy name for Distributed CPU Protection Policy."
    ::= { sapDcpFpLocMonStatEntry 1 }

sapDcpFpLocMonState  OBJECT-TYPE
    SYNTAX      TmnxDistCpuProtState
    MAX-ACCESS  read-only
    STATUS      current
    DESCRIPTION
        "The value of sapDcpFpLocMonState indicates the state of the 
         local-monitoring policer configured on Distributed CPU Protection
         Policy."
    ::= { sapDcpFpLocMonStatEntry 2 }

sapDcpFpLocMonExcdCount  OBJECT-TYPE
    SYNTAX      Counter64
    MAX-ACCESS  read-only
    STATUS      current
    DESCRIPTION
        "The value of sapDcpFpLocMonExcdCount indicates number of packets
         exceeding the policing parameters since the given local-monitoring 
         policer was previously declared as conformant or newly instantiated."
    ::= { sapDcpFpLocMonStatEntry 3 }

sapDcpFpLocMonExcdCountHi  OBJECT-TYPE
    SYNTAX      Counter32
    MAX-ACCESS  read-only
    STATUS      current
    DESCRIPTION
        "The value of sapDcpFpLocMonExcdCountHi indicates upper 32-bits of 
         sapDcpFpLocMonExcdCount."
    ::= { sapDcpFpLocMonStatEntry 4 }

sapDcpFpLocMonExcdCountLo  OBJECT-TYPE
    SYNTAX      Counter32
    MAX-ACCESS  read-only
    STATUS      current
    DESCRIPTION
        "The value of sapDcpFpLocMonExcdCountLo indicates lower 32-bits of 
         sapDcpFpLocMonExcdCount."
    ::= { sapDcpFpLocMonStatEntry 5}

sapDcpFpLocMonAllDynAlloc  OBJECT-TYPE
    SYNTAX      TruthValue
    MAX-ACCESS  read-only
    STATUS      current
    DESCRIPTION
        "The value of sapDcpFpLocMonAllDynAlloc indicates whether all the 
         dynamic policers associated with this local-monitor have been
         allocated."
    ::= { sapDcpFpLocMonStatEntry 6 }

-- --------------------------------------------------
-- sap Static ISID policy table
-- --------------------------------------------------
sapTlsStaticIsidRngTable OBJECT-TYPE
    SYNTAX          SEQUENCE OF SapTlsStaticIsidRngEntry
    MAX-ACCESS      not-accessible
    STATUS          current
    DESCRIPTION
        "This table maintains the static ISID range information 
         for SAPs."
    ::= { tmnxSapObjs 152 } 
    
sapTlsStaticIsidRngEntry OBJECT-TYPE
    SYNTAX          SapTlsStaticIsidRngEntry
    MAX-ACCESS      not-accessible
    STATUS          current
    DESCRIPTION
        "This entry maintains the static range information 
         for a specific SAP in a specific VPLS service ."
    INDEX  { svcId, sapPortId, sapEncapValue, sapTlsStaticIsidRngId }
    ::= { sapTlsStaticIsidRngTable 1 }

SapTlsStaticIsidRngEntry ::=
    SEQUENCE {
        sapTlsStaticIsidRngId              Unsigned32,
        sapTlsStaticIsidRngRowStatus       RowStatus,
        sapTlsStaticIsidRngLastChanged     TimeStamp,
        sapTlsStaticIsidRngLow             TmnxISID,
        sapTlsStaticIsidRngHigh            TmnxISID
    }
    
sapTlsStaticIsidRngId OBJECT-TYPE
    SYNTAX       Unsigned32 (1..8191)
    MAX-ACCESS   not-accessible
    STATUS       current
    DESCRIPTION     
        "The value of sapTlsStaticIsidRngId specifies the range identifier for
         the ISID policy."
    ::= { sapTlsStaticIsidRngEntry 1 }

sapTlsStaticIsidRngRowStatus OBJECT-TYPE
    SYNTAX       RowStatus
    MAX-ACCESS   read-create
    STATUS       current
    DESCRIPTION  
         "The value of sapTlsStaticIsidRngRowStatus is used for the creation and 
          deletion of rows in this table."
    ::= { sapTlsStaticIsidRngEntry 2 }   

sapTlsStaticIsidRngLastChanged OBJECT-TYPE
    SYNTAX       TimeStamp
    MAX-ACCESS   read-only
    STATUS       current
    DESCRIPTION  
        "The value of sapTlsStaticIsidRngLastChanged indicates the timestamp of
         last change to this row in sapTlsStaticIsidRngTable."
    ::= { sapTlsStaticIsidRngEntry 3 }  
    
sapTlsStaticIsidRngLow OBJECT-TYPE
    SYNTAX       TmnxISID
    MAX-ACCESS   read-create
    STATUS       current
    DESCRIPTION  
         "The value of sapTlsStaticIsidRngLow specifies the low value of the
          range for this entry."
    DEFVAL { 0 }
    ::= { sapTlsStaticIsidRngEntry 4 }   

sapTlsStaticIsidRngHigh OBJECT-TYPE
    SYNTAX       TmnxISID
    MAX-ACCESS   read-create
    STATUS       current
    DESCRIPTION  
         "The value of sapTlsStaticIsidRngHigh specifies the high value of the
          range for this entry."
    DEFVAL { 0 }
    ::= { sapTlsStaticIsidRngEntry 5 }   

-- --------------------------------------------------
-- sap Static ISID table
-- --------------------------------------------------
sapTlsStaticIsidTable OBJECT-TYPE
    SYNTAX          SEQUENCE OF SapTlsStaticIsidEntry
    MAX-ACCESS      not-accessible
    STATUS          current
    DESCRIPTION
        "This table maintains the information for each static ISID for SAPs."
    ::= { tmnxSapObjs 154 } 
    
sapTlsStaticIsidEntry OBJECT-TYPE
    SYNTAX          SapTlsStaticIsidEntry
    MAX-ACCESS      not-accessible
    STATUS          current
    DESCRIPTION
        "This entry maintains the information for a specific ISID associated
         with the specific SAP in a specific VPLS service.
         
         Entries are created and deleted by the system."
    INDEX  { svcId, sapPortId, sapEncapValue, sapTlsStaticIsid }
    ::= { sapTlsStaticIsidTable 1 }

SapTlsStaticIsidEntry ::=
    SEQUENCE {
        sapTlsStaticIsid             TmnxISID,
        sapTlsStaticIsidStatus       TmnxIsidMFibStatus
    }
    
sapTlsStaticIsid OBJECT-TYPE
    SYNTAX       TmnxISID
    MAX-ACCESS   not-accessible
    STATUS       current
    DESCRIPTION  
         "The value of sapTlsStaticIsid indicates ISID of this entry."
    ::= { sapTlsStaticIsidEntry 1 }   

sapTlsStaticIsidStatus OBJECT-TYPE
    SYNTAX       TmnxIsidMFibStatus
    MAX-ACCESS   read-only
    STATUS       current
    DESCRIPTION  
         "The value of sapTlsStaticIsidStatus indicates the MFIB status of this
          ISID."
    ::= { sapTlsStaticIsidEntry 2 }   


-- ----------------------------------
-- SAP Ethernet Loopback Table
-- ----------------------------------
sapEthLoopbackTable              OBJECT-TYPE
    SYNTAX      SEQUENCE OF SapEthLoopbackEntry
    MAX-ACCESS  not-accessible
    STATUS      current
    DESCRIPTION "The table sapEthLoopbackTable provides operators with the
                 ability to provide loopback functions on a specific SAP in
                 order to test Ethernet Virtual Circuits (EVC)."
    ::= { tmnxSapObjs 155 }

sapEthLoopbackEntry              OBJECT-TYPE
    SYNTAX      SapEthLoopbackEntry
    MAX-ACCESS  not-accessible
    STATUS      current
    DESCRIPTION "Each entry represents an active SAP loopback. The SAP is
                 placed in loopback by row creation and is removed by row
                 destruction.

                 Rows in table sapEthLoopbackTable are created and destroyed
                 by SNMP set operations on the object sapEthLoopbackRowStatus.
                 Rows in table sapEthLoopbackTable may be destroyed by the
                 system when the associated SAP has been deleted. A maximum of
                 64 rows may be created. Rows are kept in volatile storage and
                 lost upon a system reboot."
    INDEX { svcId, sapPortId, sapEncapValue }
    ::= { sapEthLoopbackTable 1 }

SapEthLoopbackEntry ::=
    SEQUENCE {
        sapEthLoopbackRowStatus       RowStatus,
        sapEthLoopbackMode            INTEGER,
        sapEthLoopbackMacSwap         TmnxEnabledDisabled,
        sapEthLoopbackMacSwapAddr     MacAddress,
        sapEthLoopbackMacSwapAddrAll  TruthValue
    }

sapEthLoopbackRowStatus          OBJECT-TYPE
    SYNTAX      RowStatus
    MAX-ACCESS  read-create
    STATUS      current
    DESCRIPTION "The value of the object sapEthLoopbackRowStatus specifies
                 the row status. It allows entries to be created and deleted in
                 sapEthLoopbackTable.

                 Rows are created by specifying the value 'createAndGo(4)' and
                 deleted by specifying the value 'destroy(6)'. If the
                 associated SAP is deleted, the sapEthLoopbackEntry row will be
                 deleted by the system.

                 Row creation will fail if the service identifier and the SAP
                 do not exist in MIB table sapBaseInfoTable with a sapType of
                 'epipe(1)' or 'tls(3)', which encompasses EPIPE, PBB (Provider
                 Backbone Bridging) EPIPE, VPLS (Virtual Private LAN Service),
                 and I-VPLS services."
    ::= { sapEthLoopbackEntry 1 }

sapEthLoopbackMode               OBJECT-TYPE
    SYNTAX      INTEGER {
                    ingress (1),
                    egress  (2)
                }
    MAX-ACCESS  read-create
    STATUS      current
    DESCRIPTION "The value of the object sapEthLoopbackMode specifies how
                 traffic will be reflected.

                 If the value is set to 'ingress(1)', traffic arriving at the
                 SAP ingress will be reflected back out the same SAP. If the
                 value is set to 'egress(2)', traffic arriving at the SAP
                 egress will be reflected back into the service in the
                 direction of the original source."
    ::= { sapEthLoopbackEntry 2 }

sapEthLoopbackMacSwap            OBJECT-TYPE
    SYNTAX      TmnxEnabledDisabled
    MAX-ACCESS  read-create
    STATUS      current
    DESCRIPTION "The value of the object sapEthLoopbackMacSwap specifies the
                 enabling or disabling of source address and destination
                 address swapping for the reflected packets when the arriving
                 packet is unicast. With sapEthLoopbackMacSwap enabled, any
                 broadcast or multicast packets arriving on a looped point will
                 be dropped."
    DEFVAL { disabled }
    ::= { sapEthLoopbackEntry 3 }

sapEthLoopbackMacSwapAddr        OBJECT-TYPE
    SYNTAX      MacAddress
    MAX-ACCESS  read-create
    STATUS      current
    DESCRIPTION "The value of the object sapEthLoopbackMacSwapAddr specifies
                 the source MAC address used in the reflected packet when the
                 arriving packet is broadcast or multicast. This does not
                 apply to arriving unicast packets."
    DEFVAL { '000000000000'h }
    ::= { sapEthLoopbackEntry 4 }

sapEthLoopbackMacSwapAddrAll     OBJECT-TYPE
    SYNTAX      TruthValue
    MAX-ACCESS  read-create
    STATUS      current
    DESCRIPTION "The value of the object sapEthLoopbackMacSwapAddrAll specifies
                 whether or not to use the configured sapEthLoopbackMacSwapAddr
                 as the source address for all reflected parameters."
    DEFVAL { false }
    ::= { sapEthLoopbackEntry 5 }

-- -------------------------------------------------------------
-- count of MAC address entries of different FDB type in a vpls
-- -------------------------------------------------------------
sapTlsFdbMacStatsTable OBJECT-TYPE
    SYNTAX          SEQUENCE OF SapTlsFdbMacStatsEntry
    MAX-ACCESS      not-accessible
    STATUS          current
    DESCRIPTION
        "This table maintains the count of MAC address entries per FDB
         type for the SAPs in VPLS services."
    ::= { tmnxSapObjs 156 } 
    
sapTlsFdbMacStatsEntry OBJECT-TYPE
    SYNTAX          SapTlsFdbMacStatsEntry
    MAX-ACCESS      not-accessible
    STATUS          current
    DESCRIPTION
        "This entry maintains the count of MAC address entries per FDB
         type for the SAP in a VPLS service."
    INDEX   { svcId, sapPortId, sapEncapValue, tlsFdbType }
    ::= { sapTlsFdbMacStatsTable 1 }

SapTlsFdbMacStatsEntry ::=
    SEQUENCE {
        sapTlsFdbMacStatsNumEntries Unsigned32
    }

sapTlsFdbMacStatsNumEntries OBJECT-TYPE
    SYNTAX Unsigned32
    MAX-ACCESS read-only
    STATUS current
    DESCRIPTION
        "The value of sapTlsFdbMacStatsNumEntries indicates the number of MAC
         address entries of the FDB type in the SAP in this service."
    ::= { sapTlsFdbMacStatsEntry 1 }


-- -------------------------------------
-- TLS SAP Extended Table
-- -------------------------------------
tmnxSapTlsExInfoTable OBJECT-TYPE
    SYNTAX          SEQUENCE OF TmnxSapTlsExInfoEntry
    MAX-ACCESS      not-accessible
    STATUS          current
    DESCRIPTION
        "This table is an augment of the sapTlsInfoTable table.
         Rows are created and destroyed automatically by the system."
    ::= { tmnxSapObjs 157 }

tmnxSapTlsExInfoEntry OBJECT-TYPE
    SYNTAX          TmnxSapTlsExInfoEntry
    MAX-ACCESS      not-accessible
    STATUS          current
    DESCRIPTION     "TLS specific information about a SAP."
    AUGMENTS { sapTlsInfoEntry }
    ::= { tmnxSapTlsExInfoTable 1 }

TmnxSapTlsExInfoEntry ::=
    SEQUENCE {
        tmnxSapTlsExLastChanged           TimeStamp,
        tmnxSapTlsExDhcpPythonPolicy      TNamedItemOrEmpty,
        tmnxSapTlsExDhcp6PythonPolicy     TNamedItemOrEmpty,
        tmnxSapTlsExRtrSolMsapTrigger     TruthValue,
        tmnxSapTlsExRtrSolUserDb          TNamedItemOrEmpty,
        tmnxSapTlsExProcCpmTrfcSapDn    TmnxEnabledDisabled,
        tmnxSapTlsExDiameterAuthPolicy   TNamedItemOrEmpty
    }

tmnxSapTlsExLastChanged OBJECT-TYPE
    SYNTAX      TimeStamp
    MAX-ACCESS  read-only
    STATUS      current
    DESCRIPTION
        "The value tmnxSapTlsExLastChanged indicates the sysUpTime at
         the time of the most recent management-initiated change to this
         row."
    ::= { tmnxSapTlsExInfoEntry 1 }

tmnxSapTlsExDhcpPythonPolicy OBJECT-TYPE
    SYNTAX      TNamedItemOrEmpty
    MAX-ACCESS  read-write
    STATUS      current
    DESCRIPTION
        "The value of tmnxSapTlsExDhcpPythonPolicy specifies the name of
         the Python policy used for DHCP discover on this SAP.

         The Python policy referenced here needs to exist in the
         TIMETRA-PYTHON-MIB::tmnxPythonPolicyTable."
    DEFVAL { "" }
    ::= { tmnxSapTlsExInfoEntry 2 }

tmnxSapTlsExDhcp6PythonPolicy OBJECT-TYPE
    SYNTAX      TNamedItemOrEmpty
    MAX-ACCESS  read-write
    STATUS      current
    DESCRIPTION
        "The value of tmnxSapTlsExDhcp6PythonPolicy specifies the name of
         the Python policy used for DHCP6 solicit on this SAP.

         The Python policy referenced here needs to exist in the
         TIMETRA-PYTHON-MIB::tmnxPythonPolicyTable."
    DEFVAL { "" }
    ::= { tmnxSapTlsExInfoEntry 3 }

tmnxSapTlsExRtrSolMsapTrigger OBJECT-TYPE
    SYNTAX          TruthValue
    MAX-ACCESS      read-write
    STATUS          current
    DESCRIPTION
        "The value of tmnxSapTlsExRtrSolMsapTrigger specifies
         whether the receipt of router solicit trigger packets
         on a VPLS SAP with a sapSubType value of 'capture'
         will result in a Radius authentication that will provide
         a service context and the creation of a SAP with a
         sapSubType value of 'managed'.

         An attempt to set the value tmnxSapTlsExRtrSolMsapTrigger
         to 'true' on a SAP with sapSubType other than 'capture'
         will return an 'inconsistentValue' error."
    DEFVAL         { false }
    ::= { tmnxSapTlsExInfoEntry 4 }

tmnxSapTlsExRtrSolUserDb OBJECT-TYPE
    SYNTAX          TNamedItemOrEmpty
    MAX-ACCESS      read-write
    STATUS          current
    DESCRIPTION
        "The value of tmnxSapTlsExRtrSolUserDb specifies the local
         user database to use for router solicit based authentication.

         If no authentication with the local user database is required,
         the value of this object must be set to the empty string.

         The value of tmnxSapTlsExRtrSolUserDb is only valid for a
         SAP with a sapSubType value of 'capture'. If the value is
         set to a  non-empty string for a SAP with a sapSubType
         value other than 'capture', an 'inconsistentValue' error
         will be returned."
    DEFVAL         { "" }
    ::= { tmnxSapTlsExInfoEntry 5 }

tmnxSapTlsExProcCpmTrfcSapDn OBJECT-TYPE
    SYNTAX          TmnxEnabledDisabled
    MAX-ACCESS      read-write
    STATUS          current
    DESCRIPTION
        "The value of tmnxSapTlsExProcCpmTrfcSapDn is applicable to simple SAPs
         configured on simple LAGs that are not part of any 'endpoint'
         configurations or complicated resiliency schemes like MC-LAG with
         inter-chassis-backup (ICB) configurations.

         When enabled, a simple LAG SAP will not be removed from the forwarding
         plane and flooded traffic (unknown unicast, broadcast and multicast)
         will be dropped on egress rather than ingress.This allows control
         traffic to be extracted on egress and where applicable processed by
         the CPM.

         The value of tmnxSapTlsExProcCpmTrfcSapDn will not prevent a VPLS
         service from entering an Operational Down state if it is the last
         active connection to enter a non-operational state. By default, without
         this value, when a LAG enters a non-operational state it is removed
         from the forwarding plane and traffic is dropped on ingress."
    DEFVAL { disabled }
    ::= { tmnxSapTlsExInfoEntry 6 }

tmnxSapTlsExDiameterAuthPolicy OBJECT-TYPE
    SYNTAX      TNamedItemOrEmpty
    MAX-ACCESS  read-write
    STATUS      current
    DESCRIPTION
        "The value of tmnxSapTlsExDiameterAuthPolicy specifies the name of
         the Diameter NASREQ application policy used for authentication.
         
         A non empty value is only allowed for a SAP with a sapSubType value of 'capture'.

         A non empty value must correspond to a row in the TIMETRA-DIAMETER-MIB::tmnxDiamApNqTable."
    DEFVAL { "" }
    ::= { tmnxSapTlsExInfoEntry 7 }


--
-- Extension to Base SAP Table
--
sapLagPerLinkHashTableLastChgd OBJECT-TYPE
    SYNTAX      TimeStamp
    MAX-ACCESS  read-only
    STATUS      current
    DESCRIPTION
        "The value of sapLagPerLinkHashTableLastChgd indicates the
         sysUpTime at the time of the last modification to 
         sapLagPerLinkHashTable by adding, deleting an entry or change
         to a writable object in the table.

         If no changes were made to the table since the last 
         re-initialization of the local network management subsystem, 
         then this object contains a zero value."
    ::= { tmnxSapObjs 158 }

sapLagPerLinkHashTable OBJECT-TYPE
    SYNTAX      SEQUENCE OF SapLagPerLinkHashEntry
    MAX-ACCESS  not-accessible
    STATUS      current
    DESCRIPTION
        "The sapLagPerLinkHashTable maintains weighted per-link-hash related
         lag attributes per SAP. A LAG that has weighted per link hash enabled,
         will use the class and weight associated with the SAP to select a link
         for egress traffic over this SAP. Selection is done such that within
         each class the total weight of all SAPs/Users on each LAG link is as
         close as possible to other links in the LAG." 
    ::= { tmnxSapObjs 159 }

sapLagPerLinkHashEntry OBJECT-TYPE
    SYNTAX      SapLagPerLinkHashEntry
    MAX-ACCESS  not-accessible
    STATUS      current
    DESCRIPTION
        "The sapLagPerLinkHashEntry maintains weighted per-link-hash related lag
         attributes for specific SAP."
    INDEX           { svcId, sapPortId, sapEncapValue }
    ::= { sapLagPerLinkHashTable 1 }

SapLagPerLinkHashEntry ::= SEQUENCE {
    sapLagPerLinkHashLastChanged       TimeStamp,
    sapLagPerLinkHashClass             TmnxLagPerLinkHashClass,
    sapLagPerLinkHashWeight            TmnxLagPerLinkHashWeight,
    sapLagPerLinkHashOperClass         TmnxLagPerLinkHashClass,
    sapLagPerLinkHashOperWeight        TmnxLagPerLinkHashWeight,
    sapLagPerLinkHashIsOverriden       TruthValue
}

sapLagPerLinkHashLastChanged  OBJECT-TYPE
    SYNTAX      TimeStamp
    MAX-ACCESS  read-only
    STATUS      current
    DESCRIPTION
        "The value of sapLagPerLinkHashLastChanged indicates the sysUpTime
         at the time of the last modification of this entry."
    ::= { sapLagPerLinkHashEntry 1 }

sapLagPerLinkHashClass  OBJECT-TYPE
    SYNTAX      TmnxLagPerLinkHashClass
    MAX-ACCESS  read-create
    STATUS      current
    DESCRIPTION
        "The value of sapLagPerLinkHashClass specifies the class to be used
         to select a LAG link for this SAP."
    DEFVAL { 1 }
    ::= { sapLagPerLinkHashEntry 2 }

sapLagPerLinkHashWeight  OBJECT-TYPE
    SYNTAX      TmnxLagPerLinkHashWeight
    MAX-ACCESS  read-create
    STATUS      current
    DESCRIPTION
        "The value of sapLagPerLinkHashWeight specifies the weight to be
         associated with this SAP when selecting a LAG link for this SAP."
    DEFVAL { 1 }
    ::= { sapLagPerLinkHashEntry 3 }

sapLagPerLinkHashOperClass  OBJECT-TYPE
    SYNTAX      TmnxLagPerLinkHashClass
    MAX-ACCESS  read-only
    STATUS      current
    DESCRIPTION
        "The value of sapLagPerLinkHashOperClass indicates the operational value
         for class associated with this SAP."
    ::= { sapLagPerLinkHashEntry 4 }

sapLagPerLinkHashOperWeight  OBJECT-TYPE
    SYNTAX      TmnxLagPerLinkHashWeight
    MAX-ACCESS  read-only
    STATUS      current
    DESCRIPTION
        "The value of sapLagPerLinkHashOperWeight indicates the operational
         value used for weight associated with this SAP."
    ::= { sapLagPerLinkHashEntry 5 }

sapLagPerLinkHashIsOverriden  OBJECT-TYPE
    SYNTAX      TruthValue
    MAX-ACCESS  read-only
    STATUS      current
    DESCRIPTION
        "The value of sapLagPerLinkHashIsOverriden indicates whether 
         administrative values, subscriber management determined operational
         weight and class are used for this SAP."
    ::= { sapLagPerLinkHashEntry 6 }

-- ----------------------------------------
-- SAP IPoE Table
-- ----------------------------------------
tmnxSapIpoeTableLastChanged      OBJECT-TYPE
    SYNTAX      TimeStamp
    MAX-ACCESS  read-only
    STATUS      current
    DESCRIPTION
        "The value of tmnxSapIpoeTableLastChanged indicates the 
         sysUpTime at the time of the most recent change to the
         tmnxSapIpoeTable."
    ::= { tmnxSapObjs 160 }

tmnxSapIpoeTable                 OBJECT-TYPE
    SYNTAX      SEQUENCE OF TmnxSapIpoeEntry
    MAX-ACCESS  not-accessible
    STATUS      current
    DESCRIPTION     
        "The table tmnxSapIpoeTable  contains IPoE session information related
         to a SAP with a sapSubType value of 'capture'."
    ::= { tmnxSapObjs 161 }

tmnxSapIpoeEntry                 OBJECT-TYPE
    SYNTAX      TmnxSapIpoeEntry
    MAX-ACCESS  not-accessible
    STATUS      current
    DESCRIPTION     
       "Each row entry represents information related to IPoE session for
        a SAP with a sapSubType value of 'capture'."
    INDEX { svcId, sapPortId, sapEncapValue }
    ::= { tmnxSapIpoeTable 1 }

TmnxSapIpoeEntry ::=
    SEQUENCE {
        tmnxSapIpoeLastChanged           TimeStamp,
        tmnxSapIpoeAdminState            TmnxEnabledDisabled,
        tmnxSapIpoeDescription           TItemDescription,
        tmnxSapIpoePolicy                TNamedItemOrEmpty,
        tmnxSapIpoeUserDb                TNamedItemOrEmpty
        }

tmnxSapIpoeLastChanged           OBJECT-TYPE
    SYNTAX      TimeStamp
    MAX-ACCESS  read-only
    STATUS      current
    DESCRIPTION
        "The value of tmnxSapIpoeLastChanged indicates the sysUpTime
         at the time of the most recent change to this
         table row."
    ::= { tmnxSapIpoeEntry 1 }
    
tmnxSapIpoeAdminState            OBJECT-TYPE
    SYNTAX      TmnxEnabledDisabled
    MAX-ACCESS  read-write
    STATUS      current
    DESCRIPTION 
        "The value of the object tmnxSapIpoeAdminState specifies the
         desired administrative state of this row."
    DEFVAL { disabled }
    ::= { tmnxSapIpoeEntry 2 }

tmnxSapIpoeDescription           OBJECT-TYPE
    SYNTAX      TItemDescription
    MAX-ACCESS  read-write
    STATUS      current
    DESCRIPTION 
        "The value of the object tmnxSapIpoeDescription specifies a user
         provided description for IPoE on this Sap."
    DEFVAL { "" }
    ::= { tmnxSapIpoeEntry 3 }

tmnxSapIpoePolicy                OBJECT-TYPE
    SYNTAX      TNamedItemOrEmpty
    MAX-ACCESS  read-write
    STATUS      current
    DESCRIPTION
        "The value of tmnxSapIpoePolicy specifies the IPoE policy
         applicable on this SAP."
    DEFVAL { "" }
    ::= { tmnxSapIpoeEntry 4 }
    
tmnxSapIpoeUserDb                OBJECT-TYPE
    SYNTAX      TNamedItemOrEmpty
    MAX-ACCESS  read-write
    STATUS      current
    DESCRIPTION
        "The value of tmnxSapIpoeUserDb specifies the local user database to
         use for authentication.

         If no authentication with the local user database is required,
         the value of this object must be set to the empty string."
    DEFVAL { "" }
    ::= { tmnxSapIpoeEntry 5 }
    
-- ------------------------------
-- IPv6 static hosts
-- ------------------------------

tmnxStaticHostIpv6Objs   OBJECT IDENTIFIER ::= { tmnxSapObjs 162 }


-- SAP Static Host IPv6 Table

sapStatHost6TableLastChanged OBJECT-TYPE
    SYNTAX      TimeStamp
    MAX-ACCESS  read-only
    STATUS      current
    DESCRIPTION
        "The value of sapStatHost6TableLastChanged indicates the
         sysUpTime at the time of the last modification to the
         sapStatHost6Table by adding, deleting an entry or change
         to a writable object in the table.

         If no changes were made to the table since the last 
         re-initialization of the local network management subsystem, 
         then this object contains a zero value."
    ::= { tmnxSapObjs 163 }

sapStatHost6Table OBJECT-TYPE
    SYNTAX          SEQUENCE OF SapStatHost6Entry
    MAX-ACCESS      not-accessible
    STATUS          current
    DESCRIPTION     "The sapStatHost6Table is used to configure IPv6 static hosts
                     on a SAP."
    ::= { tmnxStaticHostIpv6Objs 1 }

sapStatHost6Entry OBJECT-TYPE
    SYNTAX          SapStatHost6Entry
    MAX-ACCESS      not-accessible
    STATUS          current
    DESCRIPTION     "Each row entry represents information on a statically
                     configured IPv6 host. 
                     
                     Entries can be created and deleted via
                     SNMP SET operations."
    INDEX           { svcId,
                      sapPortId,
                      sapEncapValue,
                      sapStatHost6IpAddress,
                      sapStatHost6MacAddress }
    ::= { sapStatHost6Table 1 }

SapStatHost6Entry ::=
    SEQUENCE {
        sapStatHost6IpAddress            InetAddressIPv6,
        sapStatHost6MacAddress           MacAddress,
        sapStatHost6LastChanged          TimeStamp,
        sapStatHost6RowStatus            RowStatus,
        sapStatHost6AdminStatus          ServiceAdminStatus,
        sapStatHost6PrefixLen            InetAddressPrefixLength,
        sapStatHost6NextHopAddrType      InetAddressType,
        sapStatHost6NextHopAddr          InetAddress,
        sapStatHost6SubscrIdent          DisplayString,
        sapStatHost6SubProfile           ServObjName,
        sapStatHost6SlaProfile           ServObjName,
        sapStatHost6ShcvOperState        ServShcvOperState,
        sapStatHost6ShcvChecks           Unsigned32,
        sapStatHost6ShcvReplies          Unsigned32,
        sapStatHost6ShcvReplyTime        TimeStamp,
        sapStatHost6DynMacAddress        MacAddress,
        sapStatHost6RetailerSvcId        TmnxServId,
        sapStatHost6RetailerIf           InterfaceIndexOrZero,
        sapStatHost6FwdingState          TmnxOperState,
        sapStatHost6AncpString           TmnxAncpStringOrZero,
        sapStatHost6SubIdIsSapId         TruthValue,
        sapStatHost6AppProfile           ServObjName,
        sapStatHost6IntermediateDestId   DisplayString,
        sapStatHost6AdminRetailSvcId  TmnxServId
    }

sapStatHost6IpAddress OBJECT-TYPE
    SYNTAX          InetAddressIPv6
    MAX-ACCESS      not-accessible
    STATUS          current
    DESCRIPTION     "The value of the object sapStatHost6IpAddress specifies
                     the IP address of this static host."
    ::= { sapStatHost6Entry 1 }

sapStatHost6MacAddress OBJECT-TYPE
    SYNTAX          MacAddress
    MAX-ACCESS      not-accessible
    STATUS          current
    DESCRIPTION     "The value of the object sapStatHost6MacAddress specifies
                     the MAC address associated with this static host.
                     
                     The value 0:0:0:0:0:0 specifies 'no MAC address'."
    ::= { sapStatHost6Entry 2 }

sapStatHost6LastChanged OBJECT-TYPE
    SYNTAX          TimeStamp
    MAX-ACCESS      read-only
    STATUS          current
    DESCRIPTION     "The value of sapStatHost6LastChanged indicates
                     the sysUpTime at the time of the last modification
                     of this conceptual row."
    ::= { sapStatHost6Entry 3 }

sapStatHost6RowStatus OBJECT-TYPE
    SYNTAX          RowStatus
    MAX-ACCESS      read-create
    STATUS          current
    DESCRIPTION     "The value of the object sapStatHost6RowStatus controls
                     the creation and deletion of rows in this table."
    ::= { sapStatHost6Entry 4 }

sapStatHost6AdminStatus OBJECT-TYPE
    SYNTAX          ServiceAdminStatus
    MAX-ACCESS      read-create
    STATUS          current
    DESCRIPTION     "The value of sapStatHost6AdminStatus specifies
                     the administrative status of this host."
    DEFVAL          { down }
    ::= { sapStatHost6Entry 5 }

sapStatHost6PrefixLen OBJECT-TYPE
    SYNTAX          InetAddressPrefixLength (32..64 | 128)
    MAX-ACCESS      read-create
    STATUS          current
    DESCRIPTION
                    "The value of the object sapStatHost6PrefixLen specifies
                     the IPv6 address prefix length associated with this host.
                    
                     A value for this object must be specified when the conceptual
                     row is created, and it cannot be modified afterwards."
    ::= { sapStatHost6Entry 6 }
    
sapStatHost6NextHopAddrType  OBJECT-TYPE
    SYNTAX          InetAddressType
    MAX-ACCESS      read-create
    STATUS          current
    DESCRIPTION
                    "The value of sapStatHost6NextHopAddrType specifies the address 
                     type of sapStatHost6NextHopAddr."
    DEFVAL { unknown }
    ::= { sapStatHost6Entry 7 }

sapStatHost6NextHopAddr  OBJECT-TYPE
    SYNTAX          InetAddress (SIZE (0|4))
    MAX-ACCESS      read-create
    STATUS          current
    DESCRIPTION
                    "The value of sapStatHost6NextHopAddr specifies
                     the IPv4 next hop address of this IPv6 static host.
                     
                     A non-empty value of this object refers to the associated
                     IPv4 host in a dual stack model.

                     A MAC address learned from either IPv6 or IPv4 host is also
                     associated with the other ('mac-linking')."
    DEFVAL { ''H }
    ::= { sapStatHost6Entry 8 }
    
sapStatHost6SubscrIdent OBJECT-TYPE
    SYNTAX          DisplayString (SIZE (0..32))
    MAX-ACCESS      read-create
    STATUS          current
    DESCRIPTION     "The value of the object sapStatHost6SubscrIdent specifies
                     the subscriber identification for this static host."
    DEFVAL          { "" }
    ::= { sapStatHost6Entry 9 }

sapStatHost6SubProfile OBJECT-TYPE
    SYNTAX          ServObjName
    MAX-ACCESS      read-create
    STATUS          current
    DESCRIPTION     "The value of the object sapStatHost6SubProfile specifies
                     the subscriber profile for this static host. 
                     
                     A non-empty value of this object must correspond to
                     a conceptual row in the
                     TIMETRA-SUBSCRIBER-MGMT-MIB::tmnxSubProfileTable."
    DEFVAL          { "" }
    ::= { sapStatHost6Entry 10 }

sapStatHost6SlaProfile OBJECT-TYPE
    SYNTAX          ServObjName
    MAX-ACCESS      read-create
    STATUS          current
    DESCRIPTION     "The value of the object sapStatHost6SlaProfile specifies
                     the SLA profile for this static host. 
                     
                     A non-empty value of this object must correspond to
                     a conceptual row in the
                     TIMETRA-SUBSCRIBER-MGMT-MIB::tmnxSLAProfileTable."
    DEFVAL          { "" }
    ::= { sapStatHost6Entry 11 }

sapStatHost6ShcvOperState OBJECT-TYPE
    SYNTAX          ServShcvOperState
    MAX-ACCESS      read-only
    STATUS          current
    DESCRIPTION     "The value of the object sapStatHost6ShcvOperState
                     indicates the state of the subscriber host connectivity
                     check for this static host."
    ::= { sapStatHost6Entry 12 }

sapStatHost6ShcvChecks OBJECT-TYPE
    SYNTAX          Unsigned32
    MAX-ACCESS      read-only
    STATUS          current
    DESCRIPTION     "The value of the object sapStatHost6ShcvChecks indicates
                     the number of connectivity checks for this static host."
    ::= { sapStatHost6Entry 13 }

sapStatHost6ShcvReplies OBJECT-TYPE
    SYNTAX          Unsigned32
    MAX-ACCESS      read-only
    STATUS          current
    DESCRIPTION     "The value of the object sapStatHost6ShcvReplies indicates
                     the number of host replies for this static host."
    ::= { sapStatHost6Entry 14 }

sapStatHost6ShcvReplyTime OBJECT-TYPE
    SYNTAX          TimeStamp
    MAX-ACCESS      read-only
    STATUS          current
    DESCRIPTION     "The value of the object sapStatHost6ShcvReplyTime
                     indicates the timestamp of the last successful connectivity
                     check for this static host."
    ::= { sapStatHost6Entry 15 }

sapStatHost6DynMacAddress OBJECT-TYPE
    SYNTAX          MacAddress
    MAX-ACCESS      read-only
    STATUS          current
    DESCRIPTION     "The value of the object sapStatHost6DynMacAddress indicates
                     the learned MAC address while sapStatHost6MacAddress 
                     is equal to 0:0:0:0:0:0.
                     
                     The value 0:0:0:0:0:0 indicates that no MAC address is
                     learned yet."
    ::= { sapStatHost6Entry 16 }

sapStatHost6RetailerSvcId OBJECT-TYPE
    SYNTAX          TmnxServId
    MAX-ACCESS      read-only
    STATUS          current
    DESCRIPTION     "The value of the object sapStatHost6RetailerSvcId
                     indicates the service ID of the retailer VPRN service
                     to which this static host belongs. 
                     
                     When this object is non zero, the static host
                     belongs to a retailer VPRN."
    ::= { sapStatHost6Entry 17 } 

sapStatHost6RetailerIf OBJECT-TYPE
    SYNTAX          InterfaceIndexOrZero
    MAX-ACCESS      read-only
    STATUS          current
    DESCRIPTION     "The value of the object sapStatHost6RetailerIf indicates
                     the interface index of the retailer VPRN interface to which
                     this static host belongs. 
                     
                     When this object is non zero,
                     the static host belongs to a retailer VPRN."
    ::= { sapStatHost6Entry 18 } 

sapStatHost6FwdingState OBJECT-TYPE
    SYNTAX          TmnxOperState
    MAX-ACCESS      read-only
    STATUS          current
    DESCRIPTION     "The value of sapStatHost6FwdingState indicates the
                     forwarding state of this static host. 
                     
                     When the value is 'outOfService', host traffic is not forwarded;
                     while it is 'inService', host traffic is forwarded."
    ::= { sapStatHost6Entry 19 } 

sapStatHost6AncpString OBJECT-TYPE
    SYNTAX          TmnxAncpStringOrZero
    MAX-ACCESS      read-create
    STATUS          current
    DESCRIPTION     "The value of sapStatHost6AncpString specifies
                     the ancp-string associated to this SAP host."
    DEFVAL          { "" }
    ::= { sapStatHost6Entry 20 } 

sapStatHost6SubIdIsSapId OBJECT-TYPE
    SYNTAX          TruthValue
    MAX-ACCESS      read-create
    STATUS          current
    DESCRIPTION     "The value of the object sapStatHost6SubIdIsSapId
                     specifies if the SAP ID is taken as subscriber
                     identification for this static host."
    DEFVAL          { false }
    ::= { sapStatHost6Entry 21 } 

sapStatHost6AppProfile OBJECT-TYPE
    SYNTAX          ServObjName
    MAX-ACCESS      read-create
    STATUS          current
    DESCRIPTION     "The value of sapStatHost6AppProfile specifies
                     the application profile for this static host. 
                     
                     A non-empty value of this object must correspond to
                     a conceptual row in the
                     TIMETRA-BSX-NG-MIB::tmnxBsxAppProfTable."
    DEFVAL          { "" }
    ::= { sapStatHost6Entry 22 }

sapStatHost6IntermediateDestId OBJECT-TYPE
    SYNTAX          DisplayString (SIZE (0..32))
    MAX-ACCESS      read-create
    STATUS          current
    DESCRIPTION     "The value of sapStatHost6IntermediateDestId specifies
                     to which intermediate destination (for example a DSLAM)
                     this host belongs."
    DEFVAL          { "" }
    ::= { sapStatHost6Entry 23 }

sapStatHost6AdminRetailSvcId OBJECT-TYPE
    SYNTAX       TmnxServId
    MAX-ACCESS   read-create
    STATUS       current
    DESCRIPTION  "The value of sapStatHost6AdminRetailSvcId specifies the
                  forwarding service ID for an unnumbered static host in a
                  wholesale/retail context."
    DEFVAL       { 0 }
    ::= { sapStatHost6Entry 24 }
    
-- SAP Static Host IPv6 Managed Route Table
    
sapStatHost6MRtTblLastChgd OBJECT-TYPE
    SYNTAX          TimeStamp
    MAX-ACCESS      read-only
    STATUS          current
    DESCRIPTION     "The value of sapStatHost6MRtTblLastChgd indicates the
                     sysUpTime at the time of the last modification of
                     sapStatHost6MRtTable.

                     If no changes were made to the entry since the last
                     re-initialization of the local network management 
                     subsystem, this object contains a zero value."
    ::= { tmnxSapObjs 164 }

sapStatHost6MRtTable OBJECT-TYPE
    SYNTAX          SEQUENCE OF SapStatHost6MRtEntry
    MAX-ACCESS      not-accessible
    STATUS          current
    DESCRIPTION     "The sapStatHost6MRtTable contains managed routes of
                     SAP static IPv6 hosts.

                     Entries can be created and deleted via SNMP SET 
                     operations."
    ::= { tmnxStaticHostIpv6Objs 2 }

sapStatHost6MRtEntry OBJECT-TYPE
    SYNTAX          SapStatHost6MRtEntry
    MAX-ACCESS      not-accessible
    STATUS          current
    DESCRIPTION     "Each row entry represents information on a specific
                     managed route."
    INDEX           { svcId,
                      sapPortId,
                      sapEncapValue,
                      sapStatHost6IpAddress,
                      sapStatHost6MacAddress,
                      sapStatHost6MRtAddrType,
                      sapStatHost6MRtAddr,
                      sapStatHost6MRtPrefixLen }
    ::= { sapStatHost6MRtTable 1 }

SapStatHost6MRtEntry ::=
    SEQUENCE {
        sapStatHost6MRtAddrType          InetAddressType,
        sapStatHost6MRtAddr              InetAddress,
        sapStatHost6MRtPrefixLen         InetAddressPrefixLength,
        sapStatHost6MRtRowStatus         RowStatus,
        sapStatHost6MRtLastMgmtChange    TimeStamp, 
        sapStatHost6MRtStatus            TmnxManagedRouteStatus,
        sapStatHost6MRtMetric            Unsigned32
    }

sapStatHost6MRtAddrType OBJECT-TYPE
    SYNTAX          InetAddressType
    MAX-ACCESS      not-accessible
    STATUS          current
    DESCRIPTION     "The value of sapStatHost6MRtAddrType indicates
                     the address type of sapStatHost6MRtAddr."
    ::= { sapStatHost6MRtEntry 1 }

sapStatHost6MRtAddr OBJECT-TYPE
    SYNTAX          InetAddress (SIZE(4|16))
    MAX-ACCESS      not-accessible
    STATUS          current
    DESCRIPTION     "The value of sapStatHost6MRtAddr indicates
                     the IP address of the managed route."
    ::= { sapStatHost6MRtEntry 2 }

sapStatHost6MRtPrefixLen OBJECT-TYPE
    SYNTAX          InetAddressPrefixLength (0..128)
    MAX-ACCESS      not-accessible
    STATUS          current
    DESCRIPTION     "The value of sapStatHost6MRtPrefixLen indicates
                     the prefix length of the subnet associated with
                     sapStatHost6MRtAddr."
    ::= { sapStatHost6MRtEntry 3 }

sapStatHost6MRtRowStatus OBJECT-TYPE
    SYNTAX          RowStatus
    MAX-ACCESS      read-create
    STATUS          current
    DESCRIPTION     "The value of sapStatHost6MRtRowStatus controls the 
                     creation and deletion of rows in this table."
    ::= { sapStatHost6MRtEntry 4 }

sapStatHost6MRtLastMgmtChange OBJECT-TYPE
    SYNTAX          TimeStamp
    MAX-ACCESS      read-only
    STATUS          current
    DESCRIPTION     "The value of sapStatHost6MRtLastMgmtChange indicates the
                     value of sysUpTime at the time of the last management
                     change of any writable object of this row."
    ::= { sapStatHost6MRtEntry 5 }

sapStatHost6MRtStatus OBJECT-TYPE
    SYNTAX          TmnxManagedRouteStatus
    MAX-ACCESS      read-only
    STATUS          current
    DESCRIPTION     "The value of svcDhcpManagedRouteStatus indicates
                     the state of this managed route."
    ::= { sapStatHost6MRtEntry 6 }  

sapStatHost6MRtMetric OBJECT-TYPE
    SYNTAX          Unsigned32
    MAX-ACCESS      read-create
    STATUS          current
    DESCRIPTION     "The value of sapStatHost6MRtMetric specifies the 
                     route metric."
    DEFVAL { 0 }
    ::= { sapStatHost6MRtEntry 7 }

-- Sap Ingress
sapIngQosQueueDepthInfoTable        OBJECT-TYPE
    SYNTAX      SEQUENCE OF SapIngQosQueueDepthInfoEntry
    MAX-ACCESS  not-accessible
    STATUS      current
    DESCRIPTION
        "The value of sapIngQosQueueDepthInfoTable has an entry for each SAP
         ingress override queue for which the value of sapIngQosQMonitorDepth
         is set to 'true (1)'."
    ::= { tmnxSapObjs 165 }

sapIngQosQueueDepthInfoEntry        OBJECT-TYPE
    SYNTAX      SapIngQosQueueDepthInfoEntry
    MAX-ACCESS  not-accessible
    STATUS      current
    DESCRIPTION
        "The value of sapIngQosQueueDepthInfoEntry represents queue-depth
         monitoring information for SAP ingress override queue for which the
         value of sapIngQosQMonitorDepth is set to 'true (1)'."
    INDEX { svcId, sapPortId, sapEncapValue, sapIngQosQueueId }
    ::= { sapIngQosQueueDepthInfoTable 1 }

SapIngQosQueueDepthInfoEntry ::= SEQUENCE
    {
        sapIngQosQueueDepthPollPrcnt1       Unsigned32,
        sapIngQosQueueDepthPollPrcnt2       Unsigned32,
        sapIngQosQueueDepthPollPrcnt3       Unsigned32,
        sapIngQosQueueDepthPollPrcnt4       Unsigned32,
        sapIngQosQueueDepthPollPrcnt5       Unsigned32,
        sapIngQosQueueDepthPollPrcnt6       Unsigned32,
        sapIngQosQueueDepthPollPrcnt7       Unsigned32,
        sapIngQosQueueDepthPollPrcnt8       Unsigned32,
        sapIngQosQueueDepthPollPrcnt9       Unsigned32,
        sapIngQosQueueDepthPollPrcnt10      Unsigned32,
        sapIngQosQueueDepthAvgPollInt       Unsigned32,
        sapIngQosQueueDepthAvgElpsdTme      TimeStamp
    }

sapIngQosQueueDepthPollPrcnt1       OBJECT-TYPE
    SYNTAX      Unsigned32 (0..10000)
    UNITS       "hundredths of a percent"
    MAX-ACCESS  read-only
    STATUS      current
    DESCRIPTION
        "The value of sapIngQosQueueDepthPollPrcnt1 represents the percentage
         of polls in occupancy range of 0 to 10 percent for the queue depths
         seen during the polling elapsed time."
    ::= { sapIngQosQueueDepthInfoEntry 1 }

sapIngQosQueueDepthPollPrcnt2       OBJECT-TYPE
    SYNTAX      Unsigned32 (0..10000)
    UNITS       "hundredths of a percent"
    MAX-ACCESS  read-only
    STATUS      current
    DESCRIPTION
        "The value of sapIngQosQueueDepthPollPrcnt2 represents the percentage
         of polls in occupancy range of 11 to 20 percent for the queue depths
         seen during the polling elapsed time."
    ::= { sapIngQosQueueDepthInfoEntry 2 }

sapIngQosQueueDepthPollPrcnt3       OBJECT-TYPE
    SYNTAX      Unsigned32 (0..10000)
    UNITS       "hundredths of a percent"
    MAX-ACCESS  read-only
    STATUS      current
    DESCRIPTION
        "The value of sapIngQosQueueDepthPollPrcnt3 represents the percentage
         of polls in occupancy range of 21 to 30 percent for the queue depths
         seen during the polling elapsed time."
    ::= { sapIngQosQueueDepthInfoEntry 3 }

sapIngQosQueueDepthPollPrcnt4       OBJECT-TYPE
    SYNTAX      Unsigned32 (0..10000)
    UNITS       "hundredths of a percent"
    MAX-ACCESS  read-only
    STATUS      current
    DESCRIPTION
        "The value of sapIngQosQueueDepthPollPrcnt4 represents the percentage
         of polls in occupancy range of 31 to 40 percent for the queue depths
         seen during the polling elapsed time."
    ::= { sapIngQosQueueDepthInfoEntry 4 }

sapIngQosQueueDepthPollPrcnt5       OBJECT-TYPE
    SYNTAX      Unsigned32 (0..10000)
    UNITS       "hundredths of a percent"
    MAX-ACCESS  read-only
    STATUS      current
    DESCRIPTION
        "The value of sapIngQosQueueDepthPollPrcnt5 represents the percentage
         of polls in occupancy range of 41 to 50 percent for the queue depths
         seen during the polling elapsed time."
    ::= { sapIngQosQueueDepthInfoEntry 5 }

sapIngQosQueueDepthPollPrcnt6       OBJECT-TYPE
    SYNTAX      Unsigned32 (0..10000)
    UNITS       "hundredths of a percent"
    MAX-ACCESS  read-only
    STATUS      current
    DESCRIPTION
        "The value of sapIngQosQueueDepthPollPrcnt6 represents the percentage
         of polls in occupancy range of 51 to 60 percent for the queue depths
         seen during the polling elapsed time."
    ::= { sapIngQosQueueDepthInfoEntry 6 }

sapIngQosQueueDepthPollPrcnt7       OBJECT-TYPE
    SYNTAX      Unsigned32 (0..10000)
    UNITS       "hundredths of a percent"
    MAX-ACCESS  read-only
    STATUS      current
    DESCRIPTION
        "The value of sapIngQosQueueDepthPollPrcnt7 represents the percentage
         of polls in occupancy range of 61 to 70 percent for the queue depths
         seen during the polling elapsed time."
    ::= { sapIngQosQueueDepthInfoEntry 7 }

sapIngQosQueueDepthPollPrcnt8       OBJECT-TYPE
    SYNTAX      Unsigned32 (0..10000)
    UNITS       "hundredths of a percent"
    MAX-ACCESS  read-only
    STATUS      current
    DESCRIPTION
        "The value of sapIngQosQueueDepthPollPrcnt8 represents the percentage
         of polls in occupancy range of 71 to 80 percent for the queue depths
         seen during the polling elapsed time."
    ::= { sapIngQosQueueDepthInfoEntry 8 }

sapIngQosQueueDepthPollPrcnt9       OBJECT-TYPE
    SYNTAX      Unsigned32 (0..10000)
    UNITS       "hundredths of a percent"
    MAX-ACCESS  read-only
    STATUS      current
    DESCRIPTION
        "The value of sapIngQosQueueDepthPollPrcnt9 represents the percentage
         of polls in occupancy range of 81 to 90 percent for the queue depths
         seen during the polling elapsed time."
    ::= { sapIngQosQueueDepthInfoEntry 9 }

sapIngQosQueueDepthPollPrcnt10      OBJECT-TYPE
    SYNTAX      Unsigned32 (0..10000)
    UNITS       "hundredths of a percent"
    MAX-ACCESS  read-only
    STATUS      current
    DESCRIPTION
        "The value of sapIngQosQueueDepthPollPrcnt10 represents the percentage
         of polls in occupancy range of 91 to 100 percent for the queue depths
         seen during the polling elapsed time."
    ::= { sapIngQosQueueDepthInfoEntry 10 }

sapIngQosQueueDepthAvgPollInt     OBJECT-TYPE
    SYNTAX      Unsigned32
    UNITS       "milliseconds"
    MAX-ACCESS  read-only
    STATUS      current
    DESCRIPTION
        "The value of sapIngQosQueueDepthAvgPollInt represents the weighted
         average polling interval for the elapsed time."
    ::= { sapIngQosQueueDepthInfoEntry 11 }

sapIngQosQueueDepthAvgElpsdTme   OBJECT-TYPE
    SYNTAX      TimeStamp
    MAX-ACCESS  read-only
    STATUS      current
    DESCRIPTION
        "The value of sapIngQosQueueDepthAvgElpsdTme represents the average
         elapsed time since the start of queue-depth monitoring or the last
         monitoring clear."
    ::= { sapIngQosQueueDepthInfoEntry 12 }

-- Sap Egress
sapEgrQosQueueDepthInfoTable        OBJECT-TYPE
    SYNTAX      SEQUENCE OF SapEgrQosQueueDepthInfoEntry
    MAX-ACCESS  not-accessible
    STATUS      current
    DESCRIPTION
        "The value of sapEgrQosQueueDepthInfoTable has an entry for each SAP
         egress override queue for which the value of sapEgrQosQMonitorDepth
         is set to 'true (1)'."
    ::= { tmnxSapObjs 166 }

sapEgrQosQueueDepthInfoEntry        OBJECT-TYPE
    SYNTAX      SapEgrQosQueueDepthInfoEntry
    MAX-ACCESS  not-accessible
    STATUS      current
    DESCRIPTION
        "The value of sapEgrQosQueueDepthInfoEntry represents queue-depth
         monitoring information for SAP egress override queue for which the
         value of sapEgrQosQMonitorDepth is set to 'true (1)'."
    INDEX { svcId, sapPortId, sapEncapValue, sapEgrQosQueueId }
    ::= { sapEgrQosQueueDepthInfoTable 1 }

SapEgrQosQueueDepthInfoEntry ::= SEQUENCE
    {
        sapEgrQosQueueDepthPollPrcnt1       Unsigned32,
        sapEgrQosQueueDepthPollPrcnt2       Unsigned32,
        sapEgrQosQueueDepthPollPrcnt3       Unsigned32,
        sapEgrQosQueueDepthPollPrcnt4       Unsigned32,
        sapEgrQosQueueDepthPollPrcnt5       Unsigned32,
        sapEgrQosQueueDepthPollPrcnt6       Unsigned32,
        sapEgrQosQueueDepthPollPrcnt7       Unsigned32,
        sapEgrQosQueueDepthPollPrcnt8       Unsigned32,
        sapEgrQosQueueDepthPollPrcnt9       Unsigned32,
        sapEgrQosQueueDepthPollPrcnt10      Unsigned32,
        sapEgrQosQueueDepthAvgPollInt       Unsigned32,
        sapEgrQosQueueDepthAvgElpsdTme      TimeStamp
    }

sapEgrQosQueueDepthPollPrcnt1       OBJECT-TYPE
    SYNTAX      Unsigned32 (0..10000)
    UNITS       "hundredths of a percent"
    MAX-ACCESS  read-only
    STATUS      current
    DESCRIPTION
        "The value of sapEgrQosQueueDepthPollPrcnt1 represents the percentage
         of polls in occupancy range of 0 to 10 percent for the queue depths
         seen during the polling elapsed time."
    ::= { sapEgrQosQueueDepthInfoEntry 1 }

sapEgrQosQueueDepthPollPrcnt2       OBJECT-TYPE
    SYNTAX      Unsigned32 (0..10000)
    UNITS       "hundredths of a percent"
    MAX-ACCESS  read-only
    STATUS      current
    DESCRIPTION
        "The value of sapEgrQosQueueDepthPollPrcnt2 represents the percentage
         of polls in occupancy range of 11 to 20 percent for the queue depths
         seen during the polling elapsed time."
    ::= { sapEgrQosQueueDepthInfoEntry 2 }

sapEgrQosQueueDepthPollPrcnt3       OBJECT-TYPE
    SYNTAX      Unsigned32 (0..10000)
    UNITS       "hundredths of a percent"
    MAX-ACCESS  read-only
    STATUS      current
    DESCRIPTION
        "The value of sapEgrQosQueueDepthPollPrcnt3 represents the percentage
         of polls in occupancy range of 21 to 30 percent for the queue depths
         seen during the polling elapsed time."
    ::= { sapEgrQosQueueDepthInfoEntry 3 }

sapEgrQosQueueDepthPollPrcnt4       OBJECT-TYPE
    SYNTAX      Unsigned32 (0..10000)
    UNITS       "hundredths of a percent"
    MAX-ACCESS  read-only
    STATUS      current
    DESCRIPTION
        "The value of sapEgrQosQueueDepthPollPrcnt4 represents the percentage
         of polls in occupancy range of 31 to 40 percent for the queue depths
         seen during the polling elapsed time."
    ::= { sapEgrQosQueueDepthInfoEntry 4 }

sapEgrQosQueueDepthPollPrcnt5       OBJECT-TYPE
    SYNTAX      Unsigned32 (0..10000)
    UNITS       "hundredths of a percent"
    MAX-ACCESS  read-only
    STATUS      current
    DESCRIPTION
        "The value of sapEgrQosQueueDepthPollPrcnt5 represents the percentage
         of polls in occupancy range of 41 to 50 percent for the queue depths
         seen during the polling elapsed time."
    ::= { sapEgrQosQueueDepthInfoEntry 5 }

sapEgrQosQueueDepthPollPrcnt6       OBJECT-TYPE
    SYNTAX      Unsigned32 (0..10000)
    UNITS       "hundredths of a percent"
    MAX-ACCESS  read-only
    STATUS      current
    DESCRIPTION
        "The value of sapEgrQosQueueDepthPollPrcnt6 represents the percentage
         of polls in occupancy range of 51 to 60 percent for the queue depths
         seen during the polling elapsed time."
    ::= { sapEgrQosQueueDepthInfoEntry 6 }

sapEgrQosQueueDepthPollPrcnt7       OBJECT-TYPE
    SYNTAX      Unsigned32 (0..10000)
    UNITS       "hundredths of a percent"
    MAX-ACCESS  read-only
    STATUS      current
    DESCRIPTION
        "The value of sapEgrQosQueueDepthPollPrcnt7 represents the percentage
         of polls in occupancy range of 61 to 70 percent for the queue depths
         seen during the polling elapsed time."
    ::= { sapEgrQosQueueDepthInfoEntry 7 }

sapEgrQosQueueDepthPollPrcnt8       OBJECT-TYPE
    SYNTAX      Unsigned32 (0..10000)
    UNITS       "hundredths of a percent"
    MAX-ACCESS  read-only
    STATUS      current
    DESCRIPTION
        "The value of sapEgrQosQueueDepthPollPrcnt8 represents the percentage
         of polls in occupancy range of 71 to 80 percent for the queue depths
         seen during the polling elapsed time."
    ::= { sapEgrQosQueueDepthInfoEntry 8 }

sapEgrQosQueueDepthPollPrcnt9       OBJECT-TYPE
    SYNTAX      Unsigned32 (0..10000)
    UNITS       "hundredths of a percent"
    MAX-ACCESS  read-only
    STATUS      current
    DESCRIPTION
        "The value of sapEgrQosQueueDepthPollPrcnt9 represents the percentage
         of polls in occupancy range of 81 to 90 percent for the queue depths
         seen during the polling elapsed time."
    ::= { sapEgrQosQueueDepthInfoEntry 9 }

sapEgrQosQueueDepthPollPrcnt10      OBJECT-TYPE
    SYNTAX      Unsigned32 (0..10000)
    UNITS       "hundredths of a percent"
    MAX-ACCESS  read-only
    STATUS      current
    DESCRIPTION
        "The value of sapEgrQosQueueDepthPollPrcnt10 represents the percentage
         of polls in occupancy range of 91 to 100 percent for the queue depths
         seen during the polling elapsed time."
    ::= { sapEgrQosQueueDepthInfoEntry 10 }

sapEgrQosQueueDepthAvgPollInt     OBJECT-TYPE
    SYNTAX      Unsigned32
    UNITS       "milliseconds"
    MAX-ACCESS  read-only
    STATUS      current
    DESCRIPTION
        "The value of sapEgrQosQueueDepthAvgPollInt represents the weighted
         average polling interval for the elapsed time."
    ::= { sapEgrQosQueueDepthInfoEntry 11 }

sapEgrQosQueueDepthAvgElpsdTme   OBJECT-TYPE
    SYNTAX      TimeStamp
    MAX-ACCESS  read-only
    STATUS      current
    DESCRIPTION
        "The value of sapEgrQosQueueDepthAvgElpsdTme represents the average
         elapsed time since the start of queue-depth monitoring or the last
         monitoring clear."
    ::= { sapEgrQosQueueDepthInfoEntry 12 }

-- ----------------------------------------
--  sapStaticHostRipTable
--
--  Augmentation of the sapStaticHostTable
--  Use of AUGMENTS clause implies a one-to-one dependent relationship
--  between the base table, sapStaticHostTable, and the augmenting table,
--  sapStaticHostRipTable. This in effect extends the sapStaticHostTable
--  with additional columns. Creation (or deletion) of a row in the
--  sapStaticHostTable results in the same fate for the row in the
--  sapStaticHostRipTable.
-- ----------------------------------------

sapStaticHostRipTable OBJECT-TYPE
    SYNTAX          SEQUENCE OF SapStaticHostRipEntry
    MAX-ACCESS      not-accessible
    STATUS          current
    DESCRIPTION
        "The sapStaticHostRipTable augments the sapStaticHostTable.
         This table contains the parameters used for RIP."
    ::= { tmnxSapObjs 167 }

sapStaticHostRipEntry OBJECT-TYPE
    SYNTAX          SapStaticHostRipEntry  
    MAX-ACCESS      not-accessible
    STATUS          current
    DESCRIPTION     
        "Each row entry contains parameters used for RIP."
    AUGMENTS        { sapStaticHostEntry }
    ::= { sapStaticHostRipTable 1 }

SapStaticHostRipEntry ::=
    SEQUENCE {
        sapStaticHostRipPlcyName         TNamedItemOrEmpty,
        sapStaticHostRipListenerStatus   TmnxRipListenerStatus
    }

sapStaticHostRipPlcyName OBJECT-TYPE
    SYNTAX          TNamedItemOrEmpty
    MAX-ACCESS      read-only
    STATUS          current
    DESCRIPTION
        "The value of sapStaticHostRipPlcyName indicates the
         RIP policy which is used to set up the RIP listener for this
         static host."
    ::= { sapStaticHostRipEntry 1 }

sapStaticHostRipListenerStatus OBJECT-TYPE
    SYNTAX          TmnxRipListenerStatus
    MAX-ACCESS      read-only
    STATUS          current
    DESCRIPTION
        "The value of sapStaticHostRipListenerStatus indicates
         the status of the RIP listener."
    ::= { sapStaticHostRipEntry 2 }


--
-- Ethernet segment SAP table
--
sapEvpnMHEthSegTable     OBJECT-TYPE
    SYNTAX      SEQUENCE OF SapEvpnMHEthSegEntry
    MAX-ACCESS  not-accessible
    STATUS      current
    DESCRIPTION
        "The sdpEvpnMHEthSegTable contains entries for ethernet segment
         information associated with a SAP."
    ::= { tmnxSapObjs 168 }

sapEvpnMHEthSegEntry    OBJECT-TYPE
    SYNTAX      SapEvpnMHEthSegEntry
    MAX-ACCESS  not-accessible
    STATUS      current
    DESCRIPTION
        "An ethernet segment entry in the sapEvpnMHEthSegTable."
    INDEX       { svcId, sapPortId, sapEncapValue }
    ::= { sapEvpnMHEthSegTable 1}

SapEvpnMHEthSegEntry ::=    SEQUENCE {
    sapEvpnMHEthSegName     TNamedItemOrEmpty
}

sapEvpnMHEthSegName OBJECT-TYPE
    SYNTAX      TNamedItemOrEmpty (SIZE(0|1..28))
    MAX-ACCESS  read-only
    STATUS      current
    DESCRIPTION
        "The value of sapEvpnMHEthSegName indicates the ethernet segment
         name associated with the given SAP."
    ::= { sapEvpnMHEthSegEntry 1 }

-- --------------------------------------------------
-- SAP Default host ex table
-- --------------------------------------------------
sapDefHostExTableLastChanged OBJECT-TYPE
    SYNTAX       TimeStamp
    MAX-ACCESS   read-only
    STATUS       current
    DESCRIPTION
        "The value of the object sapDefHostExTableLastChanged indicates
         the value of sysUpTime at the time of the last modification of
         an conceptual row in the sapDefHostExTable."
    ::= { tmnxSapObjs 169 }

sapDefHostExTable OBJECT-TYPE
    SYNTAX          SEQUENCE OF SapDefHostExEntry 
    MAX-ACCESS      not-accessible
    STATUS          current
    DESCRIPTION
        "A table that contains SAP default host information.
        
         Entries in this table can be created or deleted via SNMP operations.
    
         A row in this table can only be created for a SAP in a group interface, 
         that is each row in the sapBaseInfoTable where the value of 
         sapIesIfIndex corresponds to a row in the vRtrIfTable
         where the value of vRtrIfType is equal to 'serviceIesGroup' 
         or 'serviceVprnGroup'."
    ::= { tmnxSapObjs 170 }

sapDefHostExEntry  OBJECT-TYPE
    SYNTAX          SapDefHostExEntry 
    MAX-ACCESS      not-accessible
    STATUS          current
    DESCRIPTION
        "SAP default host specific information."
    INDEX           { svcId, 
                      sapPortId, 
                      sapEncapValue, 
                      sapDefHostExSubnetAddrType,
                      sapDefHostExSubnetAddr,
                      sapDefHostExSubnetAddrPfxLen }
    ::= { sapDefHostExTable 1 }

SapDefHostExEntry   ::=
    SEQUENCE {
        sapDefHostExSubnetAddrType       InetAddressType,
        sapDefHostExSubnetAddr           InetAddress,
        sapDefHostExSubnetAddrPfxLen     InetAddressPrefixLength,
        sapDefHostExRowStatus            RowStatus,
        sapDefHostExLastChanged          TimeStamp,
        sapDefHostExNextHopAddrType      InetAddressType,
        sapDefHostExNextHopAddr          InetAddress
    }

sapDefHostExSubnetAddrType OBJECT-TYPE
    SYNTAX      InetAddressType
    MAX-ACCESS  not-accessible
    STATUS      current
    DESCRIPTION
        "The value of sapDefHostExSubnetAddrType indicates the address type of
         sapDefHostExSubnetAddr."
    ::= { sapDefHostExEntry 1 }

sapDefHostExSubnetAddr  OBJECT-TYPE
    SYNTAX      InetAddress (SIZE (4|16))
    MAX-ACCESS  not-accessible
    STATUS      current
    DESCRIPTION
        "The value of the object sapDefHostExSubnetAddr specifies
         the IPv4 Subnet or IPv6 Prefix address for this SAP default host.
         
         It must be equal to one of the addresses of the subscriber interface
         this SAP belongs to, that is one of its vRiaIpAddress values."
    ::= { sapDefHostExEntry 2 }

sapDefHostExSubnetAddrPfxLen OBJECT-TYPE
    SYNTAX      InetAddressPrefixLength
    MAX-ACCESS  not-accessible
    STATUS      current
    DESCRIPTION
        "The value of sapDefHostExSubnetAddrPfxLen indicates the IPv4 Subnet
         or IPv6 Prefix length of sapDefHostExSubnetAddr."
    ::= { sapDefHostExEntry 3 }

sapDefHostExRowStatus OBJECT-TYPE
    SYNTAX       RowStatus
    MAX-ACCESS   read-create
    STATUS       current
    DESCRIPTION
        "The value of sapDefHostExRowStatus specifies the row status of this row."
    ::= { sapDefHostExEntry 4 }

sapDefHostExLastChanged  OBJECT-TYPE
    SYNTAX      TimeStamp
    MAX-ACCESS  read-only
    STATUS      current
    DESCRIPTION
        "The value of sapDefHostExLastChanged indicates the sysUpTime at
         the time of the most recent management-initiated change to this
         conceptual row."
    ::= { sapDefHostExEntry 5 }

sapDefHostExNextHopAddrType OBJECT-TYPE
    SYNTAX      InetAddressType
    MAX-ACCESS  read-create
    STATUS      current
    DESCRIPTION
        "The value of sapDefHostExNextHopAddrType indicates
         the address type of sapDefHostExNextHopAddr."
    ::= { sapDefHostExEntry 6 }

sapDefHostExNextHopAddr OBJECT-TYPE
    SYNTAX      InetAddress (SIZE(4|16))
    MAX-ACCESS  read-create
    STATUS      current
    DESCRIPTION     
        "The value of sapDefHostExNextHopAddr specifies
         the next-hop IP address for this SAP default host.
         
         The value all zeroes is not allowed.
         
         A value for sapDefHostExNextHopAddr must be specified when a row
         is created and this value cannot be changed afterwards."
    ::= { sapDefHostExEntry 7 }


--
--      The per-SAP subscriber host Data Trigger statistics table
--

tmnxSapDataTrigStatsTable   OBJECT-TYPE
    SYNTAX      SEQUENCE OF TmnxSapDataTrigStatsEntry
    MAX-ACCESS  not-accessible
    STATUS      current
    DESCRIPTION
       "The tmnxSapDataTrigStatsTable contains detailed statistics information 
        about the data triggers involved in creating data-triggered subscriber hosts.
        
        The typical usage of this table is to fill in the part of the index
        that identifies a SAP, and perform a partial walk
        to get all the statistics applicable to that SAP."
    ::= { tmnxSapObjs 171 }

tmnxSapDataTrigStatsEntry   OBJECT-TYPE
    SYNTAX      TmnxSapDataTrigStatsEntry
    MAX-ACCESS  not-accessible
    STATUS      current
    DESCRIPTION
       "Each conceptual row contains detailed data trigger statistics information
        about a SAP.

        Entries in this table are created and removed automatically by the 
        system
        
        The system creates conceptual rows in this table only for SAP's where
        the value of sapStatHostMacLearnOptions is equal to 'dataTriggered'.
        
        The system does not create rows unless there is at least one non-zero counter."
    INDEX { svcId,
            sapPortId,
            sapEncapValue,
            tmnxSapDataTrigStatsId }
    ::= { tmnxSapDataTrigStatsTable 1 }

TmnxSapDataTrigStatsEntry ::= 
    SEQUENCE {
        tmnxSapDataTrigStatsId           Unsigned32,
        tmnxSapDataTrigStatsName         DisplayString,
        tmnxSapDataTrigStatsVal          Counter64
    }

tmnxSapDataTrigStatsId OBJECT-TYPE
    SYNTAX      Unsigned32 (0..20)
    MAX-ACCESS  not-accessible
    STATUS      current
    DESCRIPTION
        "The value of tmnxSapDataTrigStatsId indicates
         the identifier of the SAP data trigger statistics 
         contained in this conceptual row.
         
         It is a meaningless number generated by this system."
    ::= { tmnxSapDataTrigStatsEntry 1 }

tmnxSapDataTrigStatsName OBJECT-TYPE
    SYNTAX      DisplayString (SIZE (1..64))
    MAX-ACCESS  read-only
    STATUS      current
    DESCRIPTION 
       "The value of the object tmnxSapDataTrigStatsName indicates
        the human-readable identifier of the statistics 
        contained in this conceptual row."
    ::= { tmnxSapDataTrigStatsEntry 2 }

tmnxSapDataTrigStatsVal OBJECT-TYPE
    SYNTAX      Counter64
    MAX-ACCESS  read-only
    STATUS      current
    DESCRIPTION 
       "The value of the object tmnxSapDataTrigStatsVal indicates
        the value of the statistics contained in this conceptual row."
    ::= { tmnxSapDataTrigStatsEntry 3 }

-- --------------------------------------
-- SAP Notifications
-- --------------------------------------

sapNotificationObjects     OBJECT IDENTIFIER ::= {tmnxSapObjs 151}

sapDcpTimeEventOccured OBJECT-TYPE
    SYNTAX          TimeStamp
    MAX-ACCESS      accessible-for-notify
    STATUS          current
    DESCRIPTION     
        "The value of sapDcpTimeEventOccured indicates the actual time the
         event was detected in the system which may differ from the time that
         event was collected by the logging infrastructure."
    ::= { sapNotificationObjects 1 }


-- --------------------------------------
-- SAP Traps 
-- --------------------------------------
sapCreated NOTIFICATION-TYPE
    OBJECTS {
        custId,
        svcId,
        svcVpnId,
        sapPortId,
        sapEncapValue
    }
    STATUS          obsolete
    DESCRIPTION     "This trap is sent when a new row is created
                     in the sapBaseInfoTable."
    ::= { sapTraps 1 }

sapDeleted NOTIFICATION-TYPE
    OBJECTS {
        custId,
        svcId,
        svcVpnId,
        sapPortId,
        sapEncapValue
    }
    STATUS          obsolete
    DESCRIPTION     "This trap is sent when an existing row is
                     deleted from the sapBaseInfoTable."
    ::= { sapTraps 2 }

sapStatusChanged NOTIFICATION-TYPE
    OBJECTS {
        custId,
        svcId,
        svcVpnId,
        sapPortId,
        sapEncapValue,
        sapAdminStatus,
        sapOperStatus,
        sapOperFlags
    }
    STATUS          current
    DESCRIPTION     "The sapStatusChanged notification is generated
                     when there is a change in the administrative or
                     operating status of an SAP.
                     
                     Notice that this trap is not generated whenever
                     the SAP operating status change is caused by an
                     operating status change on the associated access
                     port."
    ::= { sapTraps 3 }

sapTlsMacAddrLimitAlarmRaised  NOTIFICATION-TYPE
    OBJECTS {
        custId,
        svcId,
        svcVpnId,
        sapPortId,
        sapEncapValue
    }
    STATUS          current
    DESCRIPTION     "The trap sapTlsMacAddrLimitAlarmRaised is sent whenever
                     the number of MAC addresses stored in the FDB for this SAP
                     increases to reach the watermark specified by the object
                     svcTlsFdbTableFullHighWatermark."
    ::= { sapTraps 4 }

sapTlsMacAddrLimitAlarmCleared  NOTIFICATION-TYPE
    OBJECTS {
        custId,
        svcId,
        svcVpnId,
        sapPortId,
        sapEncapValue
    }
    STATUS          current
    DESCRIPTION     "The trap sapTlsMacAddrLimitAlarmCleared is sent whenever
                     the number of MAC addresses stored in the FDB for this SAP
                     drops to the watermark specified by the object
                     svcTlsFdbTableFullLowWatermark."
    ::= { sapTraps 5 }

sapTlsDHCPLseStEntriesExceeded   NOTIFICATION-TYPE
    OBJECTS {
        custId,
        svcId,
        svcVpnId,
        sapPortId,
        sapEncapValue,
        tlsDhcpLseStateNewCiAddr,
        tlsDhcpLseStateNewChAddr,
        tlsDHCPClientLease
    }
    STATUS          obsolete
    DESCRIPTION     "The sapTlsDHCPLseStEntriesExceeded notification is
                     generated when the number  of  DHCP  lease states
                     entries on a given SAP reaches a user configurable
                     upper limit given by sapTlsDhcpLeasePopulate."
    ::= { sapTraps 6 }

sapTlsDHCPLeaseStateOverride NOTIFICATION-TYPE
    OBJECTS {
        custId,
        svcId,
        svcVpnId,
        sapPortId,
        sapEncapValue,
        tlsDhcpLseStateNewCiAddr,
        tlsDhcpLseStateNewChAddr,
        tlsDhcpLseStateOldCiAddr,
        tlsDhcpLseStateOldChAddr
    }
    STATUS          obsolete
    DESCRIPTION     "The sapTlsDHCPLeaseStateOverride notification is
                     generated when an existing DHCP lease state is
                     overridden by a new lease state which has the same
                     IP address but a different MAC address."
    ::= { sapTraps 7 }

sapTlsDHCPSuspiciousPcktRcvd NOTIFICATION-TYPE
    OBJECTS {
        custId,
        svcId,
        svcVpnId,
        sapPortId,
        sapEncapValue,
        tlsDhcpPacketProblem
    }
    STATUS          obsolete
    DESCRIPTION     "The sapTlsDHCPSuspiciousPcktRcvd notification is
                     generated when a DHCP packet is received with suspicious
                     content."
    ::= { sapTraps 8 }

sapDHCPLeaseEntriesExceeded NOTIFICATION-TYPE
    OBJECTS {
        custId,
        svcId,
        svcVpnId,
        sapPortId,
        sapEncapValue,
        svcDhcpLseStateNewCiAddr,
        svcDhcpLseStateNewChAddr,
        svcDhcpClientLease
    }
    STATUS          current
    DESCRIPTION     "The sapDHCPLeaseEntriesExceeded notification is generated
                     when the number of DHCP lease state entries on a given SAP
                     reaches a user configurable upper limit. This limit is
                     given by sapTlsDhcpLeasePopulate for a TLS service and by
                     TIMETRA-VRTR-MIB::vRtrIfDHCPLeasePopulate for an IES or
                     VPRN service."
    ::= { sapTraps 9 }

sapDHCPLseStateOverride NOTIFICATION-TYPE
    OBJECTS {
        custId,
        svcId,
        svcVpnId,
        sapPortId,
        sapEncapValue,
        svcDhcpLseStateNewCiAddr,
        svcDhcpLseStateNewChAddr,
        svcDhcpLseStateOldCiAddr,
        svcDhcpLseStateOldChAddr
    }
    STATUS          current
    DESCRIPTION     "The sapDHCPLseStateOverride notification is generated when
                     an existing DHCP lease state is overridden by a new lease
                     state which has the same IP address but a different MAC
                     address."
    ::= { sapTraps 10 }

sapDHCPSuspiciousPcktRcvd NOTIFICATION-TYPE
    OBJECTS {
        custId,
        svcId,
        svcVpnId,
        sapPortId,
        sapEncapValue,
        svcDhcpPacketProblem
    }
    STATUS          current
    DESCRIPTION     "The sapDHCPSuspiciousPcktRcvd notification is generated
                     when a DHCP packet is received with suspicious content."
    ::= { sapTraps 11 }

sapDHCPLseStatePopulateErr NOTIFICATION-TYPE
    OBJECTS {
        custId,
        svcId,
        svcVpnId,
        sapPortId,
        sapEncapValue,
        svcDhcpLseStatePopulateError
    }
    STATUS          current
    DESCRIPTION     "The sapDHCPLseStatePopulateErr notification indicates that
                     the system was unable to update the DHCP Lease State table
                     with the information contained in the DHCP ACK message.
                     The DHCP ACK message has been discarded."
    ::= { sapTraps 12 }

hostConnectivityLost NOTIFICATION-TYPE
    OBJECTS {
        custId,
        svcId,
        svcVpnId,
        sapPortId,
        sapEncapValue,
        hostConnectivityCiAddrType,
        hostConnectivityCiAddr,
        hostConnectivityChAddr
    }
    STATUS          current
    DESCRIPTION     "The hostConnectivityLost notification indicates that
                     the system lost the connectivity with the indicated host."
    ::= { sapTraps 13 }

hostConnectivityRestored NOTIFICATION-TYPE
    OBJECTS {
        custId,
        svcId,
        svcVpnId,
        sapPortId,
        sapEncapValue,
        hostConnectivityCiAddrType,
        hostConnectivityCiAddr,
        hostConnectivityChAddr
    }
    STATUS          current
    DESCRIPTION     "The hostConnectivityRestored notification indicates that
                     the system has restored the connectivity with the
                     indicated host."
    ::= { sapTraps 14 }

sapReceivedProtSrcMac NOTIFICATION-TYPE
    OBJECTS {
        svcId,
        sapPortId,
        sapEncapValue,
        protectedMacForNotify,
        sapTlsRestProtSrcMacAction
    }
    STATUS          current
    DESCRIPTION     "The sapReceivedProtSrcMac notification is generated when a
                     protected source MAC is received on a TLS SAP with 
                     sapTlsRestProtSrcMac 'true', or if the TLS
                     SAP belongs to an SHG with tlsShgRestProtSrcMac 'true'."
    ::= { sapTraps 15 }

sapStaticHostDynMacConflict NOTIFICATION-TYPE
    OBJECTS {
        svcId,
        sapPortId,
        sapEncapValue,
        staticHostDynamicMacIpAddress,
        staticHostDynamicMacConflict
    }
    STATUS          current
    DESCRIPTION     "The sapStaticHostDynMacConflict notification indicates
                     that the system is trying to learn a conflicting IP-only
                     static host dynamic MAC address
                     (sapStaticHostDynMacAddress)."
    ::= { sapTraps 16 }

sapTlsMacMoveExceeded NOTIFICATION-TYPE
    OBJECTS {
        custId,
        svcId,
        svcVpnId,
        sapPortId,
        sapEncapValue,
        sapAdminStatus,
        sapOperStatus,
        sapTlsMacMoveRateExcdLeft,
        sapTlsMacMoveNextUpTime,
        svcTlsMacMoveMaxRate,
        sapTlsNotifyMacAddr
    }
    STATUS          current
    DESCRIPTION     "The sapTlsMacMoveExceeded notification is generated
                     when the SAP exceeds the TLS svcTlsMacMoveMaxRate."
    ::= { sapTraps 17 }

sapDHCPProxyServerError NOTIFICATION-TYPE
    OBJECTS {
        custId,
        svcId,
        svcVpnId,
        sapPortId,
        sapEncapValue,
        svcDhcpProxyError
    }
    STATUS          current
    DESCRIPTION     "The sapDHCPProxyServerError notification indicates that
                     the system was unable to proxy DHCP requests."
    ::= { sapTraps 18 }

sapDHCPCoAError NOTIFICATION-TYPE
    OBJECTS {
        custId,
        svcId,
        svcVpnId,
        sapPortId,
        sapEncapValue,
        svcDhcpCoAError
    }
    STATUS          obsolete
    DESCRIPTION     "The sapDHCPCoAError notification indicates that
                     the system was unable to process a Change of Authorization
                     (CoA) request from a Radius server."
    ::= { sapTraps 19 }

sapDHCPSubAuthError NOTIFICATION-TYPE
    OBJECTS {
        custId,
        svcId,
        svcVpnId,
        sapPortId,
        sapEncapValue,
        svcDhcpSubAuthError
    }
    STATUS          obsolete
    DESCRIPTION     "The sapDHCPSubAuthError notification indicates that
                     the system encountered a problem while trying to
                     authenticate a subscriber."
    ::= { sapTraps 20 }

sapPortStateChangeProcessed NOTIFICATION-TYPE
    OBJECTS {
        sapNotifyPortId
    }
    STATUS          current
    DESCRIPTION     "The sapPortStateChangeProcessed notification indicates
                     that the agent has finished processing an access port
                     state change event, and that the operating status of
                     all the affected SAP's has been updated accordingly.
                     The value of the sapNotifyPortId object indicates the
                     ID of the port that experienced the state change."
    ::= { sapTraps 21 }

sapDHCPLseStateMobilityError NOTIFICATION-TYPE
    OBJECTS {
        custId,
        svcId,
        svcVpnId,
        sapPortId,
        sapEncapValue
    }
    STATUS          current
    DESCRIPTION     "The sapDHCPLseStateMobilityError notification indicates
                     that the system was unable to perform a mobility check
                     for this lease state."
    ::= { sapTraps 22 }

sapCemPacketDefectAlarm NOTIFICATION-TYPE
   OBJECTS {
        custId,
        svcVpnId,
        sapCemReportAlarmStatus,
        tmnxPortCemStatsReportAlarm
   }
   STATUS            current
   DESCRIPTION       "Generated when a CEM SAP alarm condition is detected.
                      It is generated only when the packet error indicated
                      by 'sapCemReportAlarmStatus' persists over a 3 second
                      window. tmnxPortCemStatsReportAlarm specifies, in the
                      case of APS Ports, the physical port raising the trap,
                      otherwise it is the SAP's port."
    ::= { sapTraps 23 }

sapCemPacketDefectAlarmClear NOTIFICATION-TYPE
   OBJECTS {
        custId,
        svcVpnId,
        sapCemReportAlarmStatus,
        tmnxPortCemStatsReportAlarm
   }
   STATUS            current
   DESCRIPTION       "Generated when a CEM SAP alarm condition is cleared.
                      It is generated only when the packet error indicated
                      by 'sapCemReportAlarmStatus' no longer persists over
                      a 10 second window. tmnxPortCemStatsReportAlarm
                      specifies, in the case of APS Ports, the physical
                      port raising the trap, otherwise it is the SAP's port."
    ::= { sapTraps 24 }

msapStateChanged NOTIFICATION-TYPE
   OBJECTS {
       svcId,
       sapPortId,
       sapEncapValue,
       msapStatus
   }
   STATUS          current
   DESCRIPTION     "The msapStateChanged notification is generated when a
                    Managed SAP is 'created', 'modified', or 'deleted', with the
                    value of msapStatus indicated which state it has entered."
   ::= { sapTraps 25 }

msapCreationFailure  NOTIFICATION-TYPE
   OBJECTS {
       custId,
       svcId,
       svcVpnId,
       sapPortId,
       sapEncapValue,
       svcManagedSapCreationError,
       sapNotifyPortId,
       sapNotifyEncapValue,
       sapTlsNotifyMacAddr
   }
   STATUS          current
   DESCRIPTION     "The trap msapCreationFailure is sent whenever
                    the system fails to create a managed SAP.
                    The svcId, svcVpnId, sapPortId and sapEncapValue are 
                    those of the capturing SAP.
                    
                    The values of sapNotifyPortId and sapNotifyEncapValue 
                    correspond to the managed SAP, and the value of 
                    sapTlsNotifyMacAddr is the MAC address that would have
                    been associated with the managed SAP, if the creation
                    would have succeeded."
   ::= { sapTraps 26 }
   
sapHostBGPPeeringSetupFailed NOTIFICATION-TYPE
    OBJECTS {
        custId,
        svcId,
        svcVpnId,
        sapPortId,
        sapEncapValue,
        sapBGPPeeringHostIpAddr,
        sapBGPPeeringHostIpAddrType,
        sapBGPPeeringVRtrID,
        sapBGPPeeringAttrDiscarded,
        sapBGPPeeringNotifDescription
    }
    STATUS          current
    DESCRIPTION     "The sapHostBGPPeeringSetupFailed notification indicates
                     that the system was unable to create a BGP neighbor  
                     and set up BGP peering for the given host."
    ::= { sapTraps 27 }

sapTlsDataSapInstStatusChgd NOTIFICATION-TYPE
   OBJECTS {
       sapTlsDataSapInstStatus,
       sapTlsDataSapInstLastErr
   }
   STATUS          current
   DESCRIPTION     "The sapTlsDataSapInstStatusChgd notification is generated
                    when there is a change in the value of
                    sapTlsDataSapInstStatus object.

                    sapTlsDataSapInstLastErr provides information related
                    to sapTlsDataSapInstStatus object."
   ::= { sapTraps 28 }

tmnxGreTunnelOperRemIpChg NOTIFICATION-TYPE
    OBJECTS {
        tmnxGreTunnelOperRemIpAddrType,
        tmnxGreTunnelOperRemIpAddr
    }
    STATUS          obsolete
    DESCRIPTION
        "[CAUSE] The tmnxGreTunnelOperRemIpChg notification is generated when
         there is a change in operational remote address
         'tmnxGreTunnelOperRemIpAddr' of the tunnel.

         [EFFECT] Operational state of the tunnel is not affected.

         [RECOVERY] Operator needs to look at the configuration of
         tmnxGreTunnelRemIpAddr and tmnxGreTunnelBackupRemIpAddr."
    ::= { sapTraps 29 }

sapTunnelStateChange NOTIFICATION-TYPE
    OBJECTS {
       svcId, 
       sapPortId, 
       sapEncapValue, 
       sapTunnelNotifyName, 
       sapTunnelNotifyState,
       sapTunnelNotifyReason
    }
    STATUS          current
    DESCRIPTION
        "[CAUSE] The sapTunnelStateChange notification is generated when
        IPsec/GRE tunnel indicated by sapTunnelNotifyName changes state to
        'down' due to sapTunnelNotifyReason.

        [EFFECT] IPsec/GRE tunnel associated with the SAP will remain in this
        state until a corrective action is taken.

        [RECOVERY] Depending on the reason indicated by sapTunnelNotifyReason,
        corrective action should be taken."
    ::= { sapTraps 30 }

sapAtmPppSessionFailure NOTIFICATION-TYPE
    OBJECTS {
        svcId, 
        sapPortId, 
        sapEncapValue,
        sapNotifyName,
        sapNotifyReason
    }
    STATUS          current
    DESCRIPTION
        "[CAUSE] The sapAtmPppSessionFailure notification indicates that
         the system could not create a new PPPoA session.
         
         The problem is described in the object sapNotifyReason. 
         
         The PPP user name is specified in the sapNotifyName.
        
        [EFFECT] The user that attempted to set up the PPP session cannot 
        establish the desired connection.
        
        [RECOVERY] Depending on the reason indicated by sapNotifyReason,
        corrective action may be necessary. However, it is possible that the
        failure is caused by the user's equipment configuration or by erroneous
        input by the user."
    ::= { sapTraps 31 }

sapAtmPppNcpFailure NOTIFICATION-TYPE
    OBJECTS {
        svcId,
        sapPortId,
        sapEncapValue,
        sapNotifyName,
        sapPppNcpFailureProtocol,
        sapNotifyReason
    }
    STATUS current
    DESCRIPTION
        "[CAUSE] The sapAtmPppNcpFailure notification indicates that
         there is a NCP phase setup problem.
         
         The problem is described in the object sapNotifyReason. 
         
         The PPP user name is specified in the sapNotifyName.
        
         [EFFECT] The IP protocol cannot be configured for the user that 
         attempted to set up the PPP session.
         
         [RECOVERY] Depending on the reason indicated by sapNotifyReason,
         corrective action may be necessary. However, it is possible that the
         failure is caused by the user's equipment configuration or by erroneous
         input by the user."
    ::= { sapTraps 32}

sapIpipeCeIpAddrChange NOTIFICATION-TYPE
    OBJECTS {
        custId,
        svcId,
        sapPortId,
        sapEncapValue,
        sapIpipeCeIpAddrType,
        sapIpipeCeIpAddress
    }
    STATUS          current
    DESCRIPTION
        "[CAUSE] The sapIpipeCeIpAddrChange notification indicates
         that an IP address has been discovered for the local end host
         of a specified IPIPE SAP. The IP address type is
         specified by sapIpipeCeIpAddrType. The IP address is specified
         by sapIpipeCeIpAddress.

         [EFFECT] The IP address specified by sapIpipeCeIpAddress and
         of type sapIpipeCeIpAddrType has been discovered for the local end 
         host.

         [RECOVERY]  No action is required"
    ::= { sapTraps 33 }

tmnxIpTunnelOperRemIpChg NOTIFICATION-TYPE
    OBJECTS {
        tmnxIpTunnelOperRemIpAddrType,
        tmnxIpTunnelOperRemIpAddr
    }
    STATUS          current
    DESCRIPTION
        "[CAUSE] The tmnxIpTunnelOperRemIpChg notification is generated when
         there is a change in operational remote address
         'tmnxIpTunnelOperRemIpAddr' of the tunnel.

         [EFFECT] Operational state of the tunnel is not affected.

         [RECOVERY] Operator needs to look at the configuration of
         tmnxIpTunnelRemIpAddr and tmnxIpTunnelBackupRemIpAddr."
    ::= { sapTraps 38 }

sapDcpStaticExcd             NOTIFICATION-TYPE
    OBJECTS {
        sapDcpFpStaticExcdCountHi,
        sapDcpFpStaticExcdCountLo,
        sapDCpuProtPolicy,
        sapDcpTimeEventOccured
    }
    STATUS  current
    DESCRIPTION
        "[CAUSE] The sapDcpStaticExcd notification is generated when the
         static-policer on a particular SAP has been detected as non-conformant
         to the associated distributed CPU protection policy parameters. This
         notification is generated when  
         TIMETRA-SECURITY-MIB.mib::tmnxDCpuProtStaticPlcrLogEvent is configured
         to 'enable' or 'verbose'.

         [EFFECT] The affected SAP may be using more resources than expected
         and cause the system to under-perform. This notification may indicate
         a Denial of Service attack or a misconfiguration in the network.

         [RECOVERY] Appropriate configuration changes to the distributed
         CPU protection policy or to the affected SAP may be required." 
    ::= { sapTraps 39 }

sapDcpDynamicExcd            NOTIFICATION-TYPE
    OBJECTS {
        sapDcpFpDynExcdCountHi,
        sapDcpFpDynExcdCountLo,
        sapDCpuProtPolicy,
        sapDcpTimeEventOccured
    }     
    STATUS  current
    DESCRIPTION
        "[CAUSE] The sapDcpDynamicExcd notification is generated when the
         protocol on a particular SAP has been detected as non-conformant to the
         associated distributed CPU protection policy parameters. This
         notification is generated when  
         TIMETRA-SECURITY-MIB.mib::tmnxDCpuProtProtocolDynLogEvent is configured
         to 'enable' or 'verbose'.

         [EFFECT] The affected SAP may be using more resources than expected 
         and cause the system to under-perform. This notification may indicate
         a Denial of Service attack or a misconfiguration in the network.

         [RECOVERY] Appropriate configuration changes to the distributed
         CPU protection policy or to the affected SAP may be required." 
    ::= { sapTraps 40 }    

sapDcpStaticHoldDownStart            NOTIFICATION-TYPE
    OBJECTS {
        sapDcpFpStaticExcdCountHi,
        sapDcpFpStaticExcdCountLo,
        sapDCpuProtPolicy,
        sapDcpTimeEventOccured
    } 
    STATUS  current
    DESCRIPTION
        "[CAUSE] The sapDcpStaticHoldDownStart notification is generated
         when a particular SAP starts hold-down period for an exceeding 
         static-policer. This notification is generated when
         TIMETRA-SECURITY-MIB.mib::tmnxDCpuProtStaticPlcrLogEvent is configured 
         to 'verbose'.

         [EFFECT] The static-policer will treat all packets as non-conformant
         during the hold-down period.

         [RECOVERY] There is no recovery required for this notification."
    ::= { sapTraps 41 }   

sapDcpDynamicHoldDownStart            NOTIFICATION-TYPE
    OBJECTS {
        sapDcpFpDynExcdCountHi,
        sapDcpFpDynExcdCountLo,
        sapDCpuProtPolicy,
        sapDcpTimeEventOccured
    }  
    STATUS  current
    DESCRIPTION
        "[CAUSE] The sapDcpDynamicHoldDownStart notification is generated
         when a particular SAP starts hold-down period for an exceeding 
         protocol. This notification is generated when
         TIMETRA-SECURITY-MIB.mib::tmnxDCpuProtProtocolDynLogEvent is configured
         to 'verbose'.

         [EFFECT] The protocol will treat all packets as non-conformant during
         the hold-down period.

         [RECOVERY] There is no recovery required for this notification."
    ::= { sapTraps 42 }  

sapDcpStaticHoldDownEnd            NOTIFICATION-TYPE
    OBJECTS {
        sapDcpFpStaticExcdCountHi,
        sapDcpFpStaticExcdCountLo,
        sapDCpuProtPolicy,
        sapDcpTimeEventOccured
    }  
    STATUS  current
    DESCRIPTION
        "[CAUSE] The sapDcpStaticHoldDownEnd notification is generated
         when a particular SAP completes hold-down period for an exceeding 
         static-policer. This notification is generated when 
         TIMETRA-SECURITY-MIB.mib::tmnxDCpuProtStaticPlcrLogEvent is configured 
         to 'verbose'.

         [EFFECT] The static-policer for an affected SAP will transition to a
         detection-time countdown after the hold-down period is complete.

         [RECOVERY] There is no recovery required for this notification."
    ::= { sapTraps 43 }  
  
sapDcpDynamicHoldDownEnd            NOTIFICATION-TYPE
    OBJECTS {
        sapDcpFpDynExcdCountHi,
        sapDcpFpDynExcdCountLo,
        sapDCpuProtPolicy,
        sapDcpTimeEventOccured
    }  
    STATUS  current
    DESCRIPTION
        "[CAUSE]  The sapDcpDynamicHoldDownEnd notification is generated
         when a particular SAP completes hold-down period for an exceeding 
         protocol. This notification is generated when 
         TIMETRA-SECURITY-MIB.mib::tmnxDCpuProtProtocolDynLogEvent is configured 
         to 'verbose'.

         [EFFECT] The protocol for an affected SAP will transition to a 
         detection-time countdown after the hold-down period is complete.

         [RECOVERY] There is no recovery required for this notification."
    ::= { sapTraps 44 }  

sapDcpStaticConform            NOTIFICATION-TYPE
    OBJECTS {
        sapDcpFpStaticExcdCountHi,
        sapDcpFpStaticExcdCountLo,
        sapDCpuProtPolicy,
        sapDcpTimeEventOccured
    }  
    STATUS  current
    DESCRIPTION
        "[CAUSE] The sapDcpStaticConform notification is generated when  
         the static-policer for a particular SAP has been detected as conformant
         for a period of the configured detection-time after having been 
         previously detected as exceeding and completed any hold-down period.
         This notification is generated when 
         TIMETRA-SECURITY-MIB.mib::tmnxDCpuProtStaticPlcrLogEvent is configured
         to 'enable' or 'verbose'.

         [EFFECT] The affected SAP is now in conformance with the parameters 
         configured for the associated distributed CPU protection policy.

         [RECOVERY] There is no recovery required for this notification."
    ::= { sapTraps 45 } 
   
sapDcpDynamicConform            NOTIFICATION-TYPE
    OBJECTS {
        sapDcpFpDynExcdCountHi,
        sapDcpFpDynExcdCountLo,
        sapDCpuProtPolicy,
        sapDcpTimeEventOccured
    }

    STATUS  current
    DESCRIPTION
        "[CAUSE] The sapDcpDynamicConform notification is generated when  
         the protocol for a particular SAP has been detected as conformant for
         a period of the configured detection-time after having been previously
         detected as exceeding and completed any hold-down period. This 
         notification is generated when 
         TIMETRA-SECURITY-MIB.mib::tmnxDCpuProtStaticPlcrLogEvent is configured
         to 'enable' or 'verbose'.

         [EFFECT] The affected SAP is now in conformance with the parameters 
         configured for the associated distributed CPU protection policy.

         [RECOVERY] There is no recovery required for this notification."
    ::= { sapTraps 46 } 

sapDcpLocMonExcd            NOTIFICATION-TYPE
    OBJECTS {
        sapDcpFpLocMonExcdCountHi,
        sapDcpFpLocMonExcdCountLo,
        sapDCpuProtPolicy,
        sapDcpTimeEventOccured
    }

    STATUS  current
    DESCRIPTION
        "[CAUSE] The sapDcpLocMonExcd notification is generated when the
         local-monitoring-policer for a particular SAP has transitioned from a
         conformant state to a non-conformant state and the system will attempt
         to allocate dymanic enforcement policers. This notification is
         generated when TIMETRA-SECURITY-MIB.mib::tmnxDCpuProtLocMonPlcrLogEvent
         is configured to 'verbose'.

         [EFFECT] The affected SAP may be using more resources than expected and
         cause the system to under-perform. This notification may indicate a 
         Denial of Service attack or a misconfiguration in the network.

         [RECOVERY] Appropriate configuration changes to the distributed CPU 
         protection policy or to the affected SAP may be required."
    ::= { sapTraps 47}
    
sapDcpLocMonExcdDynResource            NOTIFICATION-TYPE
    OBJECTS {
        sapDcpFpLocMonExcdCountHi,
        sapDcpFpLocMonExcdCountLo,
        sapDCpuProtPolicy,
        sapDcpTimeEventOccured
    }

    STATUS  current
    DESCRIPTION
        "[CAUSE] The sapDcpLocMonExcdDynResource notification is generated
         when the local-monitoring-policer for a particular SAP has transitioned
         from a conformant state to a non-conformant state and the system cannot
         allocate all the dynamic enforcements policers associated with the
         distributed CPU protection policy . This notification is generated when 
         TIMETRA-SECURITY-MIB.mib::tmnxDCpuProtLocMonPlcrLogEvent is configured
         to 'enable' or 'verbose'.

         [EFFECT] The affected SAP may be using more resources than expected and
         cause the system to under-perform. This notification may indicate a
         Denial of Service attack or a misconfiguration in the network.

         [RECOVERY] Appropriate configuration changes to the distributed CPU 
         protection policy or to the affected SAP or to the dynamic enforcement
         policer pool(TIMETRA-CHASSIS-MIB.mib::tmnxFPDCpuProtDynEnfrcPlcrPool)."
    ::= { sapTraps 48 }

sapDcpLocMonExcdAllDynAlloc            NOTIFICATION-TYPE
    OBJECTS {
        sapDcpFpLocMonExcdCountHi,
        sapDcpFpLocMonExcdCountLo,
        sapDCpuProtPolicy,
        sapDcpTimeEventOccured
    } 
    STATUS  current
    DESCRIPTION
        "[CAUSE] The sapDcpLocMonExcdAllDynAlloc notification is generated
         when all dynamic enforcement policers associated with a non-conformant
         local-monitoring-policer have been successfully allocated for a
         particular SAP. This notification is generated when 
         TIMETRA-SECURITY-MIB.mib::tmnxDCpuProtLocMonPlcrLogEvent is configure 
         to 'verbose'.

         [EFFECT] The affected SAP may be using more resources than expected 
         and cause the system to under-perform.

         [RECOVERY] Appropriate configuration changes to the distributed CPU 
         protection policy or to the affected SAP may be required."
    ::= { sapTraps 49 }

sapDcpLocMonExcdAllDynFreed            NOTIFICATION-TYPE
    OBJECTS {
        sapDcpFpLocMonState,
        sapDCpuProtPolicy,
        sapDcpTimeEventOccured
    }
    STATUS  current
    DESCRIPTION
        "[CAUSE] The sapDcpLocMonExcdAllDynFreed notification is generated
         for a particular SAP when all the previously allocated dynamic
         enforcement policers for a particular local-monitoring-policer on the
         associated distributed CPU protection policy have been freed up and all
         the protocols are once again being monitored by local-monitor. This
         notification is generated when 
         TIMETRA-SECURITY-MIB.mib::tmnxDCpuProtLocMonPlcrLogEvent is configured
         to 'verbose'.

         [EFFECT] The affected SAP may be using more resources than expected 
         and cause the system to under-perform.

         [RECOVERY] There is no recovery required for this notification."
    ::= { sapTraps 50 }

sapDcpDynamicEnforceAlloc            NOTIFICATION-TYPE
    OBJECTS {
        sapDcpFpDynAllocated,
        sapDCpuProtPolicy,
        sapDcpTimeEventOccured
    } 
    STATUS  current
    DESCRIPTION
        "[CAUSE] The sapDcpDynamicEnforceAlloc notification is generated 
         when a dynamic enforcement policer is allocated on a particular 
         SAP. This notification is generated when 
         TIMETRA-SECURITY-MIB.mib::tmnxDCpuProtProtocolDynLogEvent is 
         configured to 'verbose'.

         [EFFECT] The affected SAP is not in conformance with the
         configured parameters of the associated distributed CPU protection
         policy and may be using more resources than expected and cause the 
         system to under-perform.

         [RECOVERY] Appropriate configuration changes to the distributed CPU 
         protection policy or to the affected SAP may be required."
    ::= { sapTraps 51 }

sapDcpDynamicEnforceFreed            NOTIFICATION-TYPE
    OBJECTS {
        sapDcpFpDynExcdCountHi,
        sapDcpFpDynExcdCountLo,
        sapDCpuProtPolicy,
        sapDcpTimeEventOccured
    } 
    STATUS  current
    DESCRIPTION
        "[CAUSE] The sapDcpDynamicEnforceFreed notification is generated 
         when a dynamic enforcement policer is freed on a particular SAP.
         This notification is generated when
         TIMETRA-SECURITY-MIB.mib::tmnxDCpuProtProtocolDynLogEvent is configured
         to 'verbose'.

         [EFFECT] The affected SAP is now in conformance with the configured
         parameters of the associated distributed CPU protection policy.

         [RECOVERY] There is no recovery required for this notification."
    ::= { sapTraps 52 }

sapTlsMacMoveExceedNonBlock NOTIFICATION-TYPE
    OBJECTS {
        custId,
        svcId,
        svcVpnId,
        sapPortId,
        sapEncapValue,
        svcTlsMacMoveMaxRate,
        sapTlsNotifyMacAddr
    }
    STATUS          current
    DESCRIPTION
        "[CAUSE] The sapTlsMacMoveExceedNonBlock notification is generated
         when the SAP exceeds the TLS svcTlsMacMoveMaxRate when
         sapTlsLimitMacMove is set to 'nonBlocking'.
         
         [EFFECT] This notification is informational only.
         
         [RECOVERY] User can adjust the value of svcTlsMacMoveMaxRate to
         reduce the frequency of this notification."
    ::= { sapTraps 53 }

sapEthLoopbackStarted            NOTIFICATION-TYPE
    OBJECTS {
        sapEthLoopbackMode,
        sapEthLoopbackMacSwap,
        sapEthLoopbackMacSwapAddr,
        sapEthLoopbackMacSwapAddrAll
    }
    STATUS      current
    DESCRIPTION
        "[CAUSE] The sapEthLoopbackStarted notification is generated when the
         SAP is placed into loopback.

         [EFFECT] This notification is informational only."
    ::= { sapTraps 54 }

sapEthLoopbackStopped            NOTIFICATION-TYPE
    OBJECTS {
        sapEthLoopbackMode
    }
    STATUS      current
    DESCRIPTION
        "[CAUSE] The sapEthLoopbackStopped notification is generated when the
         SAP is removed from loopback.

         [EFFECT] This notification is informational only."
    ::= { sapTraps 55 }

sapTunnelEncapIpMtuTooSmall NOTIFICATION-TYPE
    OBJECTS {
       svcId,
       sapPortId,
       sapEncapValue,
       sapTunnelNotifyName,
       sapTunnelNotifyConfigIpMtu,
       sapTunnelNotifyEncapOverhead,
       sapTunnelNotifyConfigEncapIpMtu
    }
    STATUS current
    DESCRIPTION
        "[CAUSE] The sapTunnelEncapIpMtuTooSmall notification is generated when
         the addition of tunnel encapsulation to a packet at or near the IP
         Tunnel's configured IP MTU may cause it to exceed the tunnel's
         configured encapsulated IP MTU.
 
         [EFFECT] The pre-encapsulated packet may be fragmented, and will require
         reassembly by the tunnel remote endpoint, causing a performance impact.
 
         [RECOVERY] Configured IP MTU and/or encapsulated IP MTU may need to be
         changed depending on the size of the encapsulation overhead as indicated
         in 'sapTunnelNotifyEncapOverhead', and the transmission capabilities of
         the tunnel's transport network."
    ::= { sapTraps 56 }

sapHostRipListenerSetupFailed NOTIFICATION-TYPE
    OBJECTS {
        custId,
        svcId,
        svcVpnId,
        sapPortId,
        sapEncapValue,
        sapRipListenerHostIpAddr,
        sapRipListenerHostIpAddrType,
        sapRipListenerVRtrID,
        sapRipListenerNotifDescription
    }
    STATUS          current
    DESCRIPTION
        "The sapHostRipListenerSetupFailed notification is 
         generated when the system was unable to set up a 
         RIP listener for the given host.
                     
         [CAUSE] <To be documented>
         
         [EFFECT] <To be documented>
         
         [RECOVERY] No recovery is required on this system."
    ::= { sapTraps 57 }

sapStatHost6DynMacConflict NOTIFICATION-TYPE
    OBJECTS {
        sapStatHost6DynMacAddress,
        sapNotifyReason
    }
    STATUS          current
    DESCRIPTION
        "The sapStatHost6DynMacConflict notification is 
         generated when the system was unable to update the MAC
         address of a static IPv6 host.
                     
         [CAUSE] The system failed to update the MAC address of a static IPv6 host.
         
         [EFFECT] The static IPv6 host has a MAC address that is not up to date.
         
         [RECOVERY] The recovery action depends on the exact reason why the
          MAC update failed. This is clarified in the sapNotifyReason object."
    ::= { sapTraps 58 }

tmnxIpTunnelOperStateChange      NOTIFICATION-TYPE
    OBJECTS {
        tmnxIpTunnelAdminState,
        tmnxIpTunnelOperState,
        tmnxIpTunnelOperFlags
    }
    STATUS          current
    DESCRIPTION
        "[CAUSE] The tmnxIpTunnelOperStateChange notification is generated
         when there is a change in tmnxIpTunnelOperState for an IP tunnel.

         [EFFECT] When the tunnel is operationally down, traffic arriving at
         the tunnel endpoints will not be encapsulated and transported."
    ::= { sapTraps 59 }

-- ------------------------------------
-- TLS STP traps
-- ------------------------------------
topologyChangeSapMajorState NOTIFICATION-TYPE
    OBJECTS {
        custId,
        svcId,
        sapPortId,
        sapEncapValue
    }
    STATUS         current
    DESCRIPTION    "The    topologyChangeSapMajorState   notification    is
                    generated  when  a  SAP has transitioned its state from
                    learning  to  forwarding or from forwarding to blocking
                    or broken. The spanning tree topology has been modified
                    and   it   may   denote  loss  of  customer  access  or
                    redundancy.   Check   the   new  topology  against  the
                    provisioned  topology  to  determine  the  severity  of
                    connectivity loss."
    ::= { tstpTraps 1 }

newRootSap NOTIFICATION-TYPE
    OBJECTS {
        custId,
        svcId,
        sapPortId,
        sapEncapValue
    }
    STATUS          current
    DESCRIPTION     "The  newRootSap  notification is  generated  when  the
                     previous  root bridge has been aged out and a new root
                     bridge  has  been elected. A new root bridge creates a
                     new  spanning  tree topology and it may denote loss of
                     customer  access or redundancy. Check the new topology
                     against  the  provisioned  topology  to  determine the
                     severity of connectivity loss."
    ::= { tstpTraps 2 }

topologyChangeSapState NOTIFICATION-TYPE
    OBJECTS {
        custId,
        svcId,
        sapPortId,
        sapEncapValue
    }
    STATUS          current
    DESCRIPTION     "The topologyChangeSapState notification is   generated
                     when  a  SAP  has  transitioned  state  to blocking or
                     broken  from a state other than forwarding. This event
                     complements     what     is     not     covered     by
                     topologyChangeSapMajorState.    The    spanning   tree
                     topology  has  been modified and it may denote loss of
                     customer  access or redundancy. Check the new topology
                     against the provisioned topology to determine severity
                     of connectivity loss."
    ::= { tstpTraps 5 }

receivedTCN NOTIFICATION-TYPE
    OBJECTS {
        custId,
        svcId,
        sapPortId,
        sapEncapValue
    }
    STATUS          current
    DESCRIPTION     "The receivedTCN notification is generated  when  a SAP
                     has received TCN from another bridge. This bridge will
                     either  have  its  configured  BPDU  with the topology
                     change  flag  set  if  it is a root bridge, or it will
                     pass  TCN  to  its root bridge. Eventually the address
                     aging  timer  for the forwarding database will be made
                     shorter  for  a  short  period of time. No recovery is
                     needed."
    ::= { tstpTraps 6 }

higherPriorityBridge NOTIFICATION-TYPE
    OBJECTS {
        custId,
        svcId,
        sapPortId,
        sapEncapValue,
        tmnxCustomerBridgeId,
        tmnxCustomerRootBridgeId
    }
    STATUS          current
    DESCRIPTION     "The higherPriorityBridge notification is generated when
                     a  customer's device has been configured with a bridge
                     priority  equal  to  zero. The SAP that the customer's
                     device  is  connected  through will be blocked. Remove
                     the  customer's  device  or reconfigure the customer's
                     bridge priority with a value greater than zero."
    ::= { tstpTraps 9 }

bridgedTLS NOTIFICATION-TYPE
    OBJECTS {
        custId,
        svcId,
        sapPortId,
        sapEncapValue
    }
    STATUS          obsolete
    DESCRIPTION     "The  bridgedTLS  notification  is  generated  when   a
                     configuration  BPDU  has been received that identifies
                     that  another TLS with a different VPNID is attempting
                     to   bridge   with   this   TLS.   At  least  one  ESR
                     participating  within  one  of the TLS that is locally
                     connected must have an active VCP for this to be seen.
                     The  SAP  that  the  configuration BPDU is received on
                     will  be  blocked  to prevent the TLS to TLS bridging.
                     Reconfigure  the  bridged  TLS  into  a  single TLS or
                     remove the connectivity."
    ::= { tstpTraps 10 }

sapEncapPVST NOTIFICATION-TYPE
    OBJECTS {
        custId,
        svcId,
        sapPortId,
        sapEncapValue,
        tmnxOtherBridgeId
    }
    STATUS          current
    DESCRIPTION     "The sapEncapPVST  notification  is  generated when the
                     SAP  receives  a BPDU that is PVST encapsulated, after
                     having  received  BPDUs  that were 802.d encapsulated.
                     The  SAP  BPDUs  will  also  be  PVST encapsulated. No
                     recovery is needed."
    ::= { tstpTraps 11 }

sapEncapDot1d NOTIFICATION-TYPE
    OBJECTS {
        custId,
        svcId,
        sapPortId,
        sapEncapValue,
        tmnxOtherBridgeId
    }
    STATUS          current
    DESCRIPTION     "The  sapEncapDot1d  notification is generated when the
                     SAP  receives a BPDU that is 802.1d encapsulated after
                     having received BPDUs that were PVST encapsulated. The
                     SAP   BPDUs  will  also  be  802.1d  encapsulated.  No
                     recovery is needed."
    ::= { tstpTraps 12 }

sapReceiveOwnBpdu NOTIFICATION-TYPE
    OBJECTS {
        custId,
        svcId,
        sapPortId,
        sapEncapValue,
        tmnxOtherBridgeId
    }
    STATUS          obsolete
    DESCRIPTION     "The sapReceiveOwnBpdu notification is generated when the
                     SAP STP received it's own BPDU."
    ::= { tstpTraps 13 }

sapActiveProtocolChange NOTIFICATION-TYPE
    OBJECTS {
        custId,
        svcId,
        sapPortId,
        sapEncapValue,
        sapTlsStpOperProtocol
    }
    STATUS          current
    DESCRIPTION     "The sapActiveProtocolChange notification is generated
                     when  the  spanning  tree protocol on this SAP changes
                     from  rstp  to  stp  or  vise  versa.  No  recovery is
                     needed."
    ::= { tstpTraps 30 }

tmnxStpRootGuardViolation NOTIFICATION-TYPE
    OBJECTS {
        svcId,
        sapPortId,
        sapEncapValue,
        sapTlsStpRootGuardViolation
    }
    STATUS          current
    DESCRIPTION     "The tmnxStpRootGuardViolation notification is
                     generated when a SAP which has root-guard configured is
                     trying to become root (has a better STP priority vector).
                     The SAP will become alternate and traffic will be blocked."
    ::= { tstpTraps 35 }

tmnxSapStpExcepCondStateChng NOTIFICATION-TYPE
    OBJECTS {
        custId,
        svcId,
        sapPortId,
        sapEncapValue,
        sapTlsStpException
    }
    STATUS          current
    DESCRIPTION     "The tmnxSapStpExcepCondStateChng notification is
                     generated when the value of the object sapTlsStpException
                     has changed, i.e. when the exception condition 
                     changes on the indicated SAP."
    ::= { tstpTraps 37 }

-- ----------------------------------------------------------------------------
-- Conformance Information
-- ----------------------------------------------------------------------------
tmnxSapCompliances  OBJECT IDENTIFIER ::= { tmnxSapConformance 1 }
tmnxSapGroups       OBJECT IDENTIFIER ::= { tmnxSapConformance 2 }
tmnxDCSapCompliances  OBJECT IDENTIFIER ::= { tmnxSapConformance 3 }
tmnxDCSapGroups       OBJECT IDENTIFIER ::= { tmnxSapConformance 4 }


-- ----------------------------------------------
-- Compliance Statements
-- ----------------------------------------------
tmnxSap7450V6v0Compliance MODULE-COMPLIANCE
    STATUS  obsolete
    DESCRIPTION
        "The compliance statement for management of services SAPs
         on Nokia 7450 ESS series systems."
    MODULE  -- this module
        MANDATORY-GROUPS
        {
           tmnxSapV6v0Group,
           tmnxSapTlsV6v0Group,
           tmnxSapBaseV6v0Group,
           -- tmnxSapAtmV6v0Group,
           tmnxSapQosV6v0Group,
           tmnxSapStaticHostV6v0Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           tmnxSapHsmdaV6v0Group,
           tmnxSapNotifyGroup,
           tmnxSapNotificationObjV6v0Group,
           -- tmnxSapCemNotificationV6v0Group,
           -- tmnxTlsMsapPppoeV6v0Group,
           -- tmnxSapCemV6v0Group
           -- tmnxSapIpV6FilterV6v0Group
           tmnxSapDhcpV6v0Group,
           tmnxSapMrpV6v0Group,
           tmnxSapBsxV6v0Group
       }
    ::= { tmnxSapCompliances 100 }

tmnxSap7750V6v0Compliance MODULE-COMPLIANCE
    STATUS  obsolete
    DESCRIPTION
        "The compliance statement for management of services SAPs
         on Nokia SROS series systems."
    MODULE  -- this module
        MANDATORY-GROUPS
        {
           tmnxSapV6v0Group,
           tmnxSapTlsV6v0Group,
           tmnxSapBaseV6v0Group,
           tmnxSapAtmV6v0Group,
           tmnxSapQosV6v0Group,
           tmnxSapStaticHostV6v0Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           tmnxSapHsmdaV6v0Group,
           tmnxSapNotifyGroup,
           tmnxSapNotificationObjV6v0Group,
           tmnxSapCemNotificationV6v0Group,
           tmnxTlsMsapPppoeV6v0Group,
           tmnxSapCemV6v0Group,
           tmnxSapIpV6FilterV6v0Group,
           tmnxSapDhcpV6v0Group,
           tmnxSapMrpV6v0Group,
           tmnxSapBsxV6v0Group
       }
    ::= { tmnxSapCompliances 101 }

tmnxSap7710V6v0Compliance MODULE-COMPLIANCE
    STATUS  obsolete
    DESCRIPTION
        "The compliance statement for management of services SAPs
         on Nokia 7710 SR series systems."
    MODULE  -- this module
        MANDATORY-GROUPS
        {
           tmnxSapV6v0Group,
           tmnxSapTlsV6v0Group,
           tmnxSapBaseV6v0Group,
           tmnxSapAtmV6v0Group,
           tmnxSapQosV6v0Group,
           tmnxSapStaticHostV6v0Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           -- tmnxSapHsmdaV6v0Group,
           tmnxSapNotifyGroup,
           tmnxSapNotificationObjV6v0Group,
           tmnxSapCemNotificationV6v0Group,
           tmnxTlsMsapPppoeV6v0Group,
           tmnxSapCemV6v0Group,
           tmnxSapIpV6FilterV6v0Group,
           tmnxSapDhcpV6v0Group,
           tmnxSapMrpV6v0Group
       }
    ::= { tmnxSapCompliances 102 }

tmnxSap7450V6v1Compliance MODULE-COMPLIANCE
    STATUS  obsolete
    DESCRIPTION
        "The compliance statement for management of services SAPs
         on Nokia 7450 ESS series systems."
    MODULE  -- this module
        MANDATORY-GROUPS
        {
           tmnxSapV6v0Group,
           tmnxSapTlsV6v1Group,
           tmnxSapBaseV6v0Group,
           -- tmnxSapAtmV6v0Group,
           tmnxSapQosV6v0Group,
           tmnxSapStaticHostV6v1Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           -- tmnxSapMsapV6v1Group,
           tmnxSapHsmdaV6v0Group,
           tmnxSapNotifyGroup,
           tmnxSapNotificationObjV6v0Group,
           -- tmnxSapCemNotificationV6v0Group,
           -- tmnxTlsMsapPppoeV6v0Group,
           -- tmnxSapCemV6v0Group
           -- tmnxSapIpV6FilterV6v0Group
           tmnxSapDhcpV6v0Group,
           tmnxSapMrpV6v0Group,
           tmnxSapBsxV6v0Group
       }
    ::= { tmnxSapCompliances 103 }

tmnxSap7750V6v1Compliance MODULE-COMPLIANCE
    STATUS  obsolete
    DESCRIPTION
        "The compliance statement for management of services SAPs
         on Nokia SROS series systems."
    MODULE  -- this module
        MANDATORY-GROUPS
        {
           tmnxSapV6v0Group,
           tmnxSapTlsV6v1Group,
           tmnxSapBaseV6v0Group,
           tmnxSapAtmV6v0Group,
           tmnxSapQosV6v0Group,
           tmnxSapStaticHostV6v1Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           tmnxSapMsapV6v1Group,
           tmnxSapHsmdaV6v0Group,
           tmnxSapNotifyGroup,
           tmnxSapNotificationObjV6v0Group,
           tmnxSapCemNotificationV6v0Group,
           tmnxTlsMsapPppoeV6v0Group,
           tmnxSapCemV6v0Group,
           tmnxSapIpV6FilterV6v0Group,
           tmnxSapDhcpV6v0Group,
           tmnxSapMrpV6v0Group,
           tmnxSapBsxV6v0Group
       }
    ::= { tmnxSapCompliances 104 }

tmnxSap7710V6v1Compliance MODULE-COMPLIANCE
    STATUS  obsolete
    DESCRIPTION
        "The compliance statement for management of services SAPs
         on Nokia 7710 SR series systems."
    MODULE  -- this module
        MANDATORY-GROUPS
        {
           tmnxSapV6v0Group,
           tmnxSapTlsV6v1Group,
           tmnxSapBaseV6v0Group,
           tmnxSapAtmV6v0Group,
           tmnxSapQosV6v0Group,
           tmnxSapStaticHostV6v1Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           tmnxSapMsapV6v1Group,
           -- tmnxSapHsmdaV6v0Group,
           tmnxSapNotifyGroup,
           tmnxSapNotificationObjV6v0Group,
           tmnxSapCemNotificationV6v0Group,
           tmnxTlsMsapPppoeV6v0Group,
           tmnxSapCemV6v0Group,
           tmnxSapIpV6FilterV6v0Group,
           tmnxSapDhcpV6v0Group,
           tmnxSapMrpV6v0Group
           -- tmnxSapBsxV6v0Group           no Application Assurance on 7710
       }
    ::= { tmnxSapCompliances 105 }

tmnxSap7450V7v0Compliance MODULE-COMPLIANCE
    STATUS  obsolete
    DESCRIPTION
        "The compliance statement for management of services SAPs
         on Nokia 7450 ESS series systems."
    MODULE  -- this module
        MANDATORY-GROUPS
        {
           tmnxSapV7v0Group,
           tmnxSapTlsV6v1Group,
           tmnxSapBaseV6v0Group,
           tmnxSapQosV6v0Group,
           tmnxSapStaticHostV6v1Group,
           tmnxSapPortIdV6v0Group,
           tmnxSapSubMgmtV6v0Group,
           tmnxSapMstiV6v0Group,
           tmnxSapPolicyV6v0Group,
           tmnxSapL2ptV6v0Group,
           tmnxSapMsapV6v0Group,
           -- tmnxSapMsapV6v1Group,
           tmnxSapHsmdaV6v0Group,
           tmnxSapNotifyGroup,
           -- tmnxSapCemNotificationV6v0Group,
           -- tmnxTlsMsapPppoeV6v0Group,
           -- tmnxSapCemV6v0Group
           -- tmnxSapIpV6FilterV6v0Group
           tmnxSapDhcpV6v0Group,
           tmnxSapMrpV6v0Group,
           tmnxSapBsxV7v0Group,
           tmnxSapArpHostGroup,
           tmnxSapIgmpTrkGroup,
           -- tmnxSapAtmV7v0Group,
           tmnxSapIpipeV7v0Group,
           tmnxSapPbbGroup,
           tmnxSapTlsV7v0Group
        }
    ::= { tmnxSapCompliances 106 }

tmnxSap7750V7v0Compliance MODULE-COMPLIANCE
    STATUS  obsolete
    DESCRIPTION
        "The compliance statement for management of services SAPs
         on Nokia SROS series systems."
    MODULE  -- this module
        MANDATORY-GROUPS
        {
           tmnxSapV7v0Group,
           tmnxSapTlsV6v1Group,
           tmnxSapBaseV6v0Group,
           tmnxSapAtmV6v0Group,
           tmnxSapQosV6v0Group,
           tmnxSapStaticHostV6v1Group,
           tmnxSapPortIdV6v0Group,
           tmnxSapSubMgmtV6v0Group,
           tmnxSapMstiV6v0Group,
           tmnxSapPolicyV6v0Group,
           tmnxSapL2ptV6v0Group,
           tmnxSapMsapV6v0Group,
           tmnxSapMsapV6v1Group,
           tmnxSapHsmdaV6v0Group,
           tmnxSapNotifyGroup,
           tmnxSapCemNotificationV6v0Group,
           tmnxTlsMsapPppoeV6v0Group,
           tmnxSapCemV6v0Group,
           tmnxSapIpV6FilterV6v0Group,
           tmnxSapDhcpV6v0Group,
           tmnxSapMrpV6v0Group,
           tmnxSapBsxV7v0Group,
           tmnxSapArpHostGroup,
           tmnxSapIgmpTrkGroup,
           tmnxSapFrGroup,
           tmnxSapIpipeV7v0Group,
           tmnxSapPbbGroup,
           tmnxSapTlsV7v0Group
       }
    ::= { tmnxSapCompliances 107 }

tmnxSap7710V7v0Compliance MODULE-COMPLIANCE
    STATUS  obsolete
    DESCRIPTION
        "The compliance statement for management of services SAPs
         on Nokia 7710 SR series systems."
    MODULE  -- this module
        MANDATORY-GROUPS
        {
           tmnxSapV7v0Group,
           tmnxSapTlsV6v1Group,
           tmnxSapBaseV6v0Group,
           tmnxSapQosV6v0Group,
           tmnxSapStaticHostV6v1Group,
           tmnxSapPortIdV6v0Group,
           tmnxSapSubMgmtV6v0Group,
           tmnxSapMstiV6v0Group,
           tmnxSapPolicyV6v0Group,
           tmnxSapL2ptV6v0Group,
           tmnxSapMsapV6v0Group,
           tmnxSapMsapV6v1Group,
           -- tmnxSapHsmdaV6v0Group,
           tmnxSapNotifyGroup,
           tmnxSapCemNotificationV6v0Group,
           tmnxTlsMsapPppoeV6v0Group,
           tmnxSapCemV6v0Group,
           tmnxSapIpV6FilterV6v0Group,
           tmnxSapDhcpV6v0Group,
           tmnxSapMrpV6v0Group,
           -- tmnxSapBsxV7v0Group           no Application Assurance on 7710
           tmnxSapArpHostGroup,
           tmnxSapIgmpTrkGroup,
           tmnxSapFrGroup,
           tmnxSapIpipeV7v0Group,
           tmnxSapPbbGroup,
           tmnxSapTlsV7v0Group
       }
    ::= { tmnxSapCompliances 108 }

tmnxSap7450V8v0Compliance MODULE-COMPLIANCE
    STATUS  obsolete
    DESCRIPTION
        "The compliance statement for management of services SAPs
         on Nokia 7450 ESS series systems release 8.0 ."
    MODULE  -- this module
        MANDATORY-GROUPS
        {
           tmnxSapV8v0Group,
           tmnxSapTlsV8v0Group,
           tmnxSapBaseV6v0Group,
           tmnxSapQosV8v0Group,
           tmnxSapStaticHostV6v1Group,
           tmnxSapPortIdV6v0Group,
           tmnxSapSubMgmtV8v0Group,
           tmnxSapMstiV6v0Group,
           tmnxSapPolicyV6v0Group,
           tmnxSapL2ptV6v0Group,
           tmnxSapMsapV8v0Group,
           -- tmnxSapMsapV6v1Group,
           tmnxSapHsmdaV6v0Group,
           tmnxSapNotifyGroup,
           -- tmnxSapCemNotificationV6v0Group,
           -- tmnxTlsMsapPppoeV6v0Group,
           -- tmnxSapCemV6v0Group
           -- tmnxSapIpV6FilterV6v0Group
           tmnxSapDhcpV8v0Group,
           tmnxSapMrpV8v0Group,
           tmnxSapBsxV7v0Group,
           tmnxSapArpHostGroup,
           tmnxSapIgmpTrkGroup,
           tmnxSapIgmpTrkV8v0Group,
           -- tmnxSapAtmV7v0Group,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapGreGroup,
           tmnxSapMvrpV8v0Group,
           tmnxSapNotificationV8v0Group,
           tmnxSapMvrpNotificationV8v0Group,
           tmnxSapEthCfmMonitorGroup
       }
    ::= { tmnxSapCompliances 109 }

tmnxSap7750V8v0Compliance MODULE-COMPLIANCE
    STATUS  obsolete
    DESCRIPTION
        "The compliance statement for management of services SAPs
         on Nokia SROS series systems release 8.0 ."
    MODULE  -- this module
        MANDATORY-GROUPS
        {
           tmnxSapV8v0Group,
           tmnxSapTlsV8v0Group,
           tmnxSapBaseV6v0Group,
           tmnxSapAtmV6v0Group,
           tmnxSapQosV8v0Group,
           tmnxSapStaticHostV6v1Group,
           tmnxSapPortIdV6v0Group,
           tmnxSapSubMgmtV8v0Group,
           tmnxSapMstiV6v0Group,
           tmnxSapPolicyV6v0Group,
           tmnxSapL2ptV6v0Group,
           tmnxSapMsapV8v0Group,
           tmnxSapMsapV6v1Group,
           tmnxSapHsmdaV6v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapMrpV8v0Group,
           tmnxSapBsxV7v0Group,
           tmnxSapArpHostGroup,
           tmnxSapIgmpTrkGroup,
           tmnxSapIgmpTrkV8v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapGreGroup,
           tmnxSapMvrpV8v0Group,
           tmnxSapNotificationV8v0Group,
           tmnxSapMvrpNotificationV8v0Group,
           tmnxSapEthCfmMonitorGroup
       }
    ::= { tmnxSapCompliances 110 }

tmnxSap7710V8v0Compliance MODULE-COMPLIANCE
    STATUS  obsolete
    DESCRIPTION
        "The compliance statement for management of services SAPs
         on Nokia 7710 SR series systems release 8.0 ."
    MODULE  -- this module
        MANDATORY-GROUPS
        {
           tmnxSapV8v0Group,
           tmnxSapTlsV8v0Group,
           tmnxSapBaseV6v0Group,
           tmnxSapAtmV6v0Group,
           tmnxSapQosV8v0Group,
           tmnxSapStaticHostV6v1Group,
           tmnxSapPortIdV6v0Group,
           tmnxSapSubMgmtV8v0Group,
           tmnxSapMstiV6v0Group,
           tmnxSapPolicyV6v0Group,
           tmnxSapL2ptV6v0Group,
           tmnxSapMsapV8v0Group,
           tmnxSapMsapV6v1Group,
           -- tmnxSapHsmdaV6v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapMrpV8v0Group,
           -- tmnxSapBsxV7v0Group           no Application Assurance on 7710
           tmnxSapArpHostGroup,
           tmnxSapIgmpTrkGroup,
           tmnxSapIgmpTrkV8v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           -- tmnxSapEthRingGroup
           tmnxSapOverrideV8v0Group,
           tmnxSapGreGroup,
           tmnxSapMvrpV8v0Group,
           tmnxSapNotificationV8v0Group,
           tmnxSapMvrpNotificationV8v0Group
           -- tmnxSapEthCfmMonitorGroup
       }
    ::= { tmnxSapCompliances 111 }

tmnxSap7450V9v0Compliance MODULE-COMPLIANCE
    STATUS  obsolete
    DESCRIPTION
        "The compliance statement for management of services SAPs
         on Nokia 7450 ESS series systems release 9.0 ."
    MODULE  -- this module
        MANDATORY-GROUPS
        {
           tmnxSapV8v0Group,
           tmnxSapV9v0Group,
           tmnxSapTlsV8v0Group,
           tmnxSapBaseV6v0Group,
           tmnxSapQosV8v0Group,
           tmnxSapPortIdV6v0Group,
           tmnxSapSubMgmtV9v0Group,
           tmnxSapMstiV6v0Group,
           tmnxSapPolicyV6v0Group,
           tmnxSapL2ptV6v0Group,
           tmnxSapMsapV9v0Group,
           tmnxSapMsapV8v0Group,
           -- tmnxSapMsapV6v1Group,
           tmnxSapHsmdaV6v0Group,
           tmnxSapNotifyGroup,
           -- tmnxSapCemNotificationV6v0Group,
           -- tmnxTlsMsapPppoeV6v0Group,
           -- tmnxSapCemV6v0Group
           -- tmnxSapIpV6FilterV6v0Group
           tmnxSapDhcpV8v0Group,
           tmnxSapMrpV8v0Group,
           tmnxSapBsxV7v0Group,
           tmnxSapBsxV9v0Group,
           tmnxSapArpHostGroup,
           tmnxSapIgmpTrkGroup,
           tmnxSapIgmpTrkV8v0Group,
           -- tmnxSapAtmV7v0Group,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapGreGroup,
           tmnxSapMvrpV8v0Group,
           tmnxSapNotificationV8v0Group,
           tmnxSapMvrpNotificationV8v0Group,
           tmnxSapEthCfmMonitorGroup,
           tmnxSapEthCfmGroup,
           tmnxSapNotificationV9v0Group,
           tmnxSapFilterProfileV9v0Group,
           tmnxSapIpipeNotificationGroup
        }
    ::= { tmnxSapCompliances 112 }

tmnxSap7750V9v0Compliance MODULE-COMPLIANCE
    STATUS  obsolete
    DESCRIPTION
        "The compliance statement for management of services SAPs
         on Nokia SROS series systems release 9.0 ."
    MODULE  -- this module
        MANDATORY-GROUPS
        {
           tmnxSapV8v0Group,
           tmnxSapV9v0Group,
           tmnxSapTlsV8v0Group,
           tmnxSapBaseV6v0Group,
           tmnxSapAtmV6v0Group,
           tmnxSapAtmV9v0Group,
           tmnxSapQosV8v0Group,
           tmnxSapPortIdV6v0Group,
           tmnxSapSubMgmtV9v0Group,
           tmnxSapMstiV6v0Group,
           tmnxSapPolicyV6v0Group,
           tmnxSapL2ptV6v0Group,
           tmnxSapMsapV9v0Group,
           tmnxSapMsapV8v0Group,
           tmnxSapMsapV6v1Group,
           tmnxSapHsmdaV6v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapMrpV8v0Group,
           tmnxSapBsxV7v0Group,
           tmnxSapBsxV9v0Group,
           tmnxSapArpHostGroup,
           tmnxSapIgmpTrkGroup,
           tmnxSapIgmpTrkV8v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapOverrideV9v0Group,
           tmnxSapGreGroup,
           tmnxSapMvrpV8v0Group,
           tmnxSapNotificationV8v0Group,
           tmnxSapMvrpNotificationV8v0Group,
           tmnxSapEthCfmMonitorGroup,
           tmnxSapEthCfmGroup,
           tmnxSapEgrEncapGrpV9v0Group,
           tmnxSapNotificationV9v0Group,
           tmnxSapFilterProfileV9v0Group,
           tmnxSapIpipeNotificationGroup
       }
    ::= { tmnxSapCompliances 113 }

tmnxSap7710V9v0Compliance MODULE-COMPLIANCE
    STATUS  obsolete
    DESCRIPTION
        "The compliance statement for management of services SAPs
         on Nokia 7710 SR series systems release 9.0 ."
    MODULE  -- this module
        MANDATORY-GROUPS
        {
           tmnxSapV8v0Group,
           tmnxSapV9v0Group,
           tmnxSapTlsV8v0Group,
           tmnxSapBaseV6v0Group,
           tmnxSapAtmV6v0Group,
           tmnxSapAtmV9v0Group,
           tmnxSapQosV8v0Group,
           tmnxSapStaticHostV9v0Group,
           tmnxSapPortIdV6v0Group,
           tmnxSapSubMgmtV9v0Group,
           tmnxSapMstiV6v0Group,
           tmnxSapPolicyV6v0Group,
           tmnxSapL2ptV6v0Group,
           tmnxSapMsapV9v0Group,
           tmnxSapMsapV8v0Group,
           tmnxSapMsapV6v1Group,
           -- tmnxSapHsmdaV6v0Group,
           tmnxSapHsmdaV9v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapMrpV8v0Group,
           -- tmnxSapBsxV7v0Group           no Application Assurance on 7710
           -- tmnxSapBsxV9v0Group           no Application Assurance on 7710
           tmnxSapArpHostGroup,
           tmnxSapIgmpTrkGroup,
           tmnxSapIgmpTrkV8v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           tmnxSapPlcrV9v0Group,
           -- tmnxSapEthRingGroup
           tmnxSapOverrideV8v0Group,
           tmnxSapGreGroup,
           tmnxSapMvrpV8v0Group,
           tmnxSapNotificationV8v0Group,
           tmnxSapMvrpNotificationV8v0Group,
           tmnxSapEthCfmGroup,
           -- tmnxSapEthCfmMonitorGroup
           tmnxSapNotificationV9v0Group,
           
           tmnxSapDefHostV9v0Group,
           tmnxSapFilterProfileV9v0Group,
           tmnxSapIpipeNotificationGroup
       }
    ::= { tmnxSapCompliances 114 }

-- 10.0 compliance
tmnxSap7450V10v0Compliance MODULE-COMPLIANCE
    STATUS  obsolete
    DESCRIPTION
        "The compliance statement for management of services SAPs
         on Nokia 7450 ESS series systems release 10.0 ."
    MODULE  -- this module
        MANDATORY-GROUPS
        {
           tmnxSapV8v0Group,
           tmnxSapV9v0Group,
           tmnxSapV10v0Group,
           tmnxSapTlsV8v0Group,
           tmnxSapBaseV6v0Group,
           tmnxSapQosV8v0Group,
           tmnxSapPortIdV6v0Group,
           tmnxSapSubMgmtV9v0Group,
           tmnxSapMstiV6v0Group,
           tmnxSapPolicyV6v0Group,
           tmnxSapL2ptV6v0Group,
           tmnxSapMsapV9v0Group,
           tmnxSapMsapV8v0Group,
           -- tmnxSapMsapV6v1Group,
           tmnxSapHsmdaV6v0Group,
           tmnxSapNotifyGroup,
           -- tmnxSapCemNotificationV6v0Group,
           -- tmnxTlsMsapPppoeV6v0Group,
           -- tmnxSapCemV6v0Group
           -- tmnxSapIpV6FilterV6v0Group
           tmnxSapDhcpV8v0Group,
           tmnxSapMrpV8v0Group,
           tmnxSapBsxV7v0Group,
           tmnxSapBsxV9v0Group,
           tmnxSapArpHostGroup,
           tmnxSapIgmpTrkGroup,
           tmnxSapIgmpTrkV8v0Group,
           -- tmnxSapAtmV7v0Group,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapGreGroup,
           tmnxSapMvrpV8v0Group,
           tmnxSapNotificationV8v0Group,
           tmnxSapMvrpNotificationV8v0Group,
           tmnxSapEthCfmMonitorGroup,
           tmnxSapEthCfmGroup,
           tmnxSapNotificationV9v0Group,
           tmnxSapFilterProfileV9v0Group,
           tmnxSapIpipeNotificationGroup,
           tmnxSapGreV10v0Group,
           tmnxSapSpbGroup,
           tmnxSapIpTnlGroup,
           tmnxSapNotificationV10v0Group,
           tmnxSapStatsV10v0Group,
           tmnxSapMonitorIPGroup,
           tmnxIpTnlOperChgGroup
        }
    ::= { tmnxSapCompliances 115 }

tmnxSap7750V10v0Compliance MODULE-COMPLIANCE
    STATUS  obsolete
    DESCRIPTION
        "The compliance statement for management of services SAPs
         on Nokia SROS series systems release 10.0 ."
    MODULE  -- this module
        MANDATORY-GROUPS
        {
           tmnxSapV8v0Group,
           tmnxSapV9v0Group,
           tmnxSapV10v0Group,
           tmnxSapTlsV8v0Group,
           tmnxSapBaseV6v0Group,
           tmnxSapAtmV6v0Group,
           tmnxSapAtmV9v0Group,
           tmnxSapQosV8v0Group,
           tmnxSapPortIdV6v0Group,
           tmnxSapSubMgmtV9v0Group,
           tmnxSapMstiV6v0Group,
           tmnxSapPolicyV6v0Group,
           tmnxSapL2ptV6v0Group,
           tmnxSapMsapV9v0Group,
           tmnxSapMsapV8v0Group,
           tmnxSapMsapV6v1Group,
           tmnxSapHsmdaV6v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapMrpV8v0Group,
           tmnxSapBsxV7v0Group,
           tmnxSapBsxV9v0Group,
           tmnxSapBsxV10v0Group,
           tmnxSapArpHostGroup,
           tmnxSapIgmpTrkGroup,
           tmnxSapIgmpTrkV8v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapOverrideV9v0Group,
           tmnxSapGreGroup,
           tmnxSapMvrpV8v0Group,
           tmnxSapNotificationV8v0Group,
           tmnxSapMvrpNotificationV8v0Group,
           tmnxSapEthCfmMonitorGroup,
           tmnxSapEthCfmGroup,
           tmnxSapEgrEncapGrpV9v0Group,
           tmnxSapNotificationV9v0Group,
           tmnxSapFilterProfileV9v0Group,
           tmnxSapIpipeNotificationGroup,
           tmnxSapGreV10v0Group,
           tmnxSapSpbGroup,
           tmnxSapIpTnlGroup,
           tmnxSapNotificationV10v0Group,
           tmnxSapStatsV10v0Group,
           tmnxSapMonitorIPGroup,
           tmnxIpTnlOperChgGroup
       }
    ::= { tmnxSapCompliances 116 }

tmnxSap7710V10v0Compliance MODULE-COMPLIANCE
    STATUS  obsolete
    DESCRIPTION
        "The compliance statement for management of services SAPs
         on Nokia 7710 SR series systems release 10.0 ."
    MODULE  -- this module
        MANDATORY-GROUPS
        {
           tmnxSapV8v0Group,
           tmnxSapV9v0Group,
           tmnxSapV10v0Group,
           tmnxSapTlsV8v0Group,
           tmnxSapBaseV6v0Group,
           tmnxSapAtmV6v0Group,
           tmnxSapAtmV9v0Group,
           tmnxSapQosV8v0Group,
           tmnxSapStaticHostV9v0Group,
           tmnxSapPortIdV6v0Group,
           tmnxSapSubMgmtV9v0Group,
           tmnxSapMstiV6v0Group,
           tmnxSapPolicyV6v0Group,
           tmnxSapL2ptV6v0Group,
           tmnxSapMsapV9v0Group,
           tmnxSapMsapV8v0Group,
           tmnxSapMsapV6v1Group,
           -- tmnxSapHsmdaV6v0Group,
           tmnxSapHsmdaV9v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapMrpV8v0Group,
           -- tmnxSapBsxV7v0Group           no Application Assurance on 7710
           -- tmnxSapBsxV9v0Group           no Application Assurance on 7710
           -- tmnxSapBsxV10v0Group          no Application Assurance on 7710
           tmnxSapArpHostGroup,
           tmnxSapIgmpTrkGroup,
           tmnxSapIgmpTrkV8v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           tmnxSapPlcrV9v0Group,
           -- tmnxSapEthRingGroup
           tmnxSapOverrideV8v0Group,
           tmnxSapGreGroup,
           tmnxSapMvrpV8v0Group,
           tmnxSapNotificationV8v0Group,
           tmnxSapMvrpNotificationV8v0Group,
           tmnxSapEthCfmGroup,
           -- tmnxSapEthCfmMonitorGroup
           tmnxSapNotificationV9v0Group,
           tmnxSapDefHostV9v0Group,
           tmnxSapFilterProfileV9v0Group,
           tmnxSapIpipeNotificationGroup,
           tmnxSapSpbGroup,
           tmnxSapGreV10v0Group,
           tmnxSapNotificationV10v0Group,
           tmnxSapStatsV10v0Group,
           tmnxSapIpTnlGroup,
           -- tmnxSapMonitorIPGroup
           tmnxIpTnlOperChgGroup
       }
    ::= { tmnxSapCompliances 117 }

-- Release 11.0 Compliance
tmnxSap7450V11v0Compliance MODULE-COMPLIANCE
    STATUS  obsolete
    DESCRIPTION
        "The compliance statement for management of services SAPs
         on Nokia 7450 ESS series systems release 11.0."
    MODULE  -- this module
        MANDATORY-GROUPS
        {
           tmnxSapV8v0Group,
           tmnxSapV9v0Group,
           -- tmnxSapV10v0Group,
           tmnxSapTlsV8v0Group,
           tmnxSapBaseV6v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           -- tmnxSapMsapV6v1Group,
           tmnxSapHsmdaV10v0Group,
           tmnxSapNotifyGroup,
           -- tmnxSapCemNotificationV6v0Group,
           -- tmnxTlsMsapPppoeV6v0Group,
           -- tmnxSapCemV6v0Group
           -- tmnxSapIpV6FilterV6v0Group
           tmnxSapDhcpV8v0Group,
           tmnxSapDhcpV11v0Group,
           tmnxSapMrpV8v0Group,
           tmnxSapBsxV7v0Group,
           tmnxSapBsxV9v0Group,
           tmnxSapArpHostGroup,
           tmnxSapIgmpTrkGroup,
           tmnxSapIgmpTrkV8v0Group,
           tmnxSapIgmpTrkV11v0Group,
           -- tmnxSapAtmV7v0Group,
           tmnxSapStaticHostV9v0Group,
           tmnxSapStaticHostV11v0Group,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapGreObsoletedGroup,
           tmnxSapGreV11v0Group,
           tmnxSapMvrpV10v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapSpbV11v0Group,
           tmnxSapSchedulerRateV11v0Group,
           tmnxSapEthLoopbackV11v0Group,
           tmnxSapEthLpbkNotifyV11v0Group,
           sapTlsFdbMacStatsGroup,
           tmnxSapQosV11v0Group,
           tmnxIpTnlOperChgGroup
        }
    ::= { tmnxSapCompliances 118 }

tmnxSap7750V11v0Compliance MODULE-COMPLIANCE
    STATUS  obsolete
    DESCRIPTION
        "The compliance statement for management of services SAPs
         on Nokia SROS series systems release 11.0."
    MODULE  -- this module
        MANDATORY-GROUPS
        {
           tmnxSapV8v0Group,
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           tmnxSapHsmdaV10v0Group,  
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           tmnxSapBsxV7v0Group,
           tmnxSapBsxV9v0Group,
           tmnxSapBsxV10v0Group,
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           tmnxSapEthRingGroup,
           tmnxSapOverrideV8v0Group,
           tmnxSapOverrideV9v0Group,
           tmnxSapGreObsoletedGroup,
           tmnxSapGreV11v0Group,
           tmnxSapMvrpV10v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapEgrEncapGrpV9v0Group,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapDCpuProtV11v0Group,
           tmnxSapDcpNotifyObjsV11v0Group,
           tmnxSapDcpNotifyV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           tmnxSapQosV11v0Group,
           tmnxIpTnlOperChgGroup
       }
    ::= { tmnxSapCompliances 119 }

tmnxSap7710V11v0Compliance MODULE-COMPLIANCE
    STATUS  obsolete
    DESCRIPTION
        "The compliance statement for management of services SAPs
         on Nokia 7710 SR series systems release 11.0."
    MODULE  -- this module
        MANDATORY-GROUPS
        {
           tmnxSapV8v0Group,
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           -- tmnxSapHsmdaV6v0Group,
           tmnxSapHsmdaV9v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           -- tmnxSapBsxV7v0Group           no Application Assurance on 7710
           -- tmnxSapBsxV9v0Group           no Application Assurance on 7710
           -- tmnxSapBsxV10v0Group          no Application Assurance on 7710
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapTlsV7v0Group,
           tmnxSapFPropBMacV8v0Group,
           tmnxSapPlcrV8v0Group,
           tmnxSapPlcrV9v0Group,
           -- tmnxSapEthRingGroup
           tmnxSapOverrideV8v0Group,
           tmnxSapGreObsoletedGroup,
           tmnxSapGreV11v0Group,
           tmnxSapMvrpV10v0Group,
           tmnxSapNotificationV11v0Group,
           tmnxSapNotifObsoletedGroup,
           tmnxSapMvrpNotificationV8v0Group,
           tmnxSapEthCfmGroup,
           tmnxSapCflowdGroupV11v0,
           -- tmnxSapEthCfmMonitorGroup
           tmnxSapNotificationV9v0Group,
           tmnxSapDefHostV9v0Group,
           tmnxSapFilterProfileV9v0Group,
           tmnxSapIpipeNotificationGroup,
           tmnxSapSpbGroup,
           tmnxSapNotificationV10v0Group,
           tmnxSapIpTnlGroup,
           -- tmnxSapGreV10v0Group,
           tmnxSapLagV11v0Group,
           tmnxSapV11v0Group,
           -- tmnxSapMonitorIPGroup
           tmnxSapStatsV10v0Group,
           tmnxSapFlowSPecV11v0Group,
           tmnxSapDCpuProtV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           tmnxSapQosV11v0Group,
           tmnxIpTnlOperChgGroup
       }
    ::= { tmnxSapCompliances 120 }

-- Release 12.0 Compliance
tmnxSap7450V12v0Compliance MODULE-COMPLIANCE
    STATUS  obsolete
    DESCRIPTION
        "The compliance statement for management of services SAPs
         on Nokia 7450 ESS series systems release 12.0."
    MODULE  -- this module
        MANDATORY-GROUPS
        {
           tmnxSapV8v0Group,
           tmnxSapV9v0Group,
           -- tmnxSapV10v0Group,
           tmnxSapTlsV8v0Group,
           tmnxSapBaseV6v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           -- tmnxSapMsapV6v1Group,
           tmnxSapHsmdaV10v0Group,
           tmnxSapNotifyGroup,
           -- tmnxSapCemNotificationV6v0Group,
           -- tmnxTlsMsapPppoeV6v0Group,
           -- tmnxSapCemV6v0Group
           -- tmnxSapIpV6FilterV6v0Group
           tmnxSapDhcpV8v0Group,
           tmnxSapDhcpV11v0Group,
           tmnxSapMrpV8v0Group,
           tmnxSapBsxV7v0Group,
           tmnxSapBsxV9v0Group,
           tmnxSapArpHostGroup,
           tmnxSapIgmpTrkGroup,
           tmnxSapIgmpTrkV8v0Group,
           tmnxSapIgmpTrkV11v0Group,
           -- tmnxSapAtmV7v0Group,
           tmnxSapStaticHostV9v0Group,
           tmnxSapStaticHostV11v0Group,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapEthRingGroup,
           tmnxSapOverrideV8v0Group,
           tmnxSapGreObsoletedGroup,
           tmnxSapGreV11v0Group,
           tmnxSapMvrpV10v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapQosV11v0Group,
           tmnxSapTlsV12v0Group,
           tmnxMsapPlcyCpmProtV12v0Group,
           tmnxSapQosV12v0Group,
           tmnxSapEthCfmV12v0Group,
           tmnxIpTunnelV12v0Group,
           sapLagV12v0Group,
           tmnxIpTnlOperChgGroup,
           tmnxMsapQosV12v0Group
        }
    ::= { tmnxSapCompliances 121 }

tmnxSap7750V12v0Compliance MODULE-COMPLIANCE
    STATUS  obsolete
    DESCRIPTION
        "The compliance statement for management of services SAPs
         on Nokia SROS series systems release 12.0."
    MODULE  -- this module
        MANDATORY-GROUPS
        {
           tmnxSapV8v0Group,
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           tmnxSapHsmdaV10v0Group,  
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           tmnxSapBsxV7v0Group,
           tmnxSapBsxV9v0Group,
           tmnxSapBsxV10v0Group,
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapEthRingGroup,
           tmnxSapOverrideV8v0Group,
           tmnxSapOverrideV9v0Group,
           tmnxSapGreObsoletedGroup,
           tmnxSapGreV11v0Group,
           tmnxSapMvrpV10v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapEgrEncapGrpV9v0Group,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapDCpuProtV11v0Group,
           tmnxSapDcpNotifyObjsV11v0Group,
           tmnxSapDcpNotifyV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapQosV11v0Group,
           tmnxSapTlsV12v0Group,
           tmnxMsapPlcyCpmProtV12v0Group,
           tmnxSapQosV12v0Group,               
           tmnxIpTunnelV12v0Group,
           sapLagV12v0Group,
           tmnxIPTunnelGreKeyV12v0Group,
           tmnxIpTunnelFragStatV12v0Group,
           tmnxIpTunnelEncapNotifyGroup,
           tmnxIpTunnelEncaNotifyObjsGroup,
           tmnxIpTnlOperChgGroup,
           tmnxMsapQosV12v0Group
       }
    ::= { tmnxSapCompliances 122 }

tmnxSap7710V12v0Compliance MODULE-COMPLIANCE
    STATUS  obsolete
    DESCRIPTION
        "The compliance statement for management of services SAPs
         on Nokia 7710 SR series systems release 12.0."
    MODULE  -- this module
        MANDATORY-GROUPS
        {
           tmnxSapV8v0Group,
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           -- tmnxSapHsmdaV6v0Group,
           tmnxSapHsmdaV9v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           -- tmnxSapBsxV7v0Group           no Application Assurance on 7710
           -- tmnxSapBsxV9v0Group           no Application Assurance on 7710
           -- tmnxSapBsxV10v0Group          no Application Assurance on 7710
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapPlcrV9v0Group,
           -- tmnxSapEthRingGroup
           tmnxSapOverrideV8v0Group,
           tmnxSapGreObsoletedGroup,
           tmnxSapGreV11v0Group,
           tmnxSapMvrpV10v0Group,
           tmnxSapNotificationV11v0Group,
           tmnxSapNotifObsoletedGroup,
           tmnxSapMvrpNotificationV8v0Group,
           tmnxSapEthCfmGroup,
           tmnxSapCflowdGroupV11v0,
           -- tmnxSapEthCfmMonitorGroup
           tmnxSapNotificationV9v0Group,
           tmnxSapDefHostV9v0Group,
           tmnxSapFilterProfileV9v0Group,
           tmnxSapIpipeNotificationGroup,
           tmnxSapSpbGroup,
           tmnxSapNotificationV10v0Group,
           tmnxSapIpTnlGroup,
           -- tmnxSapGreV10v0Group,
           tmnxSapLagV11v0Group,
           tmnxSapV11v0Group,
           -- tmnxSapMonitorIPGroup
           tmnxSapStatsV10v0Group,
           tmnxSapFlowSPecV11v0Group,
           tmnxSapDCpuProtV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapTlsV12v0Group,
           tmnxSapQosV11v0Group,
           tmnxSapQosV12v0Group,               
           tmnxIpTunnelV12v0Group,
           sapLagV12v0Group,
           tmnxIpTnlOperChgGroup,
           tmnxMsapQosV12v0Group,
           tmnxSapMsapV12v0Group
       }
    ::= { tmnxSapCompliances 123 }

-- Release 13.0 Compliance
tmnxSap7450V13v0Compliance MODULE-COMPLIANCE
    STATUS  obsolete
    DESCRIPTION
        "The compliance statement for management of services SAPs
         on Nokia 7450 ESS series systems release 13.0."
    MODULE  -- this module
        MANDATORY-GROUPS
        {
           tmnxSapV9v0Group,
           -- tmnxSapV10v0Group,
           tmnxSapTlsV8v0Group,
           tmnxSapBaseV6v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           -- tmnxSapMsapV6v1Group,
           tmnxSapHsmdaV10v0Group,
           tmnxSapNotifyGroup,
           -- tmnxSapCemNotificationV6v0Group,
           -- tmnxTlsMsapPppoeV6v0Group,
           -- tmnxSapCemV6v0Group
           -- tmnxSapIpV6FilterV6v0Group
           tmnxSapDhcpV8v0Group,
           tmnxSapDhcpV11v0Group,
           tmnxSapMrpV8v0Group,
           tmnxSapBsxV7v0Group,
           tmnxSapBsxV9v0Group,
           tmnxSapArpHostGroup,
           tmnxSapIgmpTrkGroup,
           tmnxSapIgmpTrkV8v0Group,
           tmnxSapIgmpTrkV11v0Group,
           -- tmnxSapAtmV7v0Group,
           tmnxSapStaticHostV9v0Group,
           tmnxSapStaticHostV11v0Group,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapEthRingGroup,
           tmnxSapOverrideV8v0Group,
           tmnxSapGreObsoletedGroup,
           tmnxSapGreV11v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapQosV11v0Group,
           tmnxSapTlsV12v0Group,
           tmnxMsapPlcyCpmProtV12v0Group,
           tmnxSapQosV12v0Group,
           tmnxSapEthCfmV12v0Group,
           tmnxIpTunnelV12v0Group,
           sapLagV12v0Group,
           tmnxIpTnlOperChgGroup,
           tmnxMsapQosV12v0Group,
           tmnxSapIpoeV13v0Group,
           tmnxSapQosSchedV13v0Group,
           tmnxSapStaticHostRipV13v0Group,
           tmnxSapBaseStatsV13v0Group,
           tmnxSapQueueOvrV13v0Group,
           tmnxSapRipNotifyGroup,
           tmnxSapQosRateV13v0Group,
           tmnxSapNotificationV13v0Group,
           tmnxSapDhcpV13v0Group,
           tmnxSapV13v0Group,
           tmnxSapMvrpV13v0Group,
           tmnxSapEgrEncapGrpV13v0Group,
           sapBgpEvpnMplsMhGroup
        }
    ::= { tmnxSapCompliances 124 }

tmnxSap7750V13v0Compliance MODULE-COMPLIANCE
    STATUS  obsolete
    DESCRIPTION
        "The compliance statement for management of services SAPs
         on Nokia SROS series systems release 13.0."
    MODULE  -- this module
        MANDATORY-GROUPS
        {
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           tmnxSapHsmdaV10v0Group,  
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           tmnxSapBsxV7v0Group,
           tmnxSapBsxV9v0Group,
           tmnxSapBsxV10v0Group,
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapEthRingGroup,
           tmnxSapOverrideV8v0Group,
           tmnxSapOverrideV9v0Group,
           tmnxSapGreObsoletedGroup,
           tmnxSapGreV11v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapDCpuProtV11v0Group,
           tmnxSapDcpNotifyObjsV11v0Group,
           tmnxSapDcpNotifyV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapQosV11v0Group,
           tmnxSapTlsV12v0Group,
           tmnxMsapPlcyCpmProtV12v0Group,
           tmnxSapQosV12v0Group,               
           tmnxIpTunnelV12v0Group,
           sapLagV12v0Group,
           tmnxIPTunnelGreKeyV12v0Group,
           tmnxIpTunnelFragStatV12v0Group,
           tmnxIpTunnelEncapNotifyGroup,
           tmnxIpTunnelEncaNotifyObjsGroup,
           tmnxIpTnlOperChgGroup,
           tmnxMsapQosV12v0Group,
           tmnxSapIpoeV13v0Group,
           tmnxSapQosSchedV13v0Group,
           tmnxSapStaticHostRipV13v0Group,
           tmnxSapBaseStatsV13v0Group,
           tmnxSapQueueOvrV13v0Group,
           tmnxSapRipNotifyGroup,
           tmnxSapQosRateV13v0Group,
           tmnxSapNotificationV13v0Group,
           tmnxSapDhcpV13v0Group,
           tmnxSapV13v0Group,
           tmnxSapMvrpV13v0Group,
           tmnxSapEgrEncapGrpV13v0Group,
           sapBgpEvpnMplsMhGroup
       }
    ::= { tmnxSapCompliances 125 }

tmnxSap7710V13v0Compliance MODULE-COMPLIANCE
    STATUS  obsolete
    DESCRIPTION
        "The compliance statement for management of services SAPs
         on Nokia 7710 SR series systems release 13.0."
    MODULE  -- this module
        MANDATORY-GROUPS
        {
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           -- tmnxSapHsmdaV6v0Group,
           tmnxSapHsmdaV9v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           -- tmnxSapBsxV7v0Group           no Application Assurance on 7710
           -- tmnxSapBsxV9v0Group           no Application Assurance on 7710
           -- tmnxSapBsxV10v0Group          no Application Assurance on 7710
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapPlcrV9v0Group,
           -- tmnxSapEthRingGroup
           tmnxSapOverrideV8v0Group,
           tmnxSapGreObsoletedGroup,
           tmnxSapGreV11v0Group,
           tmnxSapNotificationV11v0Group,
           tmnxSapNotifObsoletedGroup,
           tmnxSapMvrpNotificationV8v0Group,
           tmnxSapEthCfmGroup,
           tmnxSapCflowdGroupV11v0,
           -- tmnxSapEthCfmMonitorGroup
           tmnxSapNotificationV9v0Group,
           tmnxSapDefHostV9v0Group,
           tmnxSapFilterProfileV9v0Group,
           tmnxSapIpipeNotificationGroup,
           tmnxSapSpbGroup,
           tmnxSapNotificationV10v0Group,
           tmnxSapIpTnlGroup,
           -- tmnxSapGreV10v0Group,
           tmnxSapLagV11v0Group,
           tmnxSapV11v0Group,
           -- tmnxSapMonitorIPGroup
           tmnxSapStatsV10v0Group,
           tmnxSapFlowSPecV11v0Group,
           tmnxSapDCpuProtV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapTlsV12v0Group,
           tmnxSapQosV11v0Group,
           tmnxSapQosV12v0Group,               
           tmnxIpTunnelV12v0Group,
           sapLagV12v0Group,
           tmnxIpTnlOperChgGroup,
           tmnxMsapQosV12v0Group,
           tmnxSapMsapV12v0Group,
           tmnxSapStatHost6Group,
           tmnxSapStatHost6V13v0Group,
           tmnxSapIpoeV13v0Group,
           tmnxSapDnGroup,
           tmnxSapQosSchedV13v0Group,
           tmnxSapIpipeFaultPropGroup,
           tmnxSapStaticHostRipV13v0Group,
           tmnxSapBaseStatsV13v0Group,
           tmnxSapQueueOvrV13v0Group,
           tmnxSapDiamNasreqGroup,
           tmnxSapRipNotifyGroup,
           tmnxSapQosRateV13v0Group,
           tmnxSapNotificationV13v0Group,
           tmnxSapDhcpV13v0Group,
           tmnxSapShcvPolicyGroup,
           tmnxSapV13v0Group,
           tmnxSapMvrpV13v0Group,
           tmnxSapEgrEncapGrpV13v0Group,
           sapBgpEvpnMplsMhGroup
       }
    ::= { tmnxSapCompliances 126 }

-- Release 14.0 Compliance
tmnxSap7450V14v0Compliance MODULE-COMPLIANCE
    STATUS  current
    DESCRIPTION
        "The compliance statement for management of services SAPs
         on Nokia 7450 ESS series systems release 14.0."
    MODULE  -- this module
        MANDATORY-GROUPS
        {
           tmnxSapV9v0Group,
           -- tmnxSapV10v0Group,
           tmnxSapTlsV8v0Group,
           tmnxSapBaseV6v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           -- tmnxSapMsapV6v1Group,
           tmnxSapHsmdaV10v0Group,
           tmnxSapNotifyGroup,
           -- tmnxSapCemNotificationV6v0Group,
           -- tmnxTlsMsapPppoeV6v0Group,
           -- tmnxSapCemV6v0Group
           -- tmnxSapIpV6FilterV6v0Group
           tmnxSapDhcpV8v0Group,
           tmnxSapDhcpV11v0Group,
           tmnxSapMrpV8v0Group,
           tmnxSapBsxV7v0Group,
           tmnxSapBsxV9v0Group,
           tmnxSapArpHostGroup,
           tmnxSapIgmpTrkGroup,
           tmnxSapIgmpTrkV8v0Group,
           tmnxSapIgmpTrkV11v0Group,
           -- tmnxSapAtmV7v0Group,
           tmnxSapStaticHostV9v0Group,
           tmnxSapStaticHostV11v0Group,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapEthRingGroup,
           tmnxSapOverrideV8v0Group,
           tmnxSapGreObsoletedGroup,
           tmnxSapGreV11v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapQosV11v0Group,
           tmnxSapTlsV12v0Group,
           tmnxMsapPlcyCpmProtV12v0Group,
           tmnxSapQosV12v0Group,
           tmnxSapEthCfmV12v0Group,
           tmnxIpTunnelV12v0Group,
           sapLagV12v0Group,
           tmnxIpTnlOperChgGroup,
           tmnxMsapQosV12v0Group,
           tmnxSapIpoeV13v0Group,
           tmnxSapQosSchedV13v0Group,
           tmnxSapStaticHostRipV13v0Group,
           tmnxSapBaseStatsV13v0Group,
           tmnxSapQueueOvrV13v0Group,
           tmnxSapRipNotifyGroup,
           tmnxSapQosRateV13v0Group,
           tmnxSapNotificationV13v0Group,
           tmnxSapDhcpV13v0Group,
           tmnxSapV13v0Group,
           tmnxSapMvrpV13v0Group,
           tmnxSapEgrEncapGrpV13v0Group,
           sapBgpEvpnMplsMhGroup
        }
    ::= { tmnxSapCompliances 127 }

tmnxSap7750V14v0Compliance MODULE-COMPLIANCE
    STATUS  current
    DESCRIPTION
        "The compliance statement for management of services SAPs
         on Nokia SROS series systems release 14.0."
    MODULE  -- this module
        MANDATORY-GROUPS
        {
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           tmnxSapHsmdaV10v0Group,  
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           tmnxSapBsxV7v0Group,
           tmnxSapBsxV9v0Group,
           tmnxSapBsxV10v0Group,
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapEthRingGroup,
           tmnxSapOverrideV8v0Group,
           tmnxSapOverrideV9v0Group,
           tmnxSapGreObsoletedGroup,
           tmnxSapGreV11v0Group,
           tmnxSapNotificationV11v0Group,
           tmnxSapNotifObsoletedGroup,
           tmnxSapMvrpNotificationV8v0Group,
           tmnxSapEthCfmMonitorGroup,
           tmnxSapEthCfmGroup,
           tmnxSapCflowdGroupV11v0,
           tmnxSapNotificationV9v0Group,
           tmnxSapFilterProfileV9v0Group,
           tmnxSapIpipeNotificationGroup,
           tmnxSapSpbGroup,
           tmnxSapNotificationV10v0Group,
           tmnxSapIpTnlGroup,
           tmnxSapV11v0Group,
           -- tmnxSapGreV10v0Group,
           tmnxSapLagV11v0Group,
           tmnxSapMonitorIPGroup,
           tmnxSapStatsV10v0Group,
           tmnxSapFlowSPecV11v0Group,
           tmnxSapDCpuProtV11v0Group,
           tmnxSapDcpNotifyObjsV11v0Group,
           tmnxSapDcpNotifyV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapQosV11v0Group,
           tmnxSapTlsV12v0Group,
           tmnxMsapPlcyCpmProtV12v0Group,
           tmnxSapQosV12v0Group,               
           tmnxIpTunnelV12v0Group,
           sapLagV12v0Group,
           tmnxIPTunnelGreKeyV12v0Group,
           tmnxIpTunnelFragStatV12v0Group,
           tmnxIpTunnelEncapNotifyGroup,
           tmnxIpTunnelEncaNotifyObjsGroup,
           tmnxIpTnlOperChgGroup,
           tmnxMsapQosV12v0Group,
           tmnxSapIpoeV13v0Group,
           tmnxSapQosSchedV13v0Group,
           tmnxSapStaticHostRipV13v0Group,
           tmnxSapBaseStatsV13v0Group,
           tmnxSapQueueOvrV13v0Group,
           tmnxSapRipNotifyGroup,
           tmnxSapQosRateV13v0Group,
           tmnxSapNotificationV13v0Group,
           tmnxSapDhcpV13v0Group,
           tmnxSapV13v0Group,
           tmnxSapMvrpV13v0Group,
           tmnxSapEgrEncapGrpV13v0Group,
           sapBgpEvpnMplsMhGroup
       }
    ::= { tmnxSapCompliances 128 }

tmnxSap7710V14v0Compliance MODULE-COMPLIANCE
    STATUS  current
    DESCRIPTION
        "The compliance statement for management of services SAPs
         on Nokia 7710 SR series systems release 14.0."
    MODULE  -- this module
        MANDATORY-GROUPS
        {
           tmnxSapV9v0Group,
           -- tmnxSapV10v0Group,
           tmnxSapTlsV8v0Group,
           tmnxSapBaseV6v0Group,
           tmnxSapAtmV6v0Group,
           tmnxSapAtmV9v0Group,
           tmnxSapStaticHostV9v0Group,
           tmnxSapStaticHostV11v0Group,
           tmnxSapPortIdV6v0Group,
           tmnxSapSubMgmtV9v0Group,
           tmnxSapMstiV6v0Group,
           tmnxSapPolicyV6v0Group,
           tmnxSapL2ptV6v0Group,
           tmnxSapMsapV11v0Group,
           tmnxSapMsapV9v0Group,
           tmnxSapMsapV8v0Group,
           tmnxSapMsapV6v1Group,
           -- tmnxSapHsmdaV6v0Group,
           tmnxSapHsmdaV9v0Group,
           tmnxSapNotifyGroup,
           tmnxSapCemNotificationV6v0Group,
           tmnxTlsMsapPppoeV6v0Group,
           tmnxSapCemV6v0Group,
           tmnxSapIpV6FilterV6v0Group,
           tmnxSapDhcpV8v0Group,
           tmnxSapDhcpV11v0Group,
           tmnxSapMrpV8v0Group,
           -- tmnxSapBsxV7v0Group           no Application Assurance on 7710
           -- tmnxSapBsxV9v0Group           no Application Assurance on 7710
           -- tmnxSapBsxV10v0Group          no Application Assurance on 7710
           tmnxSapArpHostGroup,
           tmnxSapIgmpTrkGroup,
           tmnxSapIgmpTrkV8v0Group,
           tmnxSapIgmpTrkV11v0Group,
           tmnxSapFrGroupV8v0,
           tmnxSapIpipeV8v0Group,
           tmnxSapRadiusFallbackGroup,
           tmnxSapPbbGroup,
           tmnxSapPbbV12v0Group,
           tmnxSapTlsV7v0Group,
           tmnxSapFPropBMacV8v0Group,
           tmnxSapPlcrV8v0Group,
           tmnxSapPlcrV9v0Group,
           -- tmnxSapEthRingGroup
           tmnxSapOverrideV8v0Group,
           tmnxSapGreObsoletedGroup,
           tmnxSapGreV11v0Group,
           tmnxSapNotificationV11v0Group,
           tmnxSapNotifObsoletedGroup,
           tmnxSapMvrpNotificationV8v0Group,
           tmnxSapEthCfmGroup,
           tmnxSapCflowdGroupV11v0,
           -- tmnxSapEthCfmMonitorGroup
           tmnxSapNotificationV9v0Group,
           tmnxSapDefHostV9v0Group,
           tmnxSapDefHostV14v0Group,
           tmnxSapFilterProfileV9v0Group,
           tmnxSapIpipeNotificationGroup,
           tmnxSapSpbGroup,
           tmnxSapNotificationV10v0Group,
           tmnxSapIpTnlGroup,
           -- tmnxSapGreV10v0Group,
           tmnxSapLagV11v0Group,
           tmnxSapV11v0Group,
           -- tmnxSapMonitorIPGroup
           tmnxSapStatsV10v0Group,
           tmnxSapFlowSPecV11v0Group,
           tmnxSapDCpuProtV11v0Group,
           tmnxSapEgrPortQGrpV11v0Group,
           tmnxSapSpbV11v0Group,
           tmnxSapSchedulerRateV11v0Group,
           tmnxSapEthLoopbackV11v0Group,
           tmnxSapEthLpbkNotifyV11v0Group,
           sapTlsFdbMacStatsGroup,
           sapTlsEtreeGroup,
           tmnxSapTlsV12v0Group,
           tmnxSapQosV11v0Group,
           tmnxSapQosV12v0Group,               
           tmnxIpTunnelV12v0Group,
           sapLagV12v0Group,
           tmnxIpTnlOperChgGroup,
           tmnxMsapQosV12v0Group,
           tmnxSapMsapV12v0Group,
           tmnxSapStatHost6Group,
           tmnxSapStatHost6V13v0Group,
           tmnxSapIpoeV13v0Group,
           tmnxSapDnGroup,
           tmnxSapQosSchedV13v0Group,
           tmnxSapIpipeFaultPropGroup,
           tmnxSapStaticHostRipV13v0Group,
           tmnxSapBaseStatsV13v0Group,
           tmnxSapQueueOvrV13v0Group,
           tmnxSapDiamNasreqGroup,
           tmnxSapRipNotifyGroup,
           tmnxSapQosRateV13v0Group,
           tmnxSapNotificationV13v0Group,
           tmnxSapDhcpV13v0Group,
           tmnxSapShcvPolicyGroup,
           tmnxSapV13v0Group,
           tmnxSapMvrpV13v0Group,
           tmnxSapEgrEncapGrpV13v0Group,
           sapBgpEvpnMplsMhGroup
       }
    ::= { tmnxSapCompliances 129 }

-- ----------------------
-- SAP Group
-- ----------------------

tmnxSapV6v0Group OBJECT-GROUP
    OBJECTS {
      sapNumEntries,
      sapPortId,
      sapEncapValue,
      sapRowStatus,
      sapType,
      sapDescription,
      sapAdminStatus,
      sapOperStatus,
      sapIngressQosPolicyId,
      sapIngressMacFilterId,
      sapIngressIpFilterId,
      sapIngressVlanTranslationId,
      sapEgressQosPolicyId,
      sapEgressMacFilterId,
      sapEgressIpFilterId,
      sapMirrorStatus,
      sapIesIfIndex,
      sapLastMgmtChange,
      sapCollectAcctStats,
      sapAccountingPolicyId,
      sapVpnId,
      sapCustId,
      sapCustMultSvcSite,
      sapIngressQosSchedulerPolicy,
      sapEgressQosSchedulerPolicy,
      sapSplitHorizonGrp,
      sapIngressSharedQueuePolicy,
      sapIngressMatchQinQDot1PBits,
      sapOperFlags,
      sapLastStatusChange,
      sapAntiSpoofing,
      sapTodSuite,
      sapIngUseMultipointShared,
      sapEgressQinQMarkTopOnly,
      sapEgressAggRateLimit,
      sapEndPoint,
      sapIngressVlanTranslation,
      sapSubType,
      sapCpmProtPolicyId,
      sapCpmProtMonitorMac,
      sapEgressFrameBasedAccounting,
      sapEthernetLLFAdminStatus,
      sapEthernetLLFOperStatus,
      sapTlsMvplsRowStatus,
      sapAntiSpoofIpAddress,
      sapAntiSpoofMacAddress,
      sapEgressFrameBasedAccounting
    }
    STATUS      obsolete
    DESCRIPTION
        "The group of objects supporting management of SAP
         general capabilities on Nokia SROS series systems."
    ::= { tmnxSapGroups 100 }


tmnxSapTlsV6v0Group OBJECT-GROUP
    OBJECTS {
      sapTlsStpAdminStatus,
      sapTlsStpPriority,
      sapTlsStpPortNum,
      sapTlsStpPathCost,
      sapTlsStpRapidStart,
      sapTlsStpBpduEncap,
      sapTlsStpPortState,
      sapTlsStpDesignatedBridge,
      sapTlsStpDesignatedPort,
      sapTlsStpForwardTransitions,
      sapTlsStpInConfigBpdus,
      sapTlsStpInTcnBpdus,
      sapTlsStpInBadBpdus,
      sapTlsStpOutConfigBpdus,
      sapTlsStpOutTcnBpdus,
      sapTlsStpOperBpduEncap,
      sapTlsVpnId,
      sapTlsCustId,
      sapTlsMacAddressLimit,
      sapTlsNumMacAddresses,
      sapTlsNumStaticMacAddresses,
      sapTlsMacLearning,
      sapTlsMacAgeing,
      sapTlsStpOperEdge,
      sapTlsStpAdminPointToPoint,
      sapTlsStpPortRole,
      sapTlsStpAutoEdge,
      sapTlsStpOperProtocol,
      sapTlsStpInRstBpdus,
      sapTlsStpOutRstBpdus,
      sapTlsLimitMacMove,
      sapTlsMacPinning,
      sapTlsDiscardUnknownSource,
      sapTlsMvplsPruneState,
      sapTlsMvplsMgmtService,
      sapTlsMvplsMgmtPortId,
      sapTlsMvplsMgmtEncapValue,
      sapTlsArpReplyAgent,
      sapTlsStpException,
      sapTlsAuthenticationPolicy,
      sapTlsL2ptTermination,
      sapTlsBpduTranslation,
      sapTlsStpRootGuard,
      sapTlsStpInsideRegion,
      sapTlsEgressMcastGroup,
      sapTlsStpInMstBpdus,
      sapTlsStpOutMstBpdus,
      sapTlsRestProtSrcMac,
      sapTlsRestProtSrcMacAction,
      sapTlsRestUnprotDstMac,
      sapTlsStpRxdDesigBridge,
      sapTlsStpRootGuardViolation,
      sapTlsShcvAction,
      sapTlsShcvSrcIp,
      sapTlsShcvSrcMac,
      sapTlsShcvInterval,
      sapTlsMvplsMgmtMsti,
      sapTlsMacMoveNextUpTime,
      sapTlsMacMoveRateExcdLeft,
      sapTlsL2ptForceBoundary,
      sapTlsLimitMacMoveLevel,
      sapTlsBpduTransOper,
      sapTlsDefMsapPolicy,
      sapTlsL2ptProtocols,
      sapTlsL2ptForceProtocols,
      sapTlsDhcpMsapTrigger,
      sapTlsDhcpProxyLeaseTime,
      sapTlsDhcpRemoteId,
      sapTlsMrpJoinTime,
      sapTlsMrpLeaveTime,
      sapTlsMrpLeaveAllTime,
      sapTlsMrpPeriodicTime,
      sapTlsMrpPeriodicEnabled
      }
    STATUS      obsolete
    DESCRIPTION
        "The group of objects supporting management of SAP
         TLS capabilities on Nokia SROS series systems."
    ::= { tmnxSapGroups 101 }

tmnxSapAtmV6v0Group OBJECT-GROUP
    OBJECTS {
      sapAtmEncapsulation,
      sapAtmIngressTrafficDescIndex,
      sapAtmEgressTrafficDescIndex,
      sapAtmOamAlarmCellHandling,
      sapAtmOamTerminate,
      sapAtmOamPeriodicLoopback,
      sapAtmLLFAdminStatus,
      sapAtmLLFOperStatus
      }
    STATUS      current
    DESCRIPTION
        "The group of objects supporting management of SAP
         ATM capabilities on Nokia SROS series systems."
    ::= { tmnxSapGroups 102 }

tmnxSapBaseV6v0Group OBJECT-GROUP
    OBJECTS {
      sapBaseStatsIngressPchipDroppedPackets,
      sapBaseStatsIngressPchipDroppedOctets,
      sapBaseStatsIngressPchipOfferedHiPrioPackets,
      sapBaseStatsIngressPchipOfferedHiPrioOctets,
      sapBaseStatsIngressPchipOfferedLoPrioPackets,
      sapBaseStatsIngressPchipOfferedLoPrioOctets,
      sapBaseStatsIngressQchipDroppedHiPrioPackets,
      sapBaseStatsIngressQchipDroppedHiPrioOctets,
      sapBaseStatsIngressQchipDroppedLoPrioPackets,
      sapBaseStatsIngressQchipDroppedLoPrioOctets,
      sapBaseStatsIngressQchipForwardedInProfPackets,
      sapBaseStatsIngressQchipForwardedInProfOctets,
      sapBaseStatsIngressQchipForwardedOutProfPackets,
      sapBaseStatsIngressQchipForwardedOutProfOctets,
      sapBaseStatsEgressQchipDroppedInProfPackets,
      sapBaseStatsEgressQchipDroppedInProfOctets,
      sapBaseStatsEgressQchipDroppedOutProfPackets,
      sapBaseStatsEgressQchipDroppedOutProfOctets,
      sapBaseStatsEgressQchipForwardedInProfPackets,
      sapBaseStatsEgressQchipForwardedInProfOctets,
      sapBaseStatsEgressQchipForwardedOutProfPackets,
      sapBaseStatsEgressQchipForwardedOutProfOctets,
      sapBaseStatsCustId,
      sapBaseStatsIngressPchipOfferedUncoloredPackets,
      sapBaseStatsIngressPchipOfferedUncoloredOctets,
      sapBaseStatsAuthenticationPktsDiscarded,
      sapBaseStatsAuthenticationPktsSuccess,
      sapBaseStatsLastClearedTime
      }
    STATUS      current
    DESCRIPTION
        "The group of objects supporting management of SAP
         Base capabilities on Nokia SROS series systems."
    ::= { tmnxSapGroups 103 }

tmnxSapQosV6v0Group OBJECT-GROUP
    OBJECTS {
      sapIngQosQueueId,
      sapIngQosQueueStatsOfferedHiPrioPackets,
      sapIngQosQueueStatsDroppedHiPrioPackets,
      sapIngQosQueueStatsOfferedLoPrioPackets,
      sapIngQosQueueStatsDroppedLoPrioPackets,
      sapIngQosQueueStatsOfferedHiPrioOctets,
      sapIngQosQueueStatsDroppedHiPrioOctets,
      sapIngQosQueueStatsOfferedLoPrioOctets,
      sapIngQosQueueStatsDroppedLoPrioOctets,
      sapIngQosQueueStatsForwardedInProfPackets,
      sapIngQosQueueStatsForwardedOutProfPackets,
      sapIngQosQueueStatsForwardedInProfOctets,
      sapIngQosQueueStatsForwardedOutProfOctets,
      sapIngQosCustId,
      sapIngQosQueueStatsUncoloredPacketsOffered,
      sapIngQosQueueStatsUncoloredOctetsOffered,
      sapEgrQosQueueId,
      sapEgrQosQueueStatsForwardedInProfPackets,
      sapEgrQosQueueStatsDroppedInProfPackets,
      sapEgrQosQueueStatsForwardedOutProfPackets,
      sapEgrQosQueueStatsDroppedOutProfPackets,
      sapEgrQosQueueStatsForwardedInProfOctets,
      sapEgrQosQueueStatsDroppedInProfOctets,
      sapEgrQosQueueStatsForwardedOutProfOctets,
      sapEgrQosQueueStatsDroppedOutProfOctets,
      sapEgrQosCustId,
      sapIngQosSchedStatsForwardedPackets,
      sapIngQosSchedStatsForwardedOctets,
      sapIngQosSchedCustId,
      sapEgrQosSchedStatsForwardedPackets,
      sapEgrQosSchedStatsForwardedOctets,
      sapEgrQosSchedCustId,

      sapIngQosQRowStatus,
      sapIngQosQLastMgmtChange,
      sapIngQosQOverrideFlags,
      sapIngQosQCBS,
      sapIngQosQMBS,
      sapIngQosQHiPrioOnly,
      sapIngQosQCIRAdaptation,
      sapIngQosQPIRAdaptation,
      sapIngQosQAdminPIR,
      sapIngQosQAdminCIR,
      sapEgrQosQRowStatus,
      sapEgrQosQLastMgmtChange,
      sapEgrQosQOverrideFlags,
      sapEgrQosQCBS,
      sapEgrQosQMBS,
      sapEgrQosQHiPrioOnly,
      sapEgrQosQCIRAdaptation,
      sapEgrQosQPIRAdaptation,
      sapEgrQosQAdminPIR,
      sapEgrQosQAdminCIR,
      sapEgrQosQAvgOverhead,
      sapIngQosSRowStatus,
      sapIngQosSLastMgmtChange,
      sapIngQosSOverrideFlags,
      sapIngQosSPIR,
      sapIngQosSCIR,
      sapIngQosSSummedCIR,
      sapEgrQosSRowStatus,
      sapEgrQosSLastMgmtChange,
      sapEgrQosSOverrideFlags,
      sapEgrQosSPIR,
      sapEgrQosSCIR,
      sapEgrQosSSummedCIR
      }
    STATUS      obsolete
    DESCRIPTION
        "The group of objects supporting management of SAP
         Ingress/Egress QoS capabilities on Nokia SROS series systems."
    ::= { tmnxSapGroups 104 }

tmnxSapStaticHostV6v0Group OBJECT-GROUP
    OBJECTS {
      sapStaticHostRowStatus,
      sapStaticHostSubscrIdent,
      sapStaticHostSubProfile,
      sapStaticHostSlaProfile,
      sapStaticHostShcvOperState,
      sapStaticHostShcvChecks,
      sapStaticHostShcvReplies,
      sapStaticHostShcvReplyTime,
      sapStaticHostDynMacAddress,
      sapStaticHostRetailerSvcId,
      sapStaticHostRetailerIf,
      sapStaticHostFwdingState,
      sapStaticHostAncpString,
      sapStaticHostSubIdIsSapId,
      sapStaticHostIntermediateDestId
      }
    STATUS      obsolete
    DESCRIPTION
        "The group of objects supporting management of SAP
         static host capabilities on Nokia SROS series systems."
    ::= { tmnxSapGroups 105 }

tmnxSapStaticHostV6v1Group OBJECT-GROUP
    OBJECTS {
      sapStaticHostRowStatus,
      sapStaticHostSubscrIdent,
      sapStaticHostSubProfile,
      sapStaticHostSlaProfile,
      sapStaticHostShcvOperState,
      sapStaticHostShcvChecks,
      sapStaticHostShcvReplies,
      sapStaticHostShcvReplyTime,
      sapStaticHostDynMacAddress,
      sapStaticHostRetailerSvcId,
      sapStaticHostRetailerIf,
      sapStaticHostFwdingState,
      sapStaticHostAncpString,
      sapStaticHostSubIdIsSapId,
      sapStaticHostIntermediateDestId,
      sapStaticHostAdminStatus,
      sapStaticHostMRtTblLastChgd,
      sapStaticHostMRtRowStatus,
      sapStaticHostMRtLastMgmtChange,
      sapStaticHostMRtStatus
      }
    STATUS      obsolete
    DESCRIPTION
        "The group of objects supporting management of SAP
         static host capabilities on Nokia SROS series systems."
    ::= { tmnxSapGroups 121 }


tmnxSapDhcpV6v0Group OBJECT-GROUP
    OBJECTS {
      sapTlsDhcpAdminState,
      sapTlsDhcpDescription,
      sapTlsDhcpSnoop,
      sapTlsDhcpLeasePopulate,
      sapTlsDhcpOperLeasePopulate,
      sapTlsDhcpInfoAction,
      sapTlsDhcpCircuitId,
      sapTlsDhcpRemoteIdString,
      sapTlsDhcpProxyAdminState,
      sapTlsDhcpProxyServerAddr,
      sapTlsDhcpProxyLTRadiusOverride,
      sapTlsDhcpVendorIncludeOptions,
      sapTlsDhcpVendorOptionString,
      sapTlsDhcpStatsClntSnoopdPckts,
      sapTlsDhcpStatsSrvrSnoopdPckts,
      sapTlsDhcpStatsClntForwdPckts,
      sapTlsDhcpStatsSrvrForwdPckts,
      sapTlsDhcpStatsClntDropdPckts,
      sapTlsDhcpStatsSrvrDropdPckts,
      sapTlsDhcpStatsClntProxRadPckts,
      sapTlsDhcpStatsClntProxLSPckts,
      sapTlsDhcpStatsGenReleasePckts,
      sapTlsDhcpStatsGenForceRenPckts,
      sapDhcpOperLeasePopulate
      }
    STATUS      obsolete
    DESCRIPTION
        "The group of objects supporting management of SAP
         TLS DHCP capabilities on Nokia SROS series systems."
    ::= { tmnxSapGroups 106 }


tmnxSapPortIdV6v0Group OBJECT-GROUP
    OBJECTS {
      sapPortIdIngQosSchedFwdPkts,
      sapPortIdIngQosSchedFwdOctets,
      sapPortIdIngQosSchedCustId,
      sapPortIdEgrQosSchedFwdPkts,
      sapPortIdEgrQosSchedFwdOctets,
      sapPortIdEgrQosSchedCustId
      }
    STATUS      current
    DESCRIPTION
        "The group of objects supporting management of SAP
         Port ID capabilities on Nokia SROS series systems."
    ::= { tmnxSapGroups 107 }


tmnxSapSubMgmtV6v0Group OBJECT-GROUP
    OBJECTS {
      sapSubMgmtAdminStatus,
      sapSubMgmtDefSubProfile,
      sapSubMgmtDefSlaProfile,
      sapSubMgmtSubIdentPolicy,
      sapSubMgmtSubscriberLimit,
      sapSubMgmtProfiledTrafficOnly,
      sapSubMgmtNonSubTrafficSubIdent,
      sapSubMgmtNonSubTrafficSubProf,
      sapSubMgmtNonSubTrafficSlaProf,
      sapSubMgmtMacDaHashing,
      sapSubMgmtDefSubIdent,
      sapSubMgmtDefSubIdentString
      }
    STATUS      obsolete
    DESCRIPTION
        "The group of objects supporting management of SAP
         Sub-management capabilities on Nokia SROS series systems."
    ::= { tmnxSapGroups 108 }


tmnxSapMstiV6v0Group OBJECT-GROUP
    OBJECTS {
      sapTlsMstiPriority,
      sapTlsMstiPathCost,
      sapTlsMstiLastMgmtChange,
      sapTlsMstiPortRole,
      sapTlsMstiPortState,
      sapTlsMstiDesignatedBridge,
      sapTlsMstiDesignatedPort
      }
    STATUS      current
    DESCRIPTION
        "The group of objects supporting management of SAP
         TLS MSTI capabilities on Nokia SROS series systems."
    ::= { tmnxSapGroups 109 }


tmnxSapIppipeV6v0Group OBJECT-GROUP
    OBJECTS {
      sapIpipeCeInetAddress,
      sapIpipeCeInetAddressType,
      sapIpipeMacRefreshInterval,
      sapIpipeMacAddress,
      sapIpipeArpedMacAddress,
      sapIpipeArpedMacAddressTimeout
      }
    STATUS      obsolete
    DESCRIPTION
        "The group of objects supporting management of SAP
         I-Pipe capabilities on Nokia SROS series systems."
    ::= { tmnxSapGroups 110 }

tmnxSapPolicyV6v0Group OBJECT-GROUP
    OBJECTS {
      sapCurrentIngressIpFilterId,
      sapCurrentIngressMacFilterId,
      sapCurrentIngressQosPolicyId,
      sapCurrentIngressQosSchedPlcy,
      sapCurrentEgressIpFilterId,
      sapCurrentEgressMacFilterId,
      sapCurrentEgressQosPolicyId,
      sapCurrentEgressQosSchedPlcy,
      sapIntendedIngressIpFilterId,
      sapIntendedIngressMacFilterId,
      sapIntendedIngressQosPolicyId,
      sapIntendedIngressQosSchedPlcy,
      sapIntendedEgressIpFilterId,
      sapIntendedEgressMacFilterId,
      sapIntendedEgressQosPolicyId,
      sapIntendedEgressQosSchedPlcy,

      sapIgQosPlcyDroppedHiPrioPackets,
      sapIgQosPlcyDroppedHiPrioOctets,
      sapIgQosPlcyDroppedLoPrioPackets,
      sapIgQosPlcyDroppedLoPrioOctets,
      sapIgQosPlcyForwardedInProfPackets,
      sapIgQosPlcyForwardedInProfOctets,
      sapIgQosPlcyForwardedOutProfPackets,
      sapIgQosPlcyForwardedOutProfOctets,
      sapEgQosPlcyDroppedInProfPackets,
      sapEgQosPlcyDroppedInProfOctets,
      sapEgQosPlcyDroppedOutProfPackets,
      sapEgQosPlcyDroppedOutProfOctets,
      sapEgQosPlcyForwardedInProfPackets,
      sapEgQosPlcyForwardedInProfOctets,
      sapEgQosPlcyForwardedOutProfPackets,
      sapEgQosPlcyForwardedOutProfOctets,
      sapIgQosPlcyQueueStatsOfferedHiPrioPackets,
      sapIgQosPlcyQueueStatsDroppedHiPrioPackets,
      sapIgQosPlcyQueueStatsOfferedLoPrioPackets,
      sapIgQosPlcyQueueStatsDroppedLoPrioPackets,
      sapIgQosPlcyQueueStatsOfferedHiPrioOctets,
      sapIgQosPlcyQueueStatsDroppedHiPrioOctets,
      sapIgQosPlcyQueueStatsOfferedLoPrioOctets,
      sapIgQosPlcyQueueStatsDroppedLoPrioOctets,
      sapIgQosPlcyQueueStatsForwardedInProfPackets,
      sapIgQosPlcyQueueStatsForwardedOutProfPackets,
      sapIgQosPlcyQueueStatsForwardedInProfOctets,
      sapIgQosPlcyQueueStatsForwardedOutProfOctets,
      sapIgQosPlcyQueueCustId,
      sapIgQosPlcyQueueStatsUncoloredPacketsOffered,
      sapIgQosPlcyQueueStatsUncoloredOctetsOffered,
      sapEgQosPlcyQueueStatsForwardedInProfPackets,
      sapEgQosPlcyQueueStatsDroppedInProfPackets,
      sapEgQosPlcyQueueStatsForwardedOutProfPackets,
      sapEgQosPlcyQueueStatsDroppedOutProfPackets,
      sapEgQosPlcyQueueStatsForwardedInProfOctets,
      sapEgQosPlcyQueueStatsDroppedInProfOctets,
      sapEgQosPlcyQueueStatsForwardedOutProfOctets,
      sapEgQosPlcyQueueStatsDroppedOutProfOctets,
      sapEgQosPlcyQueueCustId,

      sapIngSchedPlcyStatsFwdPkt,
      sapIngSchedPlcyStatsFwdOct,
      sapEgrSchedPlcyStatsFwdPkt,
      sapEgrSchedPlcyStatsFwdOct,
      sapIngSchedPlcyPortStatsFwdPkt,
      sapIngSchedPlcyPortStatsFwdOct,
      sapEgrSchedPlcyPortStatsFwdPkt,
      sapEgrSchedPlcyPortStatsFwdOct
      }
    STATUS      current
    DESCRIPTION
        "The group of objects supporting management of SAP
         ingress/egress capabilities on Nokia SROS series systems."
    ::= { tmnxSapGroups 111 }


tmnxSapCemV6v0Group OBJECT-GROUP
    OBJECTS {
      sapCemLastMgmtChange,
      sapCemEndpointType,
      sapCemBitrate,
      sapCemCasTrunkFraming,
      sapCemPayloadSize,
      sapCemJitterBuffer,
      sapCemUseRtpHeader,
      sapCemDifferential,
      sapCemTimestampFreq,
      sapCemReportAlarm,
      sapCemReportAlarmStatus,
      sapCemLocalEcid,
      sapCemRemoteMacAddr,
      sapCemRemoteEcid,
      sapCemJitterBufPackets,
      sapCemPlayoutBufPacketsThreshold,
      sapCemStatsIngressForwardedPkts,
      sapCemStatsIngressDroppedPkts,
      sapCemStatsEgressForwardedPkts,
      sapCemStatsEgressDroppedPkts,
      sapCemStatsEgressMissingPkts,
      sapCemStatsEgressPktsReOrder,
      sapCemStatsEgressJtrBfrUnderruns,
      sapCemStatsEgressJtrBfrOverruns,
      sapCemStatsEgressMisOrderDropped,
      sapCemStatsEgressMalformedPkts,
      sapCemStatsEgressLBitDropped,
      sapCemStatsEgressMultipleDropped,
      sapCemStatsEgressESs,
      sapCemStatsEgressSESs,
      sapCemStatsEgressUASs,
      sapCemStatsEgressFailureCounts,
      sapCemStatsEgressUnderrunCounts,
      sapCemStatsEgressOverrunCounts,
      sapCemStatsEgressJtrBfrDepth
      }
    STATUS      current
    DESCRIPTION
        "The group of objects supporting management of SAP
         Cem capabilities on Nokia SROS series systems."
    ::= { tmnxSapGroups 112 }


tmnxSapL2ptV6v0Group OBJECT-GROUP
    OBJECTS {
      sapTlsL2ptStatsLastClearedTime,
      sapTlsL2ptStatsL2ptEncapStpConfigBpdusRx,
      sapTlsL2ptStatsL2ptEncapStpConfigBpdusTx,
      sapTlsL2ptStatsL2ptEncapStpRstBpdusRx,
      sapTlsL2ptStatsL2ptEncapStpRstBpdusTx,
      sapTlsL2ptStatsL2ptEncapStpTcnBpdusRx,
      sapTlsL2ptStatsL2ptEncapStpTcnBpdusTx,
      sapTlsL2ptStatsL2ptEncapPvstConfigBpdusRx,
      sapTlsL2ptStatsL2ptEncapPvstConfigBpdusTx,
      sapTlsL2ptStatsL2ptEncapPvstRstBpdusRx,
      sapTlsL2ptStatsL2ptEncapPvstRstBpdusTx,
      sapTlsL2ptStatsL2ptEncapPvstTcnBpdusRx,
      sapTlsL2ptStatsL2ptEncapPvstTcnBpdusTx,
      sapTlsL2ptStatsStpConfigBpdusRx,
      sapTlsL2ptStatsStpConfigBpdusTx,
      sapTlsL2ptStatsStpRstBpdusRx,
      sapTlsL2ptStatsStpRstBpdusTx,
      sapTlsL2ptStatsStpTcnBpdusRx,
      sapTlsL2ptStatsStpTcnBpdusTx,
      sapTlsL2ptStatsPvstConfigBpdusRx,
      sapTlsL2ptStatsPvstConfigBpdusTx,
      sapTlsL2ptStatsPvstRstBpdusRx,
      sapTlsL2ptStatsPvstRstBpdusTx,
      sapTlsL2ptStatsPvstTcnBpdusRx,
      sapTlsL2ptStatsPvstTcnBpdusTx,
      sapTlsL2ptStatsOtherBpdusRx,
      sapTlsL2ptStatsOtherBpdusTx,
      sapTlsL2ptStatsOtherL2ptBpdusRx,
      sapTlsL2ptStatsOtherL2ptBpdusTx,
      sapTlsL2ptStatsOtherInvalidBpdusRx,
      sapTlsL2ptStatsOtherInvalidBpdusTx,
      sapTlsL2ptStatsL2ptEncapCdpBpdusRx,
      sapTlsL2ptStatsL2ptEncapCdpBpdusTx,
      sapTlsL2ptStatsL2ptEncapVtpBpdusRx,
      sapTlsL2ptStatsL2ptEncapVtpBpdusTx,
      sapTlsL2ptStatsL2ptEncapDtpBpdusRx,
      sapTlsL2ptStatsL2ptEncapDtpBpdusTx,
      sapTlsL2ptStatsL2ptEncapPagpBpdusRx,
      sapTlsL2ptStatsL2ptEncapPagpBpdusTx,
      sapTlsL2ptStatsL2ptEncapUdldBpdusRx,
      sapTlsL2ptStatsL2ptEncapUdldBpdusTx,
      sapTlsL2ptStatsCdpBpdusRx,
      sapTlsL2ptStatsCdpBpdusTx,
      sapTlsL2ptStatsVtpBpdusRx,
      sapTlsL2ptStatsVtpBpdusTx,
      sapTlsL2ptStatsDtpBpdusRx,
      sapTlsL2ptStatsDtpBpdusTx,
      sapTlsL2ptStatsPagpBpdusRx,
      sapTlsL2ptStatsPagpBpdusTx,
      sapTlsL2ptStatsUdldBpdusRx,
      sapTlsL2ptStatsUdldBpdusTx
      }
    STATUS      current
    DESCRIPTION
        "The group of objects supporting management of SAP
         TLS L2pt capabilities on Nokia SROS series systems."
    ::= { tmnxSapGroups 113 }


tmnxSapMsapV6v0Group OBJECT-GROUP
    OBJECTS {
      msapPlcyRowStatus,
      msapPlcyLastChanged,
      msapPlcyDescription,
      msapPlcyCpmProtPolicyId,
      msapPlcyCpmProtMonitorMac,
      msapPlcySubMgmtDefSubId,
      msapPlcySubMgmtDefSubIdStr,
      msapPlcySubMgmtDefSubProfile,
      msapPlcySubMgmtDefSlaProfile,
      msapPlcySubMgmtSubIdPlcy,
      msapPlcySubMgmtSubscriberLimit,
      msapPlcySubMgmtProfiledTrafOnly,
      msapPlcySubMgmtNonSubTrafSubId,
      msapPlcySubMgmtNonSubTrafSubProf,
      msapPlcySubMgmtNonSubTrafSlaProf,
      msapPlcyAssociatedMsaps,
      msapTlsPlcyLastChanged,
      msapTlsPlcySplitHorizonGrp,
      msapTlsPlcyArpReplyAgent,
      msapTlsPlcySubMgmtMacDaHashing,
      msapTlsPlcyDhcpLeasePopulate,
      msapTlsPlcyDhcpPrxyAdminState,
      msapTlsPlcyDhcpPrxyServAddr,
      msapTlsPlcyDhcpPrxyServAddrType,
      msapTlsPlcyDhcpPrxyLTRadOverride,
      msapTlsPlcyDhcpInfoAction,
      msapTlsPlcyDhcpCircuitId,
      msapTlsPlcyDhcpRemoteId,
      msapTlsPlcyDhcpRemoteIdString,
      msapTlsPlcyDhcpVendorInclOpts,
      msapTlsPlcyDhcpVendorOptStr,
      msapTlsPlcyDhcpPrxyLeaseTime,
      msapTlsPlcyEgressMcastGroup,
      msapTlsPlcyIgmpSnpgImportPlcy,
      msapTlsPlcyIgmpSnpgFastLeave,
      msapTlsPlcyIgmpSnpgSendQueries,
      msapTlsPlcyIgmpSnpgGenQueryIntv,
      msapTlsPlcyIgmpSnpgQueryRespIntv,
      msapTlsPlcyIgmpSnpgRobustCount,
      msapTlsPlcyIgmpSnpgLastMembIntvl,
      msapTlsPlcyIgmpSnpgMaxNbrGrps,
      msapTlsPlcyIgmpSnpgMvrFromVplsId,
      msapTlsPlcyIgmpSnpgVersion,
      msapTlsPlcyIgmpSnpgMcacPlcyName,
      msapTlsPlcyIgmpSnpgMcacPrRsvMnBW,
      msapTlsPlcyIgmpSnpgMcacUncnstBW,
      
      msapIgmpSnpgMcacLevelRowStatus,
      msapIgmpSnpgMcacLevelLastChanged,
      msapIgmpSnpgMcacLevelBW,
      msapIgmpSnpgMcacLagRowStatus,
      msapIgmpSnpgMcacLagLastChanged,
      msapIgmpSnpgMcacLagLevel,
      msapInfoCreationSapPortEncapVal,
      msapInfoCreationPlcyName,
      msapInfoReEvalPolicy,
      msapInfoLastChanged,

      msapCaptureSapStatsPktsRecvd,
      msapCaptureSapStatsPktsRedirect,
      msapCaptureSapStatsPktsDropped,
      msapPlcyTblLastChgd,
      msapTlsPlcyTblLastChgd,
      msapIgmpSnpgMcacLvlTblLastChgd,
      msapIgmpSnpgMcacLagTblLastChgd,
      msapInfoTblLastChgd
      }
    STATUS      obsolete
    DESCRIPTION
        "The group of objects supporting management of
         managed SAP capabilities on Nokia SROS series systems."
    ::= { tmnxSapGroups 114 }


tmnxSapMrpV6v0Group OBJECT-GROUP
    OBJECTS {
      sapTlsMrpRxPdus,
      sapTlsMrpDroppedPdus,
      sapTlsMrpTxPdus,
      sapTlsMrpRxNewEvent,
      sapTlsMrpRxJoinInEvent,
      sapTlsMrpRxInEvent,
      sapTlsMrpRxJoinEmptyEvent,
      sapTlsMrpRxEmptyEvent,
      sapTlsMrpRxLeaveEvent,
      sapTlsMrpTxNewEvent,
      sapTlsMrpTxJoinInEvent,
      sapTlsMrpTxInEvent,
      sapTlsMrpTxJoinEmptyEvent,
      sapTlsMrpTxEmptyEvent,
      sapTlsMrpTxLeaveEvent,
      sapTlsMmrpDeclared,
      sapTlsMmrpRegistered
      }
    STATUS      obsolete
    DESCRIPTION
        "The group of objects supporting management of SAP
         MRP capabilities on Nokia SROS series systems."
    ::= { tmnxSapGroups 115 }

tmnxSapHsmdaV6v0Group OBJECT-GROUP
    OBJECTS {
          sapIngressAggRateLimit,
          sapEgressHsmdaShaperOverride,
          sapIngressHsmdaPacketOffOvr,
          sapEgressHsmdaPacketOffOverride,
          sapIngQosHsmdaQueueRowStatus,
          sapIngQosHsmdaQueueLastChanged,
          sapIngQosHsmdaQueueAdminPIR,
          sapIngQosHsmdaQueueAdminCIR,
          sapIngQosHsmdaQueueSlopePolicy,
          sapEgrQosHsmdaQueueRowStatus,
          sapEgrQosHsmdaQueueLastChanged,
          sapEgrQosHsmdaQueueAdminPIR,
          sapEgrQosHsmdaQueueAdminCIR,
          sapEgrQosHsmdaQueueSlopePolicy,
          sapIngHsmdaQStatCustId,
          sapIngHsmdaQStatHiPktsDropped,
          sapIngHsmdaQStatLoPktsDropped,
          sapIngHsmdaQStatHiOctsDropped,
          sapIngHsmdaQStatLoOctsDropped,
          sapIngHsmdaQStatInProfPktsFwd,
          sapIngHsmdaQStatOutProfPktsFwd,
          sapIngHsmdaQStatInProfOctsFwd,
          sapIngHsmdaQStatOutProfOctsFwd,
          sapIngHsmdaQStatAllPktsOffered,
          sapIngHsmdaQStatAllOctsOffered,
          sapIngHsmdaCntrStCustId,
          sapIngHsmdaCntrStHiPktDrop,
          sapIngHsmdaCntrStLoPktDrop,
          sapIngHsmdaCntrStHiOctDrop,
          sapIngHsmdaCntrStLoOctDrop,
          sapIngHsmdaCntrStInProfPktFwd,
          sapIngHsmdaCntrStOutProfPktFwd,
          sapIngHsmdaCntrStInProfOctFwd,
          sapIngHsmdaCntrStOutProfOctFwd,
          sapIngHsmdaCntrStAllPktOffered,
          sapIngHsmdaCntrStAllOctOffered,
          sapEgrHsmdaQStatCustId,
          sapEgrHsmdaQStatInProfPktFwd,
          sapEgrHsmdaQStatInProfPktDropd,
          sapEgrHsmdaQStatOutProfPktFwd,
          sapEgrHsmdaQStatOutProfPktDropd,
          sapEgrHsmdaQStatInProfOctFwd,
          sapEgrHsmdaQStatInProfOctDropd,
          sapEgrHsmdaQStatOutProfOctFwd,
          sapEgrHsmdaQStatOutProfOctDropd,
          sapEgrHsmdaCntrStCustId,
          sapEgrHsmdaCntrStInProfPktFwd,
          sapEgrHsmdaCntrStInProfPktDrop,
          sapEgrHsmdaCntrStOutProfPktFwd,
          sapEgrHsmdaCntrStOutProfPktDrop,
          sapEgrHsmdaCntrStInProfOctFwd,
          sapEgrHsmdaCntrStInProfOctDrop,
          sapEgrHsmdaCntrStOutProfOctFwd,
          sapEgrHsmdaCntrStOutProfOctDrop
      }
    STATUS      obsolete
    DESCRIPTION
        "The group of objects supporting management of SAP Ingress/Egress
         QoS Hsmda capabilities on Nokia SROS series systems."
    ::= { tmnxSapGroups 116 }

tmnxTlsMsapPppoeV6v0Group OBJECT-GROUP
    OBJECTS {
        sapTlsPppoeMsapTrigger
    }
    STATUS      current
    DESCRIPTION
        "The group of objects supporting PPPOE on Managed SAPs
         feature on the Nokia SROS series systems."
    ::= { tmnxSapGroups 117 }

tmnxSapIpV6FilterV6v0Group OBJECT-GROUP
    OBJECTS {
      sapIngressIpv6FilterId,
      sapEgressIpv6FilterId,
      sapCurrentIngressIpv6FilterId,
      sapCurrentEgressIpv6FilterId,
      sapIntendedIngressIpv6FilterId,
      sapIntendedEgressIpv6FilterId
    }
    STATUS      current
    DESCRIPTION
        "The group of objects supporting management of SAP Ingress Policy
         capabilities on Nokia SROS series systems."
    ::= { tmnxSapGroups 118 }

tmnxSapBsxV6v0Group OBJECT-GROUP
    OBJECTS {
      sapStaticHostAppProfile,
      sapSubMgmtDefAppProfile,
      sapSubMgmtNonSubTrafficAppProf,
      msapPlcySubMgmtDefAppProfile,
      msapPlcySubMgmtNonSubTrafAppProf
      }
    STATUS      obsolete 
    DESCRIPTION
        "The group of objects supporting management of BSX (Application
         Assurance) capabilities on Nokia SROS series systems."
    ::= { tmnxSapGroups 119 }

tmnxSapMsapV6v1Group OBJECT-GROUP
    OBJECTS {
       msapL3PlcyTblLastChgd,
       msapL3PlcyLastChanged,
       msapL3PlcyAntiSpoof
      }
    STATUS      current
    DESCRIPTION
        "The group of objects supporting management of
         managed SAP L3 capabilities on Nokia SROS series systems."
    ::= { tmnxSapGroups 120 }

tmnxSapTlsV6v1Group OBJECT-GROUP
    OBJECTS {
      sapTlsStpAdminStatus,
      sapTlsStpPriority,
      sapTlsStpPortNum,
      sapTlsStpPathCost,
      sapTlsStpRapidStart,
      sapTlsStpBpduEncap,
      sapTlsStpPortState,
      sapTlsStpDesignatedBridge,
      sapTlsStpDesignatedPort,
      sapTlsStpForwardTransitions,
      sapTlsStpInConfigBpdus,
      sapTlsStpInTcnBpdus,
      sapTlsStpInBadBpdus,
      sapTlsStpOutConfigBpdus,
      sapTlsStpOutTcnBpdus,
      sapTlsStpOperBpduEncap,
      sapTlsVpnId,
      sapTlsCustId,
      sapTlsMacAddressLimit,
      sapTlsNumMacAddresses,
      sapTlsNumStaticMacAddresses,
      sapTlsMacLearning,
      sapTlsMacAgeing,
      sapTlsStpOperEdge,
      sapTlsStpAdminPointToPoint,
      sapTlsStpPortRole,
      sapTlsStpAutoEdge,
      sapTlsStpOperProtocol,
      sapTlsStpInRstBpdus,
      sapTlsStpOutRstBpdus,
      sapTlsLimitMacMove,
      sapTlsMacPinning,
      sapTlsDiscardUnknownSource,
      sapTlsMvplsPruneState,
      sapTlsMvplsMgmtService,
      sapTlsMvplsMgmtPortId,
      sapTlsMvplsMgmtEncapValue,
      sapTlsArpReplyAgent,
      sapTlsStpException,
      sapTlsAuthenticationPolicy,
      sapTlsL2ptTermination,
      sapTlsBpduTranslation,
      sapTlsStpRootGuard,
      sapTlsStpInsideRegion,
      sapTlsEgressMcastGroup,
      sapTlsStpInMstBpdus,
      sapTlsStpOutMstBpdus,
      sapTlsRestProtSrcMac,
      sapTlsRestProtSrcMacAction,
      sapTlsRestUnprotDstMac,
      sapTlsStpRxdDesigBridge,
      sapTlsStpRootGuardViolation,
      sapTlsShcvAction,
      sapTlsShcvSrcIp,
      sapTlsShcvSrcMac,
      sapTlsShcvInterval,
      sapTlsMvplsMgmtMsti,
      sapTlsMacMoveNextUpTime,
      sapTlsMacMoveRateExcdLeft,
      sapTlsL2ptForceBoundary,
      sapTlsLimitMacMoveLevel,
      sapTlsBpduTransOper,
      sapTlsDefMsapPolicy,
      sapTlsL2ptProtocols,
      sapTlsL2ptForceProtocols,
      sapTlsDhcpMsapTrigger,
      sapTlsDhcpProxyLeaseTime,
      sapTlsDhcpRemoteId,
      sapTlsMrpJoinTime,
      sapTlsMrpLeaveTime,
      sapTlsMrpLeaveAllTime,
      sapTlsMrpPeriodicTime,
      sapTlsMrpPeriodicEnabled,
      sapTlsPppoePolicy
      }
    STATUS      obsolete
    DESCRIPTION
        "The group of objects supporting management of SAP
         TLS capabilities on Nokia SROS series systems."
    ::= { tmnxSapGroups 122 }

tmnxSapArpHostGroup OBJECT-GROUP
    OBJECTS {
       sapTlsArpHostTableLastMgmtChange,
       sapTlsArpHostLastMgmtChange,
       sapTlsArpHostAdminState,
       sapTlsArpHostMaxNumHosts,
       sapTlsArpHostMinAuthIntvl,
       sapTlsArpMsapTrigger,
       msapTlsPlcyArpHostMaxNumHosts,
       msapTlsPlcyArpHostMinAuthIntvl,
       sapArpHostStatLastClearedTime,
       sapArpHostStatNumHosts,
       sapArpHostStatTriggersRx,
       sapArpHostStatTriggersIgnored,
       sapArpHostStatTrigIgnQFull,
       sapArpHostStatNumForcedVerif,
       sapArpHostStatNumCreated,
       sapArpHostStatNumDeleted,
       sapArpHostStatNumUpdated,
       sapArpHostStatNumAuthReq
      }
    STATUS      current
    DESCRIPTION
        "The group of objects supporting management of
         ARP hosts' capabilities for SAP's on Nokia SROS series 
         systems."
    ::= { tmnxSapGroups 123 }

tmnxSapV7v0Group OBJECT-GROUP
    OBJECTS {
      sapNumEntries,
      sapPortId,
      sapEncapValue,
      sapRowStatus,
      sapType,
      sapDescription,
      sapAdminStatus,
      sapOperStatus,
      sapIngressQosPolicyId,
      sapIngressMacFilterId,
      sapIngressIpFilterId,
      sapIngressVlanTranslationId,
      sapEgressQosPolicyId,
      sapEgressMacFilterId,
      sapEgressIpFilterId,
      sapMirrorStatus,
      sapIesIfIndex,
      sapLastMgmtChange,
      sapCollectAcctStats,
      sapAccountingPolicyId,
      sapVpnId,
      sapCustId,
      sapCustMultSvcSite,
      sapIngressQosSchedulerPolicy,
      sapEgressQosSchedulerPolicy,
      sapSplitHorizonGrp,
      sapIngressSharedQueuePolicy,
      sapIngressMatchQinQDot1PBits,
      sapOperFlags,
      sapLastStatusChange,
      sapAntiSpoofing,
      sapTodSuite,
      sapIngUseMultipointShared,
      sapEgressQinQMarkTopOnly,
      sapEgressAggRateLimit,
      sapEndPoint,
      sapIngressVlanTranslation,
      sapSubType,
      sapCpmProtPolicyId,
      sapCpmProtMonitorMac,
      sapEgressFrameBasedAccounting,
      sapEthernetLLFAdminStatus,
      sapEthernetLLFOperStatus,
      sapTlsMvplsRowStatus,
      sapEgressFrameBasedAccounting,
      sapCallingStationId
    }
    STATUS      obsolete
    DESCRIPTION
        "The group of objects supporting management of SAP
         general capabilities on Nokia SROS series systems."
    ::= { tmnxSapGroups 124 }

tmnxSapIgmpTrkGroup OBJECT-GROUP
    OBJECTS {
       sapIgmpTrkTableLastMgmtChange,
       sapIgmpTrkLastMgmtChange,
       sapIgmpTrkExpiryTime,
       sapIgmpTrkImportPlcy,
       sapIgmpTrkMaxNbrGrps,
       sapIgmpTrkNbrGrps,
       sapIgmpTrkMaxNbrSrcs
      }
    STATUS      current
    DESCRIPTION
        "The group of objects supporting management of
         IGMP host tracking capabilities for SAP's on Nokia SROS series 
         systems."
    ::= { tmnxSapGroups 125 }

tmnxSapFrGroup OBJECT-GROUP
    OBJECTS {
      sapFrInfoFrf12Mode,
      sapFrInfoSchedulingClass,
      sapFrInfoLastChanged,
      sapFrf12InfoFragmentThreshold,
      sapFrf12InfoLastChanged
      }
    STATUS      obsolete
    DESCRIPTION
        "The group of objects supporting management of SAP
         FR capabilities on Nokia SROS series systems."
    ::= { tmnxSapGroups 126 }

tmnxSapIpipeV7v0Group OBJECT-GROUP
    OBJECTS {
      sapIpipeCeInetAddress,
      sapIpipeCeInetAddressType,
      sapIpipeMacRefreshInterval,
      sapIpipeMacAddress,
      sapIpipeArpedMacAddress,
      sapIpipeArpedMacAddressTimeout,
      sapIpipeDiscoveredCeInetAddrType,
      sapIpipeDiscoveredCeInetAddr,
      sapIpipeUseBroadcastMac,
      sapIpipeUsingBroadcastMac
      }
    STATUS      obsolete
    DESCRIPTION
        "The group of objects supporting management of SAP
         IPIPE capabilities on Nokia SROS series systems."
    ::= { tmnxSapGroups 127 }

tmnxSapBsxV7v0Group OBJECT-GROUP
    OBJECTS {
      sapStaticHostAppProfile,
      sapSubMgmtDefAppProfile,
      sapSubMgmtNonSubTrafficAppProf,
      msapPlcySubMgmtDefAppProfile,
      msapPlcySubMgmtNonSubTrafAppProf,
      sapIsaAaApplicationProfile
      }
    STATUS      current
    DESCRIPTION
        "The group of objects supporting management of BSX (Application
         Assurance) capabilities on Nokia SROS series systems
         in release R7.0"
    ::= { tmnxSapGroups 128 }

tmnxSapTlsV7v0Group OBJECT-GROUP
    OBJECTS {
      sapTlsShcvRetryTimeout,
      sapTlsShcvRetryCount
      }
    STATUS      current
    DESCRIPTION
        "The group of objects supporting management of SAP
         TLS capabilities on Nokia SROS series systems
         added in release 7.0."
    ::= { tmnxSapGroups 137 }

tmnxSapRadiusFallbackGroup OBJECT-GROUP
    OBJECTS {
       sapTlsDefMsapService,
       sapTlsDefMsapGroupIf
      }
    STATUS      current
    DESCRIPTION
        "The group of objects supporting management of
         RADIUS fallback capabilities for SAP's on Nokia SROS series systems."
    ::= { tmnxSapGroups 129 }

tmnxSapPbbGroup OBJECT-GROUP
    OBJECTS {
       sapPbbRowStatus,
       sapPbbLastMgmtChange,
       sapPbbIgmpSnpgMRouter
      }
    STATUS      current
    DESCRIPTION
        "The group of objects supporting management of
         Provider Backbone Bridging (PBB/IEEE 802.1ah) capabilities for SAP's 
         on Nokia SROS series systems."
    ::= { tmnxSapGroups 130 }

tmnxSapFrGroupV8v0 OBJECT-GROUP
    OBJECTS {
      sapFrInfoFrf12Mode,
      sapFrInfoSchedulingClass,
      sapFrInfoLastChanged,
      sapFrf12InfoFragmentThreshold,
      sapFrf12InfoLastChanged,
      sapFrf12InfoInterleave
      }
    STATUS      current
    DESCRIPTION
        "The group of objects supporting management of SAP
         FR capabilities on Nokia SROS series systems."
    ::= { tmnxSapGroups 131 }

tmnxSapTlsV8v0Group OBJECT-GROUP
    OBJECTS {
      sapTlsStpAdminStatus,
      sapTlsStpPriority,
      sapTlsStpPortNum,
      sapTlsStpPathCost,
      sapTlsStpRapidStart,
      sapTlsStpBpduEncap,
      sapTlsStpPortState,
      sapTlsStpDesignatedBridge,
      sapTlsStpDesignatedPort,
      sapTlsStpForwardTransitions,
      sapTlsStpInConfigBpdus,
      sapTlsStpInTcnBpdus,
      sapTlsStpInBadBpdus,
      sapTlsStpOutConfigBpdus,
      sapTlsStpOutTcnBpdus,
      sapTlsStpOperBpduEncap,
      sapTlsVpnId,
      sapTlsCustId,
      sapTlsMacAddressLimit,
      sapTlsNumMacAddresses,
      sapTlsNumStaticMacAddresses,
      sapTlsMacLearning,
      sapTlsMacAgeing,
      sapTlsStpOperEdge,
      sapTlsStpAdminPointToPoint,
      sapTlsStpPortRole,
      sapTlsStpAutoEdge,
      sapTlsStpOperProtocol,
      sapTlsStpInRstBpdus,
      sapTlsStpOutRstBpdus,
      sapTlsLimitMacMove,
      sapTlsMacPinning,
      sapTlsDiscardUnknownSource,
      sapTlsMvplsPruneState,
      sapTlsMvplsMgmtService,
      sapTlsMvplsMgmtPortId,
      sapTlsMvplsMgmtEncapValue,
      sapTlsArpReplyAgent,
      sapTlsStpException,
      sapTlsAuthenticationPolicy,
      sapTlsL2ptTermination,
      sapTlsBpduTranslation,
      sapTlsStpRootGuard,
      sapTlsStpInsideRegion,
      sapTlsEgressMcastGroup,
      sapTlsStpInMstBpdus,
      sapTlsStpOutMstBpdus,
      sapTlsRestProtSrcMac,
      sapTlsRestProtSrcMacAction,
      sapTlsRestUnprotDstMac,
      sapTlsStpRxdDesigBridge,
      sapTlsStpRootGuardViolation,
      sapTlsShcvAction,
      sapTlsShcvSrcIp,
      sapTlsShcvSrcMac,
      sapTlsShcvInterval,
      sapTlsMvplsMgmtMsti,
      sapTlsMacMoveNextUpTime,
      sapTlsMacMoveRateExcdLeft,
      sapTlsL2ptForceBoundary,
      sapTlsLimitMacMoveLevel,
      sapTlsBpduTransOper,
      sapTlsDefMsapPolicy,
      sapTlsL2ptProtocols,
      sapTlsL2ptForceProtocols,
      sapTlsDhcpMsapTrigger,
      sapTlsDhcpProxyLeaseTime,
      sapTlsDhcpRemoteId,
      sapTlsMrpJoinTime,
      sapTlsMrpLeaveTime,
      sapTlsMrpLeaveAllTime,
      sapTlsMrpPeriodicTime,
      sapTlsMrpPeriodicEnabled,
      sapTlsPppoePolicy,
      sapTlsMrpPolicy,
      sapTlsSiteName,
      sapTlsDhcp6MsapTrigger,
      sapTlsInTcBitBpdus,
      sapTlsOutTcBitBpdus
      }
    STATUS      current
    DESCRIPTION
        "The group of objects supporting management of SAP
         TLS capabilities on Nokia SROS series systems."
    ::= { tmnxSapGroups 132 }

tmnxSapDhcpV8v0Group OBJECT-GROUP
    OBJECTS {
      sapTlsDhcpAdminState,
      sapTlsDhcpDescription,
      sapTlsDhcpSnoop,
      sapTlsDhcpLeasePopulate,
      sapTlsDhcpOperLeasePopulate,
      sapTlsDhcpInfoAction,
      sapTlsDhcpCircuitId,
      sapTlsDhcpRemoteIdString,
      sapTlsDhcpProxyAdminState,
      sapTlsDhcpProxyServerAddr,
      sapTlsDhcpProxyLTRadiusOverride,
      sapTlsDhcpVendorIncludeOptions,
      sapTlsDhcpVendorOptionString,
      sapTlsDhcpStatsClntSnoopdPckts,
      sapTlsDhcpStatsSrvrSnoopdPckts,
      sapTlsDhcpStatsClntForwdPckts,
      sapTlsDhcpStatsSrvrForwdPckts,
      sapTlsDhcpStatsClntDropdPckts,
      sapTlsDhcpStatsSrvrDropdPckts,
      sapTlsDhcpStatsClntProxRadPckts,
      sapTlsDhcpStatsClntProxLSPckts,
      sapTlsDhcpStatsGenReleasePckts,
      sapTlsDhcpStatsGenForceRenPckts,
      sapDhcpOperLeasePopulate
      }
    STATUS      current
    DESCRIPTION
        "The group of objects supporting management of SAP
         TLS DHCP capabilities on Nokia SROS series systems."
    ::= { tmnxSapGroups 133 }

tmnxSapV8v0Group OBJECT-GROUP
    OBJECTS {
      sapNumEntries,
      sapPortId,
      sapEncapValue,
      sapRowStatus,
      sapType,
      sapDescription,
      sapAdminStatus,
      sapOperStatus,
      sapIngressQosPolicyId,
      sapIngressMacFilterId,
      sapIngressIpFilterId,
      sapIngressVlanTranslationId,
      sapEgressQosPolicyId,
      sapEgressMacFilterId,
      sapEgressIpFilterId,
      sapMirrorStatus,
      sapIesIfIndex,
      sapLastMgmtChange,
      sapCollectAcctStats,
      sapAccountingPolicyId,
      sapVpnId,
      sapCustId,
      sapCustMultSvcSite,
      sapIngressQosSchedulerPolicy,
      sapEgressQosSchedulerPolicy,
      sapSplitHorizonGrp,
      sapIngressSharedQueuePolicy,
      sapIngressMatchQinQDot1PBits,
      sapOperFlags,
      sapLastStatusChange,
      sapAntiSpoofing,
      sapTodSuite,
      sapIngUseMultipointShared,
      sapEgressQinQMarkTopOnly,
      sapEgressAggRateLimit,
      sapEndPoint,
      sapIngressVlanTranslation,
      sapSubType,
      sapCpmProtPolicyId,
      sapCpmProtMonitorMac,
      sapEgressFrameBasedAccounting,
      sapEthernetLLFAdminStatus,
      sapEthernetLLFOperStatus,
      sapTlsMvplsRowStatus,
      sapEgressFrameBasedAccounting,
      sapCallingStationId,
      sapIngPolicerPolicy,
      sapEgrPolicerPolicy,
      sapIpv6HostInfoIpoeDhcp6Hosts,
      sapIpv6HostInfoPppDhcp6Hosts,
      sapIpv6HostInfoPppSLAACHosts,
      sapIngQosQMBSBytes,
      sapEgrQosQMBSBytes
    }
    STATUS      obsolete
    DESCRIPTION
        "The group of objects supporting management of SAP
         general capabilities on Nokia SROS series systems."
    ::= { tmnxSapGroups 134 }


tmnxSapFPropBMacV8v0Group OBJECT-GROUP
    OBJECTS {
        sapFPropBMacAddrTblLastChgd,
        sapFPropBMacAddrRowStatus
    }
    STATUS      current
    DESCRIPTION
        "The group of objects supporting management of SAP
         fault propagation BMac addresses on Nokia SROS series
         systems."
    ::= { tmnxSapGroups 135 }

tmnxSapPlcrV8v0Group OBJECT-GROUP
    OBJECTS {
       sapIngPlcrCtrlOvrLastChgd, 
       sapIngPlcrCtrlOvrLvlLastChgd, 
       sapIngPlcrCtrlOvrLvlMBS, 
       sapIngPlcrCtrlOvrLvlTblLastChgd, 
       sapIngPlcrCtrlOvrMaxRate, 
       sapIngPlcrCtrlOvrMinMBSSep, 
       sapIngPlcrCtrlOvrRowStatus, 
       sapIngPlcrCtrlOvrTblLastChgd, 
       sapIngPlcrOvrAdminCIR, 
       sapIngPlcrOvrAdminPIR, 
       sapIngPlcrOvrCBS, 
       sapIngPlcrOvrPktOffset, 
       sapIngPlcrOvrLastChgd, 
       sapIngPlcrOvrMBS, 
       sapIngPlcrOvrRowStatus, 
       sapIngPlcrOvrStatMode, 
       sapIngPlcrOvrTblLastChgd,
       sapEgrPlcrCtrlOvrLastChgd, 
       sapEgrPlcrCtrlOvrLvlLastChgd, 
       sapEgrPlcrCtrlOvrLvlMBS, 
       sapEgrPlcrCtrlOvrLvlTblLastChgd, 
       sapEgrPlcrCtrlOvrMaxRate, 
       sapEgrPlcrCtrlOvrMinMBSSep, 
       sapEgrPlcrCtrlOvrRowStatus, 
       sapEgrPlcrCtrlOvrTblLastChgd, 
       sapEgrPlcrOvrAdminCIR, 
       sapEgrPlcrOvrAdminPIR, 
       sapEgrPlcrOvrCBS, 
       sapEgrPlcrOvrPktOffset, 
       sapEgrPlcrOvrLastChgd, 
       sapEgrPlcrOvrMBS, 
       sapEgrPlcrOvrRowStatus, 
       sapEgrPlcrOvrStatMode, 
       sapEgrPlcrOvrTblLastChgd
    }
    STATUS      current
    DESCRIPTION
        "The group of objects supporting management of SAP
         Policer on Nokia SROS series systems."
    ::= { tmnxSapGroups 136 }


tmnxSapSubMgmtV8v0Group OBJECT-GROUP
    OBJECTS {
      sapSubMgmtAdminStatus,
      sapSubMgmtDefSubProfile,
      sapSubMgmtDefSlaProfile,
      sapSubMgmtSubIdentPolicy,
      sapSubMgmtSubscriberLimit,
      sapSubMgmtProfiledTrafficOnly,
      sapSubMgmtNonSubTrafficSubIdent,
      sapSubMgmtNonSubTrafficSubProf,
      sapSubMgmtNonSubTrafficSlaProf,
      sapSubMgmtMacDaHashing,
      sapSubMgmtDefSubIdent,
      sapSubMgmtDefSubIdentString,
      sapSubMgmtDefInterDestId,
      sapSubMgmtDefInterDestIdString
      }
    STATUS      obsolete
    DESCRIPTION
        "The group of objects supporting management of SAP
         Sub-management capabilities on Nokia SROS series systems."
    ::= { tmnxSapGroups 138 }


tmnxSapMsapV8v0Group OBJECT-GROUP
    OBJECTS {
      msapPlcyRowStatus,
      msapPlcyLastChanged,
      msapPlcyDescription,
      msapPlcyCpmProtPolicyId,
      msapPlcyCpmProtMonitorMac,
      msapPlcySubMgmtDefSubId,
      msapPlcySubMgmtDefSubIdStr,
      msapPlcySubMgmtDefSubProfile,
      msapPlcySubMgmtDefSlaProfile,
      msapPlcySubMgmtSubIdPlcy,
      msapPlcySubMgmtSubscriberLimit,
      msapPlcySubMgmtProfiledTrafOnly,
      msapPlcySubMgmtNonSubTrafSubId,
      msapPlcySubMgmtNonSubTrafSubProf,
      msapPlcySubMgmtNonSubTrafSlaProf,
      msapPlcySubMgmtDefInterDestId,
      msapPlcySubMgmtDefInterDestIdStr,
      msapPlcyAssociatedMsaps,
      msapPlcyIgmpTrkExpiryTime,
      msapPlcyIgmpTrkImportPlcy,
      msapPlcyIgmpTrkMaxNbrGrps,
      msapPlcyIgmpTrkMaxNbrSrcs,
      msapTlsPlcyLastChanged,
      msapTlsPlcySplitHorizonGrp,
      msapTlsPlcyArpReplyAgent,
      msapTlsPlcySubMgmtMacDaHashing,
      msapTlsPlcyDhcpLeasePopulate,
      msapTlsPlcyDhcpPrxyAdminState,
      msapTlsPlcyDhcpPrxyServAddr,
      msapTlsPlcyDhcpPrxyServAddrType,
      msapTlsPlcyDhcpPrxyLTRadOverride,
      msapTlsPlcyDhcpInfoAction,
      msapTlsPlcyDhcpCircuitId,
      msapTlsPlcyDhcpRemoteId,
      msapTlsPlcyDhcpRemoteIdString,
      msapTlsPlcyDhcpVendorInclOpts,
      msapTlsPlcyDhcpVendorOptStr,
      msapTlsPlcyDhcpPrxyLeaseTime,
      msapTlsPlcyEgressMcastGroup,
      msapTlsPlcyIgmpSnpgImportPlcy,
      msapTlsPlcyIgmpSnpgFastLeave,
      msapTlsPlcyIgmpSnpgSendQueries,
      msapTlsPlcyIgmpSnpgGenQueryIntv,
      msapTlsPlcyIgmpSnpgQueryRespIntv,
      msapTlsPlcyIgmpSnpgRobustCount,
      msapTlsPlcyIgmpSnpgLastMembIntvl,
      msapTlsPlcyIgmpSnpgMaxNbrGrps,
      msapTlsPlcyIgmpSnpgMvrFromVplsId,
      msapTlsPlcyIgmpSnpgVersion,
      msapTlsPlcyIgmpSnpgMcacPlcyName,
      msapTlsPlcyIgmpSnpgMcacPrRsvMnBW,
      msapTlsPlcyIgmpSnpgMcacUncnstBW,

      msapIgmpSnpgMcacLevelRowStatus,
      msapIgmpSnpgMcacLevelLastChanged,
      msapIgmpSnpgMcacLevelBW,
      msapIgmpSnpgMcacLagRowStatus,
      msapIgmpSnpgMcacLagLastChanged,
      msapIgmpSnpgMcacLagLevel,
      msapInfoCreationSapPortEncapVal,
      msapInfoCreationPlcyName,
      msapInfoReEvalPolicy,
      msapInfoLastChanged,

      msapCaptureSapStatsPktsRecvd,
      msapCaptureSapStatsPktsRedirect,
      msapCaptureSapStatsPktsDropped,
      msapPlcyTblLastChgd,
      msapTlsPlcyTblLastChgd,
      msapIgmpSnpgMcacLvlTblLastChgd,
      msapIgmpSnpgMcacLagTblLastChgd,
      msapInfoTblLastChgd
      }
    STATUS      current
    DESCRIPTION
        "The group of objects supporting management of
         managed SAP capabilities on Nokia SROS series systems."
    ::= { tmnxSapGroups 139 }

tmnxSapQosV8v0Group OBJECT-GROUP
    OBJECTS {
      sapIngQosQueueId,
      sapIngQosQueueStatsOfferedHiPrioPackets,
      sapIngQosQueueStatsDroppedHiPrioPackets,
      sapIngQosQueueStatsOfferedLoPrioPackets,
      sapIngQosQueueStatsDroppedLoPrioPackets,
      sapIngQosQueueStatsOfferedHiPrioOctets,
      sapIngQosQueueStatsDroppedHiPrioOctets,
      sapIngQosQueueStatsOfferedLoPrioOctets,
      sapIngQosQueueStatsDroppedLoPrioOctets,
      sapIngQosQueueStatsForwardedInProfPackets,
      sapIngQosQueueStatsForwardedOutProfPackets,
      sapIngQosQueueStatsForwardedInProfOctets,
      sapIngQosQueueStatsForwardedOutProfOctets,
      sapIngQosCustId,
      sapIngQosQueueStatsUncoloredPacketsOffered,
      sapIngQosQueueStatsUncoloredOctetsOffered,
      sapEgrQosQueueId,
      sapEgrQosQueueStatsForwardedInProfPackets,
      sapEgrQosQueueStatsDroppedInProfPackets,
      sapEgrQosQueueStatsForwardedOutProfPackets,
      sapEgrQosQueueStatsDroppedOutProfPackets,
      sapEgrQosQueueStatsForwardedInProfOctets,
      sapEgrQosQueueStatsDroppedInProfOctets,
      sapEgrQosQueueStatsForwardedOutProfOctets,
      sapEgrQosQueueStatsDroppedOutProfOctets,
      sapEgrQosCustId,
      sapIngQosSchedStatsForwardedPackets,
      sapIngQosSchedStatsForwardedOctets,
      sapIngQosSchedCustId,
      sapEgrQosSchedStatsForwardedPackets,
      sapEgrQosSchedStatsForwardedOctets,
      sapEgrQosSchedCustId,

      sapIngQosQRowStatus,
      sapIngQosQLastMgmtChange,
      sapIngQosQOverrideFlags,
      sapIngQosQCBS,
      sapIngQosQHiPrioOnly,
      sapIngQosQCIRAdaptation,
      sapIngQosQPIRAdaptation,
      sapIngQosQAdminPIR,
      sapIngQosQAdminCIR,
      sapEgrQosQRowStatus,
      sapEgrQosQLastMgmtChange,
      sapEgrQosQOverrideFlags,
      sapEgrQosQCBS,
      sapEgrQosQHiPrioOnly,
      sapEgrQosQCIRAdaptation,
      sapEgrQosQPIRAdaptation,
      sapEgrQosQAdminPIR,
      sapEgrQosQAdminCIR,
      sapEgrQosQAvgOverhead,
      sapIngQosSRowStatus,
      sapIngQosSLastMgmtChange,
      sapIngQosSOverrideFlags,
      sapIngQosSPIR,
      sapIngQosSCIR,
      sapIngQosSSummedCIR,
      sapEgrQosSRowStatus,
      sapEgrQosSLastMgmtChange,
      sapEgrQosSOverrideFlags,
      sapEgrQosSPIR,
      sapEgrQosSCIR,
      sapEgrQosSSummedCIR,
      
      sapIngQosPStatsCustId            ,
      sapIngQosPStatsMode              ,
      sapIngQosPStatsOffHiPrioPkts     ,
      sapIngQosPStatsOffHiPrioPktsLo   ,
      sapIngQosPStatsOffHiPrioPktsHi   ,
      sapIngQosPStatsDrpHiPrioPkts     ,
      sapIngQosPStatsDrpHiPrioPktsLo   ,
      sapIngQosPStatsDrpHiPrioPktsHi   ,
      sapIngQosPStatsOffLoPrioPkts     ,
      sapIngQosPStatsOffLoPrioPktsLo   ,
      sapIngQosPStatsOffLoPrioPktsHi   ,
      sapIngQosPStatsDrpLoPrioPkts     ,
      sapIngQosPStatsDrpLoPrioPktsLo   ,
      sapIngQosPStatsDrpLoPrioPktsHi   ,
      sapIngQosPStatsOffHiPrioOcts     ,
      sapIngQosPStatsOffHiPrioOctsLo   ,
      sapIngQosPStatsOffHiPrioOctsHi   ,
      sapIngQosPStatsDrpHiPrioOcts     ,
      sapIngQosPStatsDrpHiPrioOctsLo   ,
      sapIngQosPStatsDrpHiPrioOctsHi   ,
      sapIngQosPStatsOffLoPrioOcts     ,
      sapIngQosPStatsOffLoPrioOctsLo   ,
      sapIngQosPStatsOffLoPrioOctsHi   ,
      sapIngQosPStatsDrpLoPrioOcts     ,
      sapIngQosPStatsDrpLoPrioOctsLo   ,
      sapIngQosPStatsDrpLoPrioOctsHi   ,
      sapIngQosPStatsFwdInProfPkts     ,
      sapIngQosPStatsFwdInProfPktsLo   ,
      sapIngQosPStatsFwdInProfPktsHi   ,
      sapIngQosPStatsFwdOutProfPkts    ,
      sapIngQosPStatsFwdOutProfPktsLo  ,
      sapIngQosPStatsFwdOutProfPktsHi  ,
      sapIngQosPStatsFwdInProfOcts     ,
      sapIngQosPStatsFwdInProfOctsLo   ,
      sapIngQosPStatsFwdInProfOctsHi   ,
      sapIngQosPStatsFwdOutProfOcts    ,
      sapIngQosPStatsFwdOutProfOctsLo  ,
      sapIngQosPStatsFwdOutProfOctsHi  ,
      sapIngQosPStatsUncolPktsOff      ,
      sapIngQosPStatsUncolPktsOffLo    ,
      sapIngQosPStatsUncolPktsOffHi    ,
      sapIngQosPStatsUncolOctsOff      ,
      sapIngQosPStatsUncolOctsOffLo    ,
      sapIngQosPStatsUncolOctsOffHi    ,
      
      sapEgrQosPStatsCustId            ,
      sapEgrQosPStatsMode              ,
      sapEgrQosPStatsOffInProfPkts     ,
      sapEgrQosPStatsOffInProfPktsLo   ,
      sapEgrQosPStatsOffInProfPktsHi   ,
      sapEgrQosPStatsFwdInProfPkts     ,
      sapEgrQosPStatsFwdInProfPktsLo   ,
      sapEgrQosPStatsFwdInProfPktsHi   ,
      sapEgrQosPStatsDrpInProfPkts     ,
      sapEgrQosPStatsDrpInProfPktsLo   ,
      sapEgrQosPStatsDrpInProfPktsHi   ,
      sapEgrQosPStatsOffOutProfPkts    ,
      sapEgrQosPStatsOffOutProfPktsLo  ,
      sapEgrQosPStatsOffOutProfPktsHi  ,
      sapEgrQosPStatsFwdOutProfPkts    ,
      sapEgrQosPStatsFwdOutProfPktsLo  ,
      sapEgrQosPStatsFwdOutProfPktsHi  ,
      sapEgrQosPStatsDrpOutProfPkts    ,
      sapEgrQosPStatsDrpOutProfPktsLo  ,
      sapEgrQosPStatsDrpOutProfPktsHi  ,
      sapEgrQosPStatsOffInProfOcts     ,
      sapEgrQosPStatsOffInProfOctsLo   ,
      sapEgrQosPStatsOffInProfOctsHi   ,
      sapEgrQosPStatsFwdInProfOcts     ,
      sapEgrQosPStatsFwdInProfOctsLo   ,
      sapEgrQosPStatsFwdInProfOctsHi   ,
      sapEgrQosPStatsDrpInProfOcts     ,
      sapEgrQosPStatsDrpInProfOctsLo   ,
      sapEgrQosPStatsDrpInProfOctsHi   ,
      sapEgrQosPStatsOffOutProfOcts    ,
      sapEgrQosPStatsOffOutProfOctsLo  ,
      sapEgrQosPStatsOffOutProfOctsHi  ,
      sapEgrQosPStatsFwdOutProfOcts    ,
      sapEgrQosPStatsFwdOutProfOctsLo  ,
      sapEgrQosPStatsFwdOutProfOctsHi  ,
      sapEgrQosPStatsDrpOutProfOcts    ,
      sapEgrQosPStatsDrpOutProfOctsLo  ,
      sapEgrQosPStatsDrpOutProfOctsHi  ,
      sapEgrQosPStatsUncolPktsOff      ,
      sapEgrQosPStatsUncolPktsOffLo    ,
      sapEgrQosPStatsUncolPktsOffHi    ,
      sapEgrQosPStatsUncolOctsOff      ,
      sapEgrQosPStatsUncolOctsOffLo    ,
      sapEgrQosPStatsUncolOctsOffHi    ,
      
      sapIgQosPlcyPStatCustId          ,
      sapIgQosPlcyPStatMode            ,
      sapIgQosPlcyPStatOffHiPrioPkts   ,
      sapIgQosPlcyPStatDrpHiPrioPkts   ,
      sapIgQosPlcyPStatOffLoPrioPkts   ,
      sapIgQosPlcyPStatDrpLoPrioPkts   ,
      sapIgQosPlcyPStatOffHiPrioOcts   ,
      sapIgQosPlcyPStatDrpHiPrioOcts   ,
      sapIgQosPlcyPStatOffLoPrioOcts   ,
      sapIgQosPlcyPStatDrpLoPrioOcts   ,
      sapIgQosPlcyPStatFwdInProfPkts   ,
      sapIgQosPlcyPStatFwdOutProfPkts  ,
      sapIgQosPlcyPStatFwdInProfOcts   ,
      sapIgQosPlcyPStatFwdOutProfOcts  ,
      sapIgQosPlcyPStatUncolPktsOff    ,
      sapIgQosPlcyPStatUncolOctsOff    ,
      sapIgQosPlcyPStatOffHiPrioPkts   ,
      sapIgQosPlcyPStatOffHiPrioPktsL  ,
      sapIgQosPlcyPStatOffHiPrioPktsH  ,
      sapIgQosPlcyPStatDrpHiPrioPkts   ,
      sapIgQosPlcyPStatDrpHiPrioPktsL  ,
      sapIgQosPlcyPStatDrpHiPrioPktsH  ,
      sapIgQosPlcyPStatOffLoPrioPkts   ,
      sapIgQosPlcyPStatOffLoPrioPktsL  ,
      sapIgQosPlcyPStatOffLoPrioPktsH  ,
      sapIgQosPlcyPStatDrpLoPrioPkts   ,
      sapIgQosPlcyPStatDrpLoPrioPktsL  ,
      sapIgQosPlcyPStatDrpLoPrioPktsH  ,
      sapIgQosPlcyPStatOffHiPrioOcts   ,
      sapIgQosPlcyPStatOffHiPrioOctsL  ,
      sapIgQosPlcyPStatOffHiPrioOctsH  ,
      sapIgQosPlcyPStatDrpHiPrioOcts   ,
      sapIgQosPlcyPStatDrpHiPrioOctsL  ,
      sapIgQosPlcyPStatDrpHiPrioOctsH  ,
      sapIgQosPlcyPStatOffLoPrioOcts   ,
      sapIgQosPlcyPStatOffLoPrioOctsL  ,
      sapIgQosPlcyPStatOffLoPrioOctsH  ,
      sapIgQosPlcyPStatDrpLoPrioOcts   ,
      sapIgQosPlcyPStatDrpLoPrioOctsL  ,
      sapIgQosPlcyPStatDrpLoPrioOctsH  ,
      sapIgQosPlcyPStatFwdInProfPkts   ,
      sapIgQosPlcyPStatFwdInProfPktsL  ,
      sapIgQosPlcyPStatFwdInProfPktsH  ,
      sapIgQosPlcyPStatFwdOutProfPkts  ,
      sapIgQosPlcyPStatFwdOutProfPktsL ,
      sapIgQosPlcyPStatFwdOutProfPktsH ,
      sapIgQosPlcyPStatFwdInProfOcts   ,
      sapIgQosPlcyPStatFwdInProfOctsL  ,
      sapIgQosPlcyPStatFwdInProfOctsH  ,
      sapIgQosPlcyPStatFwdOutProfOcts  ,
      sapIgQosPlcyPStatFwdOutProfOctsL ,
      sapIgQosPlcyPStatFwdOutProfOctsH ,
      sapIgQosPlcyPStatUncolPktsOff    ,
      sapIgQosPlcyPStatUncolPktsOffL   ,
      sapIgQosPlcyPStatUncolPktsOffH   ,
      sapIgQosPlcyPStatUncolOctsOff    ,
      sapIgQosPlcyPStatUncolOctsOffL   ,
      sapIgQosPlcyPStatUncolOctsOffH   ,
      
--      sapEgQosPlcyPStatPlcyId          ,
--      sapEgQosPlcyPStatPolId           ,
      sapEgQosPlcyPStatCustId          ,
      sapEgQosPlcyPStatMode            ,
      sapEgQosPlcyPStatOffInProfPkts   ,
      sapEgQosPlcyPStatOffInProfPktsL  ,
      sapEgQosPlcyPStatOffInProfPktsH  ,
      sapEgQosPlcyPStatFwdInProfPkts   ,
      sapEgQosPlcyPStatFwdInProfPktsL  ,
      sapEgQosPlcyPStatFwdInProfPktsH  ,
      sapEgQosPlcyPStatDrpInProfPkts   ,
      sapEgQosPlcyPStatDrpInProfPktsL  ,
      sapEgQosPlcyPStatDrpInProfPktsH  ,
      sapEgQosPlcyPStatOffOutProfPkts  ,
      sapEgQosPlcyPStatOffOutProfPktsL ,
      sapEgQosPlcyPStatOffOutProfPktsH ,
      sapEgQosPlcyPStatFwdOutProfPkts  ,
      sapEgQosPlcyPStatFwdOutProfPktsL ,
      sapEgQosPlcyPStatFwdOutProfPktsH ,
      sapEgQosPlcyPStatDrpOutProfPkts  ,
      sapEgQosPlcyPStatDrpOutProfPktsL ,
      sapEgQosPlcyPStatDrpOutProfPktsH ,
      sapEgQosPlcyPStatOffInProfOcts   ,
      sapEgQosPlcyPStatOffInProfOctsL  ,
      sapEgQosPlcyPStatOffInProfOctsH  ,
      sapEgQosPlcyPStatFwdInProfOcts   ,
      sapEgQosPlcyPStatFwdInProfOctsL  ,
      sapEgQosPlcyPStatFwdInProfOctsH  ,
      sapEgQosPlcyPStatDrpInProfOcts   ,
      sapEgQosPlcyPStatDrpInProfOctsL  ,
      sapEgQosPlcyPStatDrpInProfOctsH  ,
      sapEgQosPlcyPStatOffOutProfOcts  ,
      sapEgQosPlcyPStatOffOutProfOctsL ,
      sapEgQosPlcyPStatOffOutProfOctsH ,
      sapEgQosPlcyPStatFwdOutProfOcts  ,
      sapEgQosPlcyPStatFwdOutProfOctsL ,
      sapEgQosPlcyPStatFwdOutProfOctsH ,
      sapEgQosPlcyPStatDrpOutProfOcts  ,
      sapEgQosPlcyPStatDrpOutProfOctsL ,
      sapEgQosPlcyPStatDrpOutProfOctsH ,
      sapEgrQosArbitStatsFwdOcts, 
      sapEgrQosArbitStatsFwdOctsHi, 
      sapEgrQosArbitStatsFwdOctsLo, 
      sapEgrQosArbitStatsFwdPkts, 
      sapEgrQosArbitStatsFwdPktsHi, 
      sapEgrQosArbitStatsFwdPktsLo, 
      sapIngQosArbitStatsFwdOcts, 
      sapIngQosArbitStatsFwdOctsHi, 
      sapIngQosArbitStatsFwdOctsLo, 
      sapIngQosArbitStatsFwdPkts, 
      sapIngQosArbitStatsFwdPktsHi, 
      sapIngQosArbitStatsFwdPktsLo, 
      sapPortIdEgrQosArbitFwdOcts, 
      sapPortIdEgrQosArbitFwdOctsHi, 
      sapPortIdEgrQosArbitFwdOctsLo, 
      sapPortIdEgrQosArbitFwdPkts, 
      sapPortIdEgrQosArbitFwdPktsHi, 
      sapPortIdEgrQosArbitFwdPktsLo, 
      sapPortIdIngQosArbitFwdOcts, 
      sapPortIdIngQosArbitFwdOctsHi, 
      sapPortIdIngQosArbitFwdOctsLo, 
      sapPortIdIngQosArbitFwdPkts, 
      sapPortIdIngQosArbitFwdPktsHi, 
      sapPortIdIngQosArbitFwdPktsLo
    }
    STATUS      obsolete
    DESCRIPTION
        "The group of objects supporting management of SAP
         Ingress/Egress QoS capabilities on Nokia SROS series systems."
    ::= { tmnxSapGroups 140 }

tmnxSapMrpV8v0Group OBJECT-GROUP
    OBJECTS {
      sapTlsMrpRxPdus,
      sapTlsMrpDroppedPdus,
      sapTlsMrpTxPdus,
      sapTlsMrpRxNewEvent,
      sapTlsMrpRxJoinInEvent,
      sapTlsMrpRxInEvent,
      sapTlsMrpRxJoinEmptyEvent,
      sapTlsMrpRxEmptyEvent,
      sapTlsMrpRxLeaveEvent,
      sapTlsMrpTxNewEvent,
      sapTlsMrpTxJoinInEvent,
      sapTlsMrpTxInEvent,
      sapTlsMrpTxJoinEmptyEvent,
      sapTlsMrpTxEmptyEvent,
      sapTlsMrpTxLeaveEvent,
      sapTlsMmrpDeclared,
      sapTlsMmrpRegistered,
      sapTlsMmrpEndStation
      }
    STATUS      current
    DESCRIPTION
        "The group of objects supporting management of SAP
         MRP capabilities on release 8.0 of Nokia SROS series systems."
    ::= { tmnxSapGroups 141 }

tmnxSapMvrpV8v0Group OBJECT-GROUP
    OBJECTS {
       sapTmplLastChanged, 
       sapTmplRowStatus, 
       sapTmplSapCount, 
       sapTmplType, 
       sapTmplTblLastChanged,
       sapTmplTlsLastChanged, 
       sapTmplTlsMacAgeing, 
       sapTmplTlsTblLastChanged,
       sapTlsEsVidGrpEndVlanTag, 
       sapTlsEsVidGrpLastChgd, 
       sapTlsEsVidGrpRowStatus, 
       sapTlsEsVidGrpStartVlanTag, 
       sapTlsEsVidGrpTblLastChanged,
       sapTmplUsed,
       sapTmplUserCreationOrigin,
       sapTmplUserCreatorSvcId,
       sapTmplCollectAcctStats, 
       sapTmplEgrPolicerPolicy, 
       sapTmplEgressAggRateLimit, 
       sapTmplEgressFrameBasedAcctg, 
       sapTmplEgressIpFilterId, 
       sapTmplEgressIpv6FilterId, 
       sapTmplEgressMacFilterId, 
       sapTmplEgressQinQMarkTopOnly, 
       sapTmplEgressQosPolicyId, 
       sapTmplEgressQosSchedulerPolicy, 
       sapTmplIngPolicerPolicy, 
       sapTmplIngUseMultipointShared, 
       sapTmplIngressAggRateLimit, 
       sapTmplIngressIpFilterId, 
       sapTmplIngressIpv6FilterId, 
       sapTmplIngressMacFilterId, 
       sapTmplIngressMatchQinQDot1PBits, 
       sapTmplIngressQosPolicyId, 
       sapTmplIngressQosSchedulerPolicy, 
       sapTmplIngressSharedQueuePolicy, 
       sapTmplTlsBpduTranslation, 
       sapTmplTlsDiscardUnknownSource, 
       sapTmplTlsL2ptProtocols, 
       sapTmplTlsL2ptTermination, 
       sapTmplTlsLimitMacMove, 
       sapTmplTlsLimitMacMoveLevel, 
       sapTmplTlsMacAddressLimit, 
       sapTmplTlsMacLearning, 
       sapTmplTlsStpAdminPointToPoint, 
       sapTmplTlsStpAdminStatus, 
       sapTmplTlsStpAutoEdge, 
       sapTmplTlsStpBpduEncap, 
       sapTmplTlsStpPathCost, 
       sapTmplTlsStpPriority, 
       sapTmplTlsStpRapidStart, 
       sapTmplTlsStpRootGuard,
       sapTmplDot1agCfmMip,
       sapTmplCpmProtPolicyId,
       sapTmplCpmProtMonitorMac,
       sapTlsDataSapInstStatus,
       sapTlsDataSapInstLastErr,
       sapTlsMvrpDeclared, 
       sapTlsMvrpEndStation, 
       sapTlsMvrpRegistered,
       sapTlsMvrpAdminStatus,
       sapTlsMvrpOperStatus,
       sapTlsInTcBitBpdus,
       sapTlsOutTcBitBpdus
    }
    STATUS      obsolete
    DESCRIPTION
        "The group of objects supporting management of SAP MVRP
         capabilities on release 8.0R4 of Nokia SROS series systems."
    ::= { tmnxSapGroups 142 }

tmnxSapIpipeV8v0Group OBJECT-GROUP
    OBJECTS {
      sapIpipeCeInetAddress,
      sapIpipeCeInetAddressType,
      sapIpipeMacRefreshInterval,
      sapIpipeMacAddress,
      sapIpipeArpedMacAddress,
      sapIpipeArpedMacAddressTimeout,
      sapIpipeDiscoveredCeInetAddrType,
      sapIpipeDiscoveredCeInetAddr,
      sapIpipeUseBroadcastMac,
      sapIpipeUsingBroadcastMac,
      sapIpipeIpv6LinkLocalCeInetAddr,
      sapIpipeIpv6GlobalCeInetAddr,
      sapIpipeIpv6DiscoveredMacAddress
      }
    STATUS      current
    DESCRIPTION
        "The group of objects supporting management of SAP
         IPIPE capabilities on Nokia SROS series systems."
    ::= { tmnxSapGroups 143 }

tmnxSapEthRingGroup OBJECT-GROUP
    OBJECTS {
      sapEthRingIndex
      }
    STATUS      current
    DESCRIPTION
        "The group of objects supporting management of SAP
         ETH-RING capabilities on Nokia SROS systems."
    ::= { tmnxSapGroups 144 }

tmnxSapOverrideV8v0Group OBJECT-GROUP
    OBJECTS {
      sapIngQosQWeight,
      sapIngQosQCIRWeight, 
      sapEgrQosQWeight,
      sapEgrQosQCIRWeight
      }
    STATUS      current
    DESCRIPTION
        "The group of objects supporting management of SAP override
         capabilities on release 8.0R4 of Nokia SROS series systems."
    ::= { tmnxSapGroups 145 }

tmnxSapV9v0Group OBJECT-GROUP
    OBJECTS {
        sapOperGrp,
        sapMonitorOperGrp,
        sapIngressFlowspec,
        sapTlsPppMsapTrigger,
        sapTlsPppPolicy,
        sapTlsTrackSrrpInst,
        sapTlsPppUserDb,
        sapTlsPppoeUserDb,
        sapHostsAdminState
    }
    STATUS      current
    DESCRIPTION
        "The group of objects supporting management of SAP
         general capabilities on release 9.0 of Nokia SROS series systems."
    ::= { tmnxSapGroups 146 }

tmnxSapAtmV9v0Group OBJECT-GROUP
    OBJECTS {
        sapAtmSubPppIndex,
        sapAtmDetectedEncapsulation,
        sapAtmIngressTrafficDescIndexOvr,
        sapAtmEgressTrafficDescIndexOvr,
        sapAtmVcRangeRowStatus,      
        sapAtmVcRangeLastMgmtChange, 
        sapAtmVcRangeVpiStart,       
        sapAtmVcRangeVpiEnd,         
        sapAtmVcRangeVciStart,       
        sapAtmVcRangeVciEnd,
        sapAtmPppStatsRxPackets,
        sapAtmPppStatsRxDropped,
        sapAtmPppStatsTxPackets 
    }
    STATUS      current
    DESCRIPTION
        "The group of objects supporting management of SAP
         ATM capabilities that were added in release 9.0 
         of Nokia SROS series systems."
    ::= { tmnxSapGroups 147 }

tmnxSapEthCfmMonitorGroup OBJECT-GROUP
    OBJECTS {
      sapCpmProtEthCfmMonitorFlags,
      sapTmplCpmProtEthCfmMonitorFlags
    }
    STATUS      current
    DESCRIPTION
        "The group of objects supporting management of SAP Ethernet
         Connectivity Fault Management Monitoring capabilities on release
         8.0 R4 of Nokia SROS series systems."
    ::= { tmnxSapGroups 148 }

tmnxSapGreGroup OBJECT-GROUP
    OBJECTS {
       tmnxGreTunnelAdminState,  
       tmnxGreTunnelBackupRemIpAddr,  
       tmnxGreTunnelBackupRemIpAddrType,  
       tmnxGreTunnelOperRemIpAddr,  
       tmnxGreTunnelOperRemIpAddrType,  
       tmnxGreTunnelBytesRx,  
       tmnxGreTunnelBytesRxHi,  
       tmnxGreTunnelBytesRxLo,  
       tmnxGreTunnelBytesTx,  
       tmnxGreTunnelBytesTxHi,  
       tmnxGreTunnelBytesTxLo,  
       tmnxGreTunnelDeliverySvcId,  
       tmnxGreTunnelDescription,  
       tmnxGreTunnelDscp,  
       tmnxGreTunnelLastChanged,  
       tmnxGreTunnelDstIpAddr,  
       tmnxGreTunnelDstIpAddrType,  
       tmnxGreTunnelLclIpAddr,  
       tmnxGreTunnelLclIpAddrType,  
       tmnxGreTunnelOperFlags,  
       tmnxGreTunnelOperState,  
       tmnxGreTunnelPktsRx,  
       tmnxGreTunnelPktsRxHi,  
       tmnxGreTunnelPktsRxLo,  
       tmnxGreTunnelPktsTx,  
       tmnxGreTunnelPktsTxHi,  
       tmnxGreTunnelPktsTxLo,  
       tmnxGreTunnelRemIpAddr,  
       tmnxGreTunnelRemIpAddrType,  
       tmnxGreTunnelRowStatus,  
       tmnxGreTunnelRxErrors,  
       tmnxGreTunnelTableLastChanged,  
       tmnxGreTunnelTxErrors,
       tmnxGreTunnelInvalidChksumRx, 
       tmnxGreTunnelInvalidChksumRxHi, 
       tmnxGreTunnelInvalidChksumRxLo, 
       tmnxGreTunnelKeyIgnoredRx, 
       tmnxGreTunnelKeyIgnoredRxHi, 
       tmnxGreTunnelKeyIgnoredRxLo, 
       tmnxGreTunnelLoopsRx, 
       tmnxGreTunnelLoopsRxHi, 
       tmnxGreTunnelLoopsRxLo, 
       tmnxGreTunnelSeqIgnoredRx, 
       tmnxGreTunnelSeqIgnoredRxHi, 
       tmnxGreTunnelSeqIgnoredRxLo, 
       tmnxGreTunnelTooBigTx, 
       tmnxGreTunnelTooBigTxHi, 
       tmnxGreTunnelTooBigTxLo, 
       tmnxGreTunnelVersUnsupRx, 
       tmnxGreTunnelVersUnsupRxHi, 
       tmnxGreTunnelVersUnsupRxLo,
       tmnxSapGreTunnelCount
    }
    STATUS      obsolete
    DESCRIPTION
        "The group of objects supporting management of SAP GRE specific
         capabilities on Nokia SROS series systems."
    ::= { tmnxSapGroups 149 }

tmnxSapIgmpTrkV8v0Group OBJECT-GROUP
    OBJECTS {
        sapIgmpTrkDisRtrAlertChk
      }
    STATUS      current
    DESCRIPTION
        "The group of objects supporting management of
         IGMP host tracking capabilities for SAP's on release 8.0 
         Nokia SROS series systems."
    ::= { tmnxSapGroups 150 }

tmnxSapBsxV9v0Group OBJECT-GROUP
    OBJECTS {
      sapTransitIpPolicyId,
      sapTransitPrefixPolicyId
      }
    STATUS      current
    DESCRIPTION
        "The group of objects supporting management of BSX (Application
         Assurance) SAP capabilities on Nokia SROS series systems
         in release 9.0"
    ::= { tmnxSapGroups 151 }

tmnxSapMsapV9v0Group OBJECT-GROUP
    OBJECTS {
      msapAtmPlcyLastChanged,
      msapAtmPlcyIngTrafficDescIndex,
      msapAtmPlcyEgrTrafficDescIndex,
      msapAtmPlcyOamAlarmCellHandling,
      msapAtmPlcyOamPeriodicLoopback,
      msapAtmPlcyTblLastChgd
    }
    STATUS      current
    DESCRIPTION
        "The group of objects supporting management of
         managed SAP capabilities on Nokia SROS series systems
         added in release 9.0."
    ::= { tmnxSapGroups 152 }

tmnxSapOverrideV9v0Group OBJECT-GROUP
    OBJECTS {
      sapIngQosQAdminPIRPercent,
      sapIngQosQAdminCIRPercent, 
      sapEgrQosQAdminPIRPercent,
      sapEgrQosQAdminCIRPercent
      }
    STATUS      current
    DESCRIPTION
        "The group of objects supporting management of SAP override
         capabilities on Nokia SROS series systems added in release 9.0."
    ::= { tmnxSapGroups 153 }

tmnxSapPlcrV9v0Group OBJECT-GROUP
    OBJECTS {
       sapEgrPlcrOvrAdminPIRPercent, 
       sapEgrPlcrOvrAdminCIRPercent,
       sapIngPlcrOvrAdminPIRPercent, 
       sapIngPlcrOvrAdminCIRPercent  
    }
    STATUS      current
    DESCRIPTION
        "The group of objects supporting management of SAP
         Policer on Nokia SROS series systems in release 9.0."
    ::= { tmnxSapGroups 154 }

tmnxSapEgrEncapGrpV9v0Group OBJECT-GROUP
    OBJECTS {
       sapEgrEncapGroupTblLastChgd,
       sapEgrEncapGroupRowStatus,
       sapEgrEncapGroupLastChanged,
       sapEgrEncapGroupType,
       sapEgrEncapGroupQosPerMember,
       sapEgrEncapGroupQosPolicyId,
       sapEgrEncapGroupSchedulerPolicy,
       sapEgrEncapGroupAggRateLimit,
       sapEgrEncapGrpFrameBasedAccnt,
       sapEgrEncapGrpMemActTblLastChgd,
       sapEgrEncapGroupBeginMember,
       sapEgrEncapGroupEndMember,
       sapEgrEncapGroupMemberAction,
       sapEgrEncapGrpRangeEndId,
       sapEgrEncapGrpMemberLastChanged,
       sapEgrEGBaseStLastClearedTime,
       sapEgrEGBaseStCustId,  
       sapEgrEGBaseStQcDpdInPfPkts, 
       sapEgrEGBaseStQcDpdInPfPkts,         
       sapEgrEGBaseStQcDpdInPfPktsL, 
       sapEgrEGBaseStQcDpdInPfPktsH, 
       sapEgrEGBaseStQcDpdInPfOcts,  
       sapEgrEGBaseStQcDpdInPfOctsL, 
       sapEgrEGBaseStQcDpdInPfOctsH, 
       sapEgrEGBaseStQcDpdOutPfPkts, 
       sapEgrEGBaseStQcDpdOutPfPktsL,
       sapEgrEGBaseStQcDpdOutPfPktsH,
       sapEgrEGBaseStQcDpdOutPfOcts, 
       sapEgrEGBaseStQcDpdOutPfOctsL,
       sapEgrEGBaseStQcDpdOutPfOctsH,
       sapEgrEGBaseStQcFwdInPfPkts,  
       sapEgrEGBaseStQcFwdInPfPktsL, 
       sapEgrEGBaseStQcFwdInPfPktsH, 
       sapEgrEGBaseStQcFwdInPfOcts,  
       sapEgrEGBaseStQcFwdInPfOctsL, 
       sapEgrEGBaseStQcFwdInPfOctsH, 
       sapEgrEGBaseStQcFwdOutPfPkts, 
       sapEgrEGBaseStQcFwdOutPfPktsL,
       sapEgrEGBaseStQcFwdOutPfPktsH,
       sapEgrEGBaseStQcFwdOutPfOcts, 
       sapEgrEGBaseStQcFwdOutPfOctsL,
       sapEgrEGBaseStQcFwdOutPfOctsH,
       sapEgrEGMbrBaseStQcDpdInPfPkts,  
       sapEgrEGMbrBaseStQcDpdInPfPktsL, 
       sapEgrEGMbrBaseStQcDpdInPfPktsH, 
       sapEgrEGMbrBaseStQcDpdInPfOcts,  
       sapEgrEGMbrBaseStQcDpdInPfOctsL, 
       sapEgrEGMbrBaseStQcDpdInPfOctsH, 
       sapEgrEGMbrBaseStQcDpdOutPfPkts, 
       sapEgrEGMbrBaseStQcDpdOutPfPktsL,
       sapEgrEGMbrBaseStQcDpdOutPfPktsH,
       sapEgrEGMbrBaseStQcDpdOutPfOcts, 
       sapEgrEGMbrBaseStQcDpdOutPfOctsL,
       sapEgrEGMbrBaseStQcDpdOutPfOctsH,
       sapEgrEGMbrBaseStQcFwdInPfPkts,  
       sapEgrEGMbrBaseStQcFwdInPfPktsL, 
       sapEgrEGMbrBaseStQcFwdInPfPktsH,
       sapEgrEGMbrBaseStQcFwdInPfOcts,  
       sapEgrEGMbrBaseStQcFwdInPfOctsL, 
       sapEgrEGMbrBaseStQcFwdInPfOctsH, 
       sapEgrEGMbrBaseStQcFwdOutPfPkts, 
       sapEgrEGMbrBaseStQcFwdOutPfPktsL,
       sapEgrEGMbrBaseStQcFwdOutPfPktsH,
       sapEgrEGMbrBaseStQcFwdOutPfOcts, 
       sapEgrEGMbrBaseStQcFwdOutPfOctsL,
       sapEgrEGMbrBaseStQcFwdOutPfOctsH,
       sapEgrEGMbrBaseStLstClearedTime, 
       sapEgrEGMbrBaseStCustId,     
       sapEgrEGQueueStFwdInPfPkts,  
       sapEgrEGQueueStFwdInPfPktsL, 
       sapEgrEGQueueStFwdInPfPktsH, 
       sapEgrEGQueueStDpdInPfPkts,  
       sapEgrEGQueueStDpdInPfPktsL, 
       sapEgrEGQueueStDpdInPfPktsH, 
       sapEgrEGQueueStFwdOutPfPkts, 
       sapEgrEGQueueStFwdOutPfPktsL,
       sapEgrEGQueueStFwdOutPfPktsH,
       sapEgrEGQueueStDpdOutPfPkts, 
       sapEgrEGQueueStDpdOutPfPktsL,
       sapEgrEGQueueStDpdOutPfPktsH,
       sapEgrEGQueueStFwdInPfOcts,  
       sapEgrEGQueueStFwdInPfOctsL, 
       sapEgrEGQueueStFwdInPfOctsH, 
       sapEgrEGQueueStDpdInPfOcts,  
       sapEgrEGQueueStDpdInPfOctsL, 
       sapEgrEGQueueStDpdInPfOctsH, 
       sapEgrEGQueueStFwdOutPfOcts, 
       sapEgrEGQueueStFwdOutPfOctsL,
       sapEgrEGQueueStFwdOutPfOctsH,
       sapEgrEGQueueStDpdOutPfOcts, 
       sapEgrEGQueueStDpdOutPfOctsL,
       sapEgrEGQueueStDpdOutPfOctsH,
       sapEgrEGCustId,   
       sapEgrEGMbrQueueStFwdInPfPkts,   
       sapEgrEGMbrQueueStFwdInPfPktsL,  
       sapEgrEGMbrQueueStFwdInPfPktsH,  
       sapEgrEGMbrQueueStDpdInPfPkts,   
       sapEgrEGMbrQueueStDpdInPfPktsL,  
       sapEgrEGMbrQueueStDpdInPfPktsH,  
       sapEgrEGMbrQueueStFwdOutPfPkts,  
       sapEgrEGMbrQueueStFwdOutPfPktsL, 
       sapEgrEGMbrQueueStFwdOutPfPktsH, 
       sapEgrEGMbrQueueStDpdOutPfPkts,  
       sapEgrEGMbrQueueStDpdOutPfPktsL, 
       sapEgrEGMbrQueueStDpdOutPfPktsH, 
       sapEgrEGMbrQueueStFwdInPfOcts,   
       sapEgrEGMbrQueueStFwdInPfOctsL,  
       sapEgrEGMbrQueueStFwdInPfOctsH,  
       sapEgrEGMbrQueueStDpdInPfOcts,  
       sapEgrEGMbrQueueStDpdInPfOctsL,  
       sapEgrEGMbrQueueStDpdInPfOctsH,  
       sapEgrEGMbrQueueStFwdOutPfOcts,  
       sapEgrEGMbrQueueStFwdOutPfOctsL, 
       sapEgrEGMbrQueueStFwdOutPfOctsH, 
       sapEgrEGMbrQueueStDpdOutPfOcts,  
       sapEgrEGMbrQueueStDpdOutPfOctsL, 
       sapEgrEGMbrQueueStDpdOutPfOctsH, 
       sapEgrEGMbrQueueCustId,           
       sapEgrEGSchedStFwdPkts,  
       sapEgrEGSchedStFwdPktsL, 
       sapEgrEGSchedStFwdPktsH, 
       sapEgrEGSchedStFwdOcts, 
       sapEgrEGSchedStFwdOctsL, 
       sapEgrEGSchedStFwdOctsH, 
       sapEgrEGSchedCustId,      
       sapEgrEGMbrSchedStFwdPkts, 
       sapEgrEGMbrSchedStFwdPktsL,
       sapEgrEGMbrSchedStFwdPktsH,
       sapEgrEGMbrSchedStFwdOcts, 
       sapEgrEGMbrSchedStFwdOctsL,
       sapEgrEGMbrSchedStFwdOctsH,
       sapEgrEGMbrSchedCustId,     
       sapPortIdEgrEGSchedFwdPkts,  
       sapPortIdEgrEGSchedFwdPktsL, 
       sapPortIdEgrEGSchedFwdPktsH, 
       sapPortIdEgrEGSchedFwdOcts,  
       sapPortIdEgrEGSchedFwdOctsL, 
       sapPortIdEgrEGSchedFwdOctsH, 
       sapPortIdEgrEGSchedCustId, 
       sapPortIdEgrEGMbrSchedFwdPkts,  
       sapPortIdEgrEGMbrSchedFwdPktsL, 
       sapPortIdEgrEGMbrSchedFwdPktsH, 
       sapPortIdEgrEGMbrSchedFwdOcts,  
       sapPortIdEgrEGMbrSchedFwdOctsL, 
       sapPortIdEgrEGMbrSchedFwdOctsH, 
       sapPortIdEgrEGMbrSchedCustId
       }
    STATUS      obsolete
    DESCRIPTION
        "The group of objects supporting management of SAP
         encapsulation group on Nokia SROS series systems in 
         release 9.0."
    ::= { tmnxSapGroups 155 }

tmnxSapStaticHostV9v0Group OBJECT-GROUP
    OBJECTS {
      sapStaticHostRowStatus,
      sapStaticHostSubscrIdent,
      sapStaticHostSubProfile,
      sapStaticHostSlaProfile,
      sapStaticHostShcvOperState,
      sapStaticHostShcvChecks,
      sapStaticHostShcvReplies,
      sapStaticHostShcvReplyTime,
      sapStaticHostDynMacAddress,
      sapStaticHostRetailerSvcId,
      sapStaticHostRetailerIf,
      sapStaticHostFwdingState,
      sapStaticHostAncpString,
      sapStaticHostSubIdIsSapId,
      sapStaticHostIntermediateDestId,
      sapStaticHostAdminStatus,
      sapStaticHostMRtTblLastChgd,
      sapStaticHostMRtRowStatus,
      sapStaticHostMRtLastMgmtChange,
      sapStaticHostMRtStatus
      }
    STATUS      current
    DESCRIPTION
        "The group of objects supporting management of SAP
         static host capabilities on Nokia SROS series systems."
    ::= { tmnxSapGroups 156 }

tmnxSapSubMgmtV9v0Group OBJECT-GROUP
    OBJECTS {
      sapSubMgmtAdminStatus,
      sapSubMgmtDefSubProfile,
      sapSubMgmtDefSlaProfile,
      sapSubMgmtSubIdentPolicy,
      sapSubMgmtSubscriberLimit,
      sapSubMgmtProfiledTrafficOnly,
      sapSubMgmtNonSubTrafficSubIdent,
      sapSubMgmtNonSubTrafficSubProf,
      sapSubMgmtNonSubTrafficSlaProf,
      sapSubMgmtMacDaHashing,
      sapSubMgmtDefSubIdent,
      sapSubMgmtDefSubIdentString,
      sapSubMgmtDefInterDestId,
      sapSubMgmtDefInterDestIdString
      }
    STATUS      current
    DESCRIPTION
        "The group of objects supporting management of SAP
         Sub-management capabilities on Nokia SROS series 9.x systems."
    ::= { tmnxSapGroups 157 }

tmnxSapHsmdaV9v0Group OBJECT-GROUP
    OBJECTS {
        sapEgrQosHsmdaQueueMBS,
        sapEgrQosHsmdaQueueWrrWeight,
        sapEgressHsmdaWrrPolicyOvr
    }
    STATUS      current
    DESCRIPTION
        "The group of objects supporting management of SAP Egress QOS Hsmda
         capabilities on Nokia SROS series systems release 9.0."
    ::= { tmnxSapGroups 158 }

tmnxSapDefHostV9v0Group OBJECT-GROUP
    OBJECTS {
        sapDefHostTableLastChanged,
        sapDefHostLastChanged,
        sapDefHostRowStatus,
        sapDefHostNextHopIpv4Addr
      }
    STATUS      current
    DESCRIPTION
        "The group of objects supporting management of Default Host SAP
         capabilities on Nokia SROS series 9.x systems."
    ::= { tmnxSapGroups 159 }

tmnxSapFilterProfileV9v0Group OBJECT-GROUP
    OBJECTS {
      sapStaticHostFilterProfile,
      sapSubMgmtDefFilterProfile,
      msapPlcySubMgmtDefFilterProfile
    }
    STATUS      current
    DESCRIPTION
        "The group of objects supporting management of SAP
         Filter Profiles on Nokia SROS series systems."
    ::= { tmnxSapGroups 160 }

tmnxSapV10v0Group OBJECT-GROUP
    OBJECTS {
        sapSiteName,
        sapTlsDhcpUserDb,
        sapHostLockoutPolicy,
        sapTlsAutoLearnMacProtect,
        tmnxGreTunnelReassembly,
        tmnxGreTunnelClearDfBit, 
        tmnxGreTunnelIpMtu, 
        sapIngressFPQGrp,
        sapIngressFPQGrpInstanceId,
        sapIpv6HostInfoIpoeSLAACHosts
    }
    STATUS      obsolete
    DESCRIPTION
        "The group of objects supporting management of SAP
         general capabilities on release 10.0 of Nokia SROS
         series systems."
    ::= { tmnxSapGroups 161 }

tmnxSapBsxV10v0Group OBJECT-GROUP
    OBJECTS {
        sapAarpId,
        sapAarpServRefType 
    }
    STATUS      current
    DESCRIPTION
        "The group of objects supporting management of BSX (Application
         Assurance) SAP capabilities on Nokia SROS series systems
         in release 10.0"
    ::= { tmnxSapGroups 162 }

tmnxSapIgmpTrkV11v0Group OBJECT-GROUP
    OBJECTS {
        sapIgmpTrkMaxNbrGrpSrcs
      }
    STATUS      current
    DESCRIPTION
        "The group of objects supporting management of
         IGMP host tracking capabilities for SAP's on release 11.0 
         Nokia SROS series systems."
    ::= { tmnxSapGroups 163 }

tmnxSapMsapV11v0Group OBJECT-GROUP
    OBJECTS {
      msapPlcyIgmpTrkMaxNbrGrpSrcs
    }
    STATUS      current
    DESCRIPTION
        "The group of objects supporting management of
         managed SAP capabilities on Nokia SROS series systems
         added in release 11.0."
    ::= { tmnxSapGroups 164 }

tmnxSapDhcpV11v0Group OBJECT-GROUP
    OBJECTS {
        sapTlsDhcpStatsClntProxUDBPckts
    }
    STATUS      current
    DESCRIPTION
        "The group of objects supporting management of SAP
         TLS DHCP capabilities on Nokia SROS series systems
         added in release 11.0."
    ::= { tmnxSapGroups 165 }
    
tmnxSapStaticHostV11v0Group OBJECT-GROUP
    OBJECTS {
        sapStaticHostAdminRetailSvcId
      }
    STATUS      current
    DESCRIPTION
        "The group of objects supporting management of SAP
         static host capabilities on Nokia SROS series systems
         added in release 11.0."
    ::= { tmnxSapGroups 166 }

-- Notification objects

tmnxSapNotificationObjV6v0Group OBJECT-GROUP
    OBJECTS {
      sapNotifyPortId,
      svcManagedSapCreationError,
      msapStatus
    }
    STATUS      obsolete
    DESCRIPTION
        "The group of objects supporting management of notifications
         on Nokia SROS series systems."
    ::= { tmnxSapGroups 200 }

tmnxSapNotificationObjV7v0Group OBJECT-GROUP
    OBJECTS {
      sapNotifyPortId,
      svcManagedSapCreationError,
      msapStatus,
      sapTlsNotifyMacAddr,
      sapBGPPeeringHostIpAddr,
      sapBGPPeeringHostIpAddrType,
      sapBGPPeeringAttrDiscarded,
      sapBGPPeeringNotifDescription,
      sapBGPPeeringVRtrID,
      sapNotifyEncapValue
    }
    STATUS      current
    DESCRIPTION
        "The group of objects supporting management of notifications
         on Nokia SROS series systems."
    ::= { tmnxSapGroups 201 }

tmnxSapNotifyObjsV8v0R5Group OBJECT-GROUP
    OBJECTS {
      sapTunnelNotifyName,
      sapTunnelNotifyReason,
      sapTunnelNotifyState
    }
    STATUS      current
    DESCRIPTION
        "The group of objects supporting management of notifications
         on Nokia SROS series systems."
    ::= { tmnxSapGroups 202 }

tmnxSapNotificationObjV9v0Group OBJECT-GROUP
    OBJECTS {
      sapNotifyReason,
      sapNotifyName,
      sapPppNcpFailureProtocol
    }
    STATUS      current
    DESCRIPTION
        "The group of notification objects added in release 9.0
         of Nokia SROS."
    ::= { tmnxSapGroups 203 }

tmnxSapIpipeNotifyObjsGroup OBJECT-GROUP
    OBJECTS {
      sapIpipeCeIpAddrType,
      sapIpipeCeIpAddress
    }
    STATUS      current
    DESCRIPTION
        "The group of objects supporting management of notifications
         for Ipipes on Nokia SROS series systems."
    ::= { tmnxSapGroups 204 }
    
tmnxSapRipNotifyObjsGroup OBJECT-GROUP
    OBJECTS {
      sapRipListenerHostIpAddr,
      sapRipListenerHostIpAddrType,
      sapRipListenerVRtrID,
      sapRipListenerNotifDescription
    }
    STATUS      current
    DESCRIPTION
        "The group of objects supporting management of notifications
         for RIP listener on Nokia SROS series systems."
    ::= { tmnxSapGroups 205 }

tmnxSapDefHostV14v0Group OBJECT-GROUP
    OBJECTS {
        sapDefHostExTableLastChanged     ,
        sapDefHostExRowStatus            ,
        sapDefHostExLastChanged          ,
        sapDefHostExNextHopAddrType      ,
        sapDefHostExNextHopAddr          
      }
    STATUS      current
    DESCRIPTION
        "The group of objects supporting management of Default Host SAP
         capabilities on Nokia SROS series 14.x systems."
    ::= { tmnxSapGroups 206 }

-- Obsoleted Group
tmnxSapObsoletedV6v0Group OBJECT-GROUP
    OBJECTS {
      sapTlsDhcpSnooping,
      sapTlsDhcpLseStateRemainLseTime,
      sapTlsDhcpLseStateOption82,
      sapTlsDhcpLseStatePersistKey
    }
    STATUS      obsolete
    DESCRIPTION
        "The group of obsolete objects for the services feature
         on Nokia SROS series systems."
    ::= { tmnxSapGroups 300 }

tmnxSapObsoletedV7v0Group OBJECT-GROUP
    OBJECTS {
      sapTlsDhcpSnooping,
      sapTlsDhcpLseStateRemainLseTime,
      sapTlsDhcpLseStateOption82,
      sapTlsDhcpLseStatePersistKey,
      sapAntiSpoofIpAddress,
      sapAntiSpoofMacAddress
    }
    STATUS      current
    DESCRIPTION
        "The group of obsolete objects on Nokia SROS series
         systems."
    ::= { tmnxSapGroups 301 }

tmnxSapObsoletedV8v0Group OBJECT-GROUP
    OBJECTS {
      sapIngQosQMBS,
      sapEgrQosQMBS
    }
    STATUS      current
    DESCRIPTION
        "The group of obsolete objects on Nokia SROS series
         systems."
    ::= { tmnxSapGroups 302 }

-- NOTIFICATION Group
tmnxSapNotifyGroup NOTIFICATION-GROUP
    NOTIFICATIONS   {
      sapStatusChanged,
      sapTlsMacAddrLimitAlarmRaised,
      sapTlsMacAddrLimitAlarmCleared,
      sapDHCPLeaseEntriesExceeded,
      sapDHCPLseStateOverride,
      sapDHCPSuspiciousPcktRcvd,
      sapDHCPLseStatePopulateErr,
      hostConnectivityLost,
      hostConnectivityRestored,
      sapReceivedProtSrcMac,
      sapStaticHostDynMacConflict,
      sapTlsMacMoveExceeded,
      sapDHCPProxyServerError,
      sapPortStateChangeProcessed,
      sapDHCPLseStateMobilityError,
      msapStateChanged,
      msapCreationFailure,
      topologyChangeSapMajorState,
      newRootSap,
      topologyChangeSapState,
      receivedTCN,
      higherPriorityBridge,
      sapEncapPVST,
      sapEncapDot1d,
      sapActiveProtocolChange,
      tmnxStpRootGuardViolation,
      tmnxSapStpExcepCondStateChng,
      sapHostBGPPeeringSetupFailed
    }
    STATUS      current
    DESCRIPTION
        "The group of notifications for the Sap feature
         on Nokia SROS series systems."
    ::= { tmnxSapGroups 400 }

tmnxSapCemNotificationV6v0Group NOTIFICATION-GROUP
    NOTIFICATIONS   {
        sapCemPacketDefectAlarm,
        sapCemPacketDefectAlarmClear
    }
    STATUS      current
    DESCRIPTION
        "The group of notifications supporting the CEM Sap feature
         on Nokia 7710 SR series systems."
    ::= { tmnxSapGroups 401 }

tmnxSapObsoletedNotifyGroup NOTIFICATION-GROUP
    NOTIFICATIONS   {
      sapCreated,
      sapDeleted,
      sapTlsDHCPLseStEntriesExceeded,
      sapTlsDHCPLeaseStateOverride,
      sapTlsDHCPSuspiciousPcktRcvd,
      sapDHCPCoAError,
      sapDHCPSubAuthError,
      bridgedTLS,
      sapReceiveOwnBpdu
    }
    STATUS      current
    DESCRIPTION
        "The group of obsolete notifications for the Sap feature
         on Nokia SROS series systems."
    ::= { tmnxSapGroups 402 }

tmnxSapMvrpNotificationV8v0Group NOTIFICATION-GROUP
    NOTIFICATIONS   {
        sapTlsDataSapInstStatusChgd
    }
    STATUS      current
    DESCRIPTION
        "The group of notifications supporting the MVRP Sap feature
         on Nokia 7710 SR series systems."
    ::= { tmnxSapGroups 403 }

tmnxSapNotificationV8v0Group NOTIFICATION-GROUP
    NOTIFICATIONS   {
        tmnxGreTunnelOperRemIpChg,
        sapTunnelStateChange
    }
    STATUS      obsolete
    DESCRIPTION
        "The group of notifications supporting the additional SAP feature
         on Nokia SROS series systems."
    ::= { tmnxSapGroups 404 }

tmnxSapEthCfmGroup OBJECT-GROUP
    OBJECTS {
        sapEthCfmTblLastChanged,
        sapEthCfmRowLastChanged,
        sapEthCfmTunnelFaultNotification,
        sapEthCfmMcLagPropHoldTimeRemain,
        sapEthCfmAisEnable,
        sapEthCfmVMepFilter
    }
    STATUS      current
    DESCRIPTION
        "The group of objects supporting Ethernet Connectivity Fault Management
         (CFM) for the SAP feature on Nokia SROS series systems for
         release 9.0."
    ::= { tmnxSapGroups 405 }

tmnxSapNotificationV9v0Group NOTIFICATION-GROUP
    NOTIFICATIONS   {
        sapAtmPppSessionFailure,
        sapAtmPppNcpFailure
    }
    STATUS      current
    DESCRIPTION
    "The group of SAP notifications added in release 9.0 of 
     Nokia SROS series system."
    ::= { tmnxSapGroups 406 }

tmnxSapIpipeNotificationGroup NOTIFICATION-GROUP
    NOTIFICATIONS   {
        sapIpipeCeIpAddrChange
    }
    STATUS      current
    DESCRIPTION
    "The group of Ipipe SAP notifications for added in the 
     Nokia SROS series system."
    ::= { tmnxSapGroups 407 }

tmnxSapSpbGroup OBJECT-GROUP
    OBJECTS {
       sapTlsSpbAdminState,
       sapTlsSpbIfIndex, 
       sapTlsSpbLastChgd, 
       sapTlsSpbRowStatus, 
       sapTlsSpbTblLastChanged
    }
    STATUS      current
    DESCRIPTION
        "The group of objects supporting Shortest Path Bridging
         (SPB) for the SAP feature on Nokia SROS series systems."
    ::= { tmnxSapGroups 408 }

tmnxSapMonitorIPGroup OBJECT-GROUP
    OBJECTS {
        sapCpmProtMonitorIP
    }
    STATUS      current
    DESCRIPTION
        "The group of objects supporting per-source, per-SAP IP monitoring on
         Nokia SROS series release 9.0 systems."
    ::= { tmnxSapGroups 409 }

tmnxSapV11v0Group OBJECT-GROUP
    OBJECTS {
        sapSiteName,
        sapTlsDhcpUserDb,
        sapHostLockoutPolicy,
        sapTlsAutoLearnMacProtect,
        sapIngressFPQGrp,
        sapIngressFPQGrpInstanceId,
        sapIpv6HostInfoIpoeSLAACHosts,
        sapIgnoreOperDown,
        sapTlsDhcp6UserDb
    }
    STATUS      current
    DESCRIPTION
        "The group of objects supporting SAP feature on Nokia SROS
        series release 11.0 systems."
    ::= { tmnxSapGroups 410 }

tmnxSapIpTnlGroup OBJECT-GROUP
    OBJECTS {
       tmnxIpTnlDstAddrLastChanged, 
       tmnxIpTnlDstAddrRowStatus, 
       tmnxIpTnlDstAddrTableLastChanged, 
       tmnxIpTunnelAdminState, 
       tmnxIpTunnelBackupRemIpAddr, 
       tmnxIpTunnelBackupRemIpAddrType, 
       tmnxIpTunnelBytesRx, 
       tmnxIpTunnelBytesRxHi, 
       tmnxIpTunnelBytesRxLo, 
       tmnxIpTunnelBytesTx, 
       tmnxIpTunnelBytesTxHi, 
       tmnxIpTunnelBytesTxLo, 
       tmnxIpTunnelClearDfBit, 
       tmnxIpTunnelDeliverySvcId, 
       tmnxIpTunnelDescription, 
       tmnxIpTunnelDscp, 
       tmnxIpTunnelGreHeader, 
       tmnxIpTunnelInvalidChksumRx, 
       tmnxIpTunnelInvalidChksumRxHi, 
       tmnxIpTunnelInvalidChksumRxLo, 
       tmnxIpTunnelIpMtu, 
       tmnxIpTunnelKeyIgnoredRx, 
       tmnxIpTunnelKeyIgnoredRxHi, 
       tmnxIpTunnelKeyIgnoredRxLo, 
       tmnxIpTunnelLastChanged, 
       tmnxIpTunnelLclIpAddr, 
       tmnxIpTunnelLclIpAddrType, 
       tmnxIpTunnelLoopsRx, 
       tmnxIpTunnelLoopsRxHi, 
       tmnxIpTunnelLoopsRxLo, 
       tmnxIpTunnelOperFlags, 
       tmnxIpTunnelOperRemIpAddr, 
       tmnxIpTunnelOperRemIpAddrType, 
       tmnxIpTunnelOperState, 
       tmnxIpTunnelPktsRx, 
       tmnxIpTunnelPktsRxHi, 
       tmnxIpTunnelPktsRxLo, 
       tmnxIpTunnelPktsTx, 
       tmnxIpTunnelPktsTxHi, 
       tmnxIpTunnelPktsTxLo, 
       tmnxIpTunnelReassembly, 
       tmnxIpTunnelRemIpAddr, 
       tmnxIpTunnelRemIpAddrType, 
       tmnxIpTunnelRowStatus, 
       tmnxIpTunnelRxErrors, 
       tmnxIpTunnelSeqIgnoredRx, 
       tmnxIpTunnelSeqIgnoredRxHi, 
       tmnxIpTunnelSeqIgnoredRxLo, 
       tmnxIpTunnelTableLastChanged, 
       tmnxIpTunnelTooBigTx, 
       tmnxIpTunnelTooBigTxHi, 
       tmnxIpTunnelTooBigTxLo, 
       tmnxIpTunnelTxErrors, 
       tmnxIpTunnelVersUnsupRx, 
       tmnxIpTunnelVersUnsupRxHi, 
       tmnxIpTunnelVersUnsupRxLo,
       tmnxIpTunnelHostISA
    }
    STATUS      current
    DESCRIPTION
        "The group of objects supporting SAP IP Tunnel feature on Nokia
         SROS series release 10.0 systems."
    ::= { tmnxSapGroups 411 }

tmnxSapGreV10v0Group OBJECT-GROUP
    OBJECTS {
        tmnxGreTunnelHostISA
    }
    STATUS      obsolete
    DESCRIPTION
        "The group of additional objects supporting SAP feature on
        Nokia SROS series release 10.0 systems."
    ::= { tmnxSapGroups 412 }

tmnxSapNotificationV10v0Group NOTIFICATION-GROUP
    NOTIFICATIONS   {
        tmnxIpTunnelOperRemIpChg
    }
    STATUS      current
    DESCRIPTION
        "The group of notifications supporting the additional SAP feature
         on Nokia SROS series systems."
    ::= { tmnxSapGroups 413 }

tmnxSapHsmdaV10v0Group OBJECT-GROUP
    OBJECTS {
      sapEgressHsmdaShaperOverride,
      sapIngressHsmdaPacketOffOvr,
      sapEgressHsmdaPacketOffOverride,
      sapEgrQosHsmdaQueueRowStatus,
      sapEgrQosHsmdaQueueLastChanged,
      sapEgrQosHsmdaQueueAdminPIR,
      sapEgrQosHsmdaQueueAdminCIR,
      sapEgrQosHsmdaQueueSlopePolicy,
      sapEgrHsmdaQStatCustId,
      sapEgrHsmdaQStatInProfPktFwd,
      sapEgrHsmdaQStatInProfPktDropd,
      sapEgrHsmdaQStatOutProfPktFwd,
      sapEgrHsmdaQStatOutProfPktDropd,
      sapEgrHsmdaQStatInProfOctFwd,
      sapEgrHsmdaQStatInProfOctDropd,
      sapEgrHsmdaQStatOutProfOctFwd,
      sapEgrHsmdaQStatOutProfOctDropd,
      sapEgrHsmdaCntrStCustId,
      sapEgrHsmdaCntrStInProfPktFwd,
      sapEgrHsmdaCntrStInProfPktDrop,
      sapEgrHsmdaCntrStOutProfPktFwd,
      sapEgrHsmdaCntrStOutProfPktDrop,
      sapEgrHsmdaCntrStInProfOctFwd,
      sapEgrHsmdaCntrStInProfOctDrop,
      sapEgrHsmdaCntrStOutProfOctFwd,
      sapEgrHsmdaCntrStOutProfOctDrop
      }
    STATUS      current
    DESCRIPTION
        "The group of objects supporting management of SAP Ingress/Egress
         QoS Hsmda capabilities on Nokia SROS series systems in
         10.0 release."
    ::= { tmnxSapGroups 414 }

tmnxSapObsoletedV10v0Group OBJECT-GROUP
    OBJECTS {
        sapIngressAggRateLimit,
        sapIngressHsmdaPacketOffOvr,
        sapEgrQosHsmdaQueueAdminCIR,
        sapIngHsmdaQStatCustId,
        sapIngHsmdaQStatHiPktsDropped,
        sapIngHsmdaQStatLoPktsDropped,
        sapIngHsmdaQStatHiOctsDropped,
        sapIngHsmdaQStatLoOctsDropped,
        sapIngHsmdaQStatInProfPktsFwd,
        sapIngHsmdaQStatOutProfPktsFwd,
        sapIngHsmdaQStatInProfOctsFwd,
        sapIngHsmdaQStatOutProfOctsFwd,
        sapIngHsmdaQStatAllPktsOffered,
        sapIngHsmdaQStatAllOctsOffered,
        sapIngHsmdaCntrStCustId,
        sapIngHsmdaCntrStHiPktDrop,
        sapIngHsmdaCntrStLoPktDrop,
        sapIngHsmdaCntrStHiOctDrop,
        sapIngHsmdaCntrStLoOctDrop,
        sapIngHsmdaCntrStInProfPktFwd,
        sapIngHsmdaCntrStOutProfPktFwd,
        sapIngHsmdaCntrStInProfOctFwd,
        sapIngHsmdaCntrStOutProfOctFwd,
        sapIngHsmdaCntrStAllPktOffered,
        sapIngHsmdaCntrStAllOctOffered,
        sapIngQosHsmdaQueueRowStatus,
        sapIngQosHsmdaQueueLastChanged,
        sapIngQosHsmdaQueueAdminPIR,
        sapIngQosHsmdaQueueAdminCIR,
        sapIngQosHsmdaQueueSlopePolicy,
        sapTmplIngressAggRateLimit
    }
    STATUS      current
    DESCRIPTION
        "The group of obsolete objects on Nokia SROS series
         systems in 10.0 release."
    ::= { tmnxSapGroups 415 }

tmnxSapLagV11v0Group OBJECT-GROUP
    OBJECTS {
        sapLagLinkMapProfile,
        sapExtLastChanged,
        sapExtLagActivePort,
        sapExtTableLastChanged,
        msapPlcyLagLinkMapProfile
    }
    STATUS      current
    DESCRIPTION
        "The group of additional objects supporting SAP LAG feature on
        Nokia SROS series release 11.0 systems."
    ::= { tmnxSapGroups 416 }

tmnxSapMvrpV10v0Group OBJECT-GROUP
    OBJECTS {
       sapTmplLastChanged, 
       sapTmplRowStatus, 
       sapTmplSapCount, 
       sapTmplType, 
       sapTmplTblLastChanged,
       sapTmplTlsLastChanged, 
       sapTmplTlsMacAgeing, 
       sapTmplTlsTblLastChanged,
       sapTlsEsVidGrpEndVlanTag, 
       sapTlsEsVidGrpLastChgd, 
       sapTlsEsVidGrpRowStatus, 
       sapTlsEsVidGrpStartVlanTag, 
       sapTlsEsVidGrpTblLastChanged,
       sapTmplUsed,
       sapTmplUserCreationOrigin,
       sapTmplUserCreatorSvcId,
       sapTmplCollectAcctStats, 
       sapTmplEgrPolicerPolicy, 
       sapTmplEgressAggRateLimit, 
       sapTmplEgressFrameBasedAcctg, 
       sapTmplEgressIpFilterId, 
       sapTmplEgressIpv6FilterId, 
       sapTmplEgressMacFilterId, 
       sapTmplEgressQinQMarkTopOnly, 
       sapTmplEgressQosPolicyId, 
       sapTmplEgressQosSchedulerPolicy, 
       sapTmplIngPolicerPolicy, 
       sapTmplIngUseMultipointShared, 
       sapTmplIngressIpFilterId, 
       sapTmplIngressIpv6FilterId, 
       sapTmplIngressMacFilterId, 
       sapTmplIngressMatchQinQDot1PBits, 
       sapTmplIngressQosPolicyId, 
       sapTmplIngressQosSchedulerPolicy, 
       sapTmplIngressSharedQueuePolicy, 
       sapTmplTlsBpduTranslation, 
       sapTmplTlsDiscardUnknownSource, 
       sapTmplTlsL2ptProtocols, 
       sapTmplTlsL2ptTermination, 
       sapTmplTlsLimitMacMove, 
       sapTmplTlsLimitMacMoveLevel, 
       sapTmplTlsMacAddressLimit, 
       sapTmplTlsMacLearning, 
       sapTmplTlsStpAdminPointToPoint, 
       sapTmplTlsStpAdminStatus, 
       sapTmplTlsStpAutoEdge, 
       sapTmplTlsStpBpduEncap, 
       sapTmplTlsStpPathCost, 
       sapTmplTlsStpPriority, 
       sapTmplTlsStpRapidStart, 
       sapTmplTlsStpRootGuard,
       sapTmplDot1agCfmMip,
       sapTmplCpmProtPolicyId,
       sapTmplCpmProtMonitorMac,
       sapTlsDataSapInstStatus,
       sapTlsDataSapInstLastErr,
       sapTlsMvrpDeclared, 
       sapTlsMvrpEndStation, 
       sapTlsMvrpRegistered,
       sapTlsMvrpAdminStatus,
       sapTlsMvrpOperStatus,
       sapTlsInTcBitBpdus,
       sapTlsOutTcBitBpdus
    }
    STATUS      obsolete
    DESCRIPTION
        "The group of objects supporting management of SAP MVRP
         capabilities on release 10.0 of Nokia SROS series systems."
    ::= { tmnxSapGroups 417 }

tmnxSapFlowSPecV11v0Group OBJECT-GROUP
        OBJECTS {
            sapIngressFlowspec,
            sapIngressIPv6Flowspec
        }
        STATUS      current
        DESCRIPTION
            "The group of additional objects supporting SAP BGP Flow-Spec feature
             on Nokia SROS series release 11.0 systems."
        ::= { tmnxSapGroups 418 }

tmnxSapGreObsoletedGroup OBJECT-GROUP
    OBJECTS {
       tmnxGreTunnelAdminState,  
       tmnxGreTunnelBackupRemIpAddr,  
       tmnxGreTunnelBackupRemIpAddrType,  
       tmnxGreTunnelOperRemIpAddr,  
       tmnxGreTunnelOperRemIpAddrType,  
       tmnxGreTunnelBytesRx,  
       tmnxGreTunnelBytesRxHi,  
       tmnxGreTunnelBytesRxLo,  
       tmnxGreTunnelBytesTx,  
       tmnxGreTunnelBytesTxHi,  
       tmnxGreTunnelBytesTxLo,  
       tmnxGreTunnelDeliverySvcId,  
       tmnxGreTunnelDescription,  
       tmnxGreTunnelDscp,  
       tmnxGreTunnelLastChanged,  
       tmnxGreTunnelDstIpAddr,  
       tmnxGreTunnelDstIpAddrType,  
       tmnxGreTunnelLclIpAddr,  
       tmnxGreTunnelLclIpAddrType,  
       tmnxGreTunnelOperFlags,  
       tmnxGreTunnelOperState,  
       tmnxGreTunnelPktsRx,  
       tmnxGreTunnelPktsRxHi,  
       tmnxGreTunnelPktsRxLo,  
       tmnxGreTunnelPktsTx,  
       tmnxGreTunnelPktsTxHi,  
       tmnxGreTunnelPktsTxLo,  
       tmnxGreTunnelRemIpAddr,  
       tmnxGreTunnelRemIpAddrType,  
       tmnxGreTunnelRowStatus,  
       tmnxGreTunnelRxErrors,  
       tmnxGreTunnelTableLastChanged,  
       tmnxGreTunnelTxErrors,
       tmnxGreTunnelInvalidChksumRx, 
       tmnxGreTunnelInvalidChksumRxHi, 
       tmnxGreTunnelInvalidChksumRxLo, 
       tmnxGreTunnelKeyIgnoredRx, 
       tmnxGreTunnelKeyIgnoredRxHi, 
       tmnxGreTunnelKeyIgnoredRxLo, 
       tmnxGreTunnelLoopsRx, 
       tmnxGreTunnelLoopsRxHi, 
       tmnxGreTunnelLoopsRxLo, 
       tmnxGreTunnelSeqIgnoredRx, 
       tmnxGreTunnelSeqIgnoredRxHi, 
       tmnxGreTunnelSeqIgnoredRxLo, 
       tmnxGreTunnelTooBigTx, 
       tmnxGreTunnelTooBigTxHi, 
       tmnxGreTunnelTooBigTxLo, 
       tmnxGreTunnelVersUnsupRx, 
       tmnxGreTunnelVersUnsupRxHi, 
       tmnxGreTunnelVersUnsupRxLo,
       tmnxGreTunnelClearDfBit,
       tmnxGreTunnelHostISA,
       tmnxGreTunnelIpMtu,
       tmnxGreTunnelReassembly
    }
    STATUS      current
    DESCRIPTION
        "The group of obsoleted objects supporting management of SAP GRE
         specific capabilities on Nokia SROS series systems."
    ::= { tmnxSapGroups 419 }

tmnxSapGreV11v0Group OBJECT-GROUP
    OBJECTS {
       tmnxSapGreTunnelCount
    }
    STATUS      current
    DESCRIPTION
        "The group of objects supporting management of SAP GRE specific
         capabilities on Nokia SROS series systems."
    ::= { tmnxSapGroups 420 }

tmnxSapNotifObsoletedGroup NOTIFICATION-GROUP
    NOTIFICATIONS   {
        tmnxGreTunnelOperRemIpChg
    }
    STATUS      current
    DESCRIPTION
        "The group of obsoleted notifications supporting the additional SAP
         feature on Nokia SROS series systems."
    ::= { tmnxSapGroups 421 }

tmnxSapNotificationV11v0Group NOTIFICATION-GROUP
    NOTIFICATIONS   {
        sapTunnelStateChange,
        tmnxIpTunnelOperStateChange
    }
    STATUS      current
    DESCRIPTION
        "The group of notifications supporting additional SAP features
         on Nokia SROS series systems release 11.0."
    ::= { tmnxSapGroups 422 }

tmnxSapStatsV10v0Group OBJECT-GROUP
    OBJECTS {
        sapBaseStatsIngressCPMPackets,
        sapBaseStatsIngressCPMPacketsHi,
        sapBaseStatsIngressCPMPacketsLo,
        sapBaseStatsIngressCPMOctets,
        sapBaseStatsIngressCPMOctetsHi,
        sapBaseStatsIngressCPMOctetsLo
    }
    STATUS      current
    DESCRIPTION
        "The group of additional objects supporting SAP stats feature
         on Nokia SROS series release 10.0 systems."
    ::= { tmnxSapGroups 423 }

tmnxSapDCpuProtV11v0Group OBJECT-GROUP
    OBJECTS {
        sapDCpuProtPolicy,
        msapPlcyDCpuProtPolicy,
        sapDcpFpStaticState,
        sapDcpFpStaticExcdCount,
        sapDcpFpStaticExcdCountHi,
        sapDcpFpStaticExcdCountLo,
        sapDcpFpStaticHoldDown,
        sapDcpFpStaticDetectionTime,
        sapDcpFpDynState,
        sapDcpFpDynExcdCount,
        sapDcpFpDynExcdCountHi,
        sapDcpFpDynExcdCountLo,
        sapDcpFpDynHoldDown,
        sapDcpFpDynDetectionTime,
        sapDcpFpDynAllocated,
        sapDcpFpLocMonState,
        sapDcpFpLocMonExcdCount,
        sapDcpFpLocMonExcdCountHi,
        sapDcpFpLocMonExcdCountLo,
        sapDcpFpLocMonAllDynAlloc
    }
    STATUS      current
    DESCRIPTION
        "The group of additional objects supporting Distributed Cpu Protection
         feature for SAP on Nokia SROS series release 11.0 systems."
    ::= { tmnxSapGroups 424 }

tmnxSapEgrPortQGrpV11v0Group OBJECT-GROUP
    OBJECTS {
        sapEgressPortQGrp,
        sapEgressPortQGrpInstanceId
    }
    STATUS      current
    DESCRIPTION
        "The group of additional objects supporting egress port queue-group
         feature for SAP on Nokia SROS series release 11.0 systems."
    ::= { tmnxSapGroups 425 }

tmnxSapDcpNotifyObjsV11v0Group   OBJECT-GROUP
    OBJECTS {
        sapDcpTimeEventOccured
    }
    STATUS        current
    DESCRIPTION
        "The group of objects supporting management of Distributed CPU
         Protection feature for SAP on Nokia SROS series release 11.0
         systems."
    ::= { tmnxSapGroups 426 }

tmnxSapDcpNotifyV11v0Group    NOTIFICATION-GROUP
    NOTIFICATIONS {
        sapTlsMacMoveExceedNonBlock,
        sapDcpStaticExcd,
        sapDcpDynamicExcd,   
        sapDcpStaticHoldDownStart,
        sapDcpDynamicHoldDownStart,
        sapDcpStaticHoldDownEnd,
        sapDcpDynamicHoldDownEnd,
        sapDcpStaticConform,
        sapDcpDynamicConform,
        sapDcpLocMonExcd,
        sapDcpLocMonExcdDynResource,
        sapDcpLocMonExcdAllDynAlloc,
        sapDcpLocMonExcdAllDynFreed,
        sapDcpDynamicEnforceAlloc,
        sapDcpDynamicEnforceFreed
    }
    STATUS current
    DESCRIPTION
        "The group of notifications supporting management of Distributed CPU
         Protection feature for SAP on Nokia SROS series release 11.0
         systems."
    ::= { tmnxSapGroups 427 }

tmnxSapSchedulerRateV11v0Group OBJECT-GROUP
    OBJECTS {
        sapIngQosSPIRHi,
        sapIngQosSPIRLo,
        sapIngQosSCIRHi,
        sapIngQosSCIRLo,
        sapEgrQosSPIRHi,
        sapEgrQosSPIRLo,
        sapEgrQosSCIRHi,
        sapEgrQosSCIRLo
    }
    STATUS      current
    DESCRIPTION
        "The group of objects supporting management of Scheduler policies
         on Nokia SROS series systems release 11.0."
    ::= { tmnxSapGroups 428 } 

tmnxSapSpbV11v0Group OBJECT-GROUP
    OBJECTS {
        sapTlsStaticIsidStatus,
        sapTlsStaticIsidRngRowStatus,
        sapTlsStaticIsidRngLastChanged,
        sapTlsStaticIsidRngLow,
        sapTlsStaticIsidRngHigh
    }
    STATUS      current
    DESCRIPTION
        "The group of objects supporting management of SPB feature
         on Nokia SROS series systems release 11.0."
    ::= { tmnxSapGroups 429 } 

tmnxSapEthLoopbackV11v0Group     OBJECT-GROUP
    OBJECTS {
        sapEthLoopbackRowStatus,
        sapEthLoopbackMode,
        sapEthLoopbackMacSwap,
        sapEthLoopbackMacSwapAddr,
        sapEthLoopbackMacSwapAddrAll
    }
    STATUS      current
    DESCRIPTION
        "The group of objects supporting management of the SAP Ethernet
         Loopback feature on Nokia SROS series systems in release
         11.0."
    ::= { tmnxSapGroups 430 } 

tmnxSapEthLpbkNotifyV11v0Group   NOTIFICATION-GROUP
    NOTIFICATIONS {
        sapEthLoopbackStarted,
        sapEthLoopbackStopped
    }
    STATUS      current
    DESCRIPTION
        "The group of notifications supporting management of the SAP Ethernet
         Loopback feature on Nokia SROS series systems in release
         11.0."
    ::= { tmnxSapGroups 431 } 

tmnxSapQosV11v0Group OBJECT-GROUP
    OBJECTS {
      sapIngQosQueueId,
      sapIngQosQueueStatsOfferedHiPrioPackets,
      sapIngQosQueueStatsDroppedHiPrioPackets,
      sapIngQosQueueStatsOfferedLoPrioPackets,
      sapIngQosQueueStatsDroppedLoPrioPackets,
      sapIngQosQueueStatsOfferedHiPrioOctets,
      sapIngQosQueueStatsDroppedHiPrioOctets,
      sapIngQosQueueStatsOfferedLoPrioOctets,
      sapIngQosQueueStatsDroppedLoPrioOctets,
      sapIngQosQueueStatsForwardedInProfPackets,
      sapIngQosQueueStatsForwardedOutProfPackets,
      sapIngQosQueueStatsForwardedInProfOctets,
      sapIngQosQueueStatsForwardedOutProfOctets,
      sapIngQosCustId,
      sapIngQosQueueStatsUncoloredPacketsOffered,
      sapIngQosQueueStatsUncoloredOctetsOffered,
      sapEgrQosQueueId,
      sapEgrQosQueueStatsForwardedInProfPackets,
      sapEgrQosQueueStatsDroppedInProfPackets,
      sapEgrQosQueueStatsForwardedOutProfPackets,
      sapEgrQosQueueStatsDroppedOutProfPackets,
      sapEgrQosQueueStatsForwardedInProfOctets,
      sapEgrQosQueueStatsDroppedInProfOctets,
      sapEgrQosQueueStatsForwardedOutProfOctets,
      sapEgrQosQueueStatsDroppedOutProfOctets,
      sapEgrQosCustId,
      sapIngQosSchedStatsForwardedPackets,
      sapIngQosSchedStatsForwardedOctets,
      sapIngQosSchedCustId,
      sapEgrQosSchedStatsForwardedPackets,
      sapEgrQosSchedStatsForwardedOctets,
      sapEgrQosSchedCustId,
      sapIngQosQRowStatus,
      sapIngQosQLastMgmtChange,
      sapIngQosQOverrideFlags,
      sapIngQosQCBS,
      sapIngQosQHiPrioOnly,
      sapIngQosQCIRAdaptation,
      sapIngQosQPIRAdaptation,
      sapIngQosQAdminPIR,
      sapIngQosQAdminCIR,
      sapEgrQosQRowStatus,
      sapEgrQosQLastMgmtChange,
      sapEgrQosQOverrideFlags,
      sapEgrQosQCBS,
      sapEgrQosQHiPrioOnly,
      sapEgrQosQCIRAdaptation,
      sapEgrQosQPIRAdaptation,
      sapEgrQosQAdminPIR,
      sapEgrQosQAdminCIR,
      sapEgrQosQAvgOverhead,
      sapIngQosSRowStatus,
      sapIngQosSLastMgmtChange,
      sapIngQosSOverrideFlags,
      sapIngQosSSummedCIR,
      sapEgrQosSRowStatus,
      sapEgrQosSLastMgmtChange,
      sapEgrQosSOverrideFlags,
      sapEgrQosSSummedCIR,    
      sapIngQosPStatsCustId            ,
      sapIngQosPStatsMode              ,
      sapIngQosPStatsOffHiPrioPkts     ,
      sapIngQosPStatsOffHiPrioPktsLo   ,
      sapIngQosPStatsOffHiPrioPktsHi   ,
      sapIngQosPStatsDrpHiPrioPkts     ,
      sapIngQosPStatsDrpHiPrioPktsLo   ,
      sapIngQosPStatsDrpHiPrioPktsHi   ,
      sapIngQosPStatsOffLoPrioPkts     ,
      sapIngQosPStatsOffLoPrioPktsLo   ,
      sapIngQosPStatsOffLoPrioPktsHi   ,
      sapIngQosPStatsDrpLoPrioPkts     ,
      sapIngQosPStatsDrpLoPrioPktsLo   ,
      sapIngQosPStatsDrpLoPrioPktsHi   ,
      sapIngQosPStatsOffHiPrioOcts     ,
      sapIngQosPStatsOffHiPrioOctsLo   ,
      sapIngQosPStatsOffHiPrioOctsHi   ,
      sapIngQosPStatsDrpHiPrioOcts     ,
      sapIngQosPStatsDrpHiPrioOctsLo   ,
      sapIngQosPStatsDrpHiPrioOctsHi   ,
      sapIngQosPStatsOffLoPrioOcts     ,
      sapIngQosPStatsOffLoPrioOctsLo   ,
      sapIngQosPStatsOffLoPrioOctsHi   ,
      sapIngQosPStatsDrpLoPrioOcts     ,
      sapIngQosPStatsDrpLoPrioOctsLo   ,
      sapIngQosPStatsDrpLoPrioOctsHi   ,
      sapIngQosPStatsFwdInProfPkts     ,
      sapIngQosPStatsFwdInProfPktsLo   ,
      sapIngQosPStatsFwdInProfPktsHi   ,
      sapIngQosPStatsFwdOutProfPkts    ,
      sapIngQosPStatsFwdOutProfPktsLo  ,
      sapIngQosPStatsFwdOutProfPktsHi  ,
      sapIngQosPStatsFwdInProfOcts     ,
      sapIngQosPStatsFwdInProfOctsLo   ,
      sapIngQosPStatsFwdInProfOctsHi   ,
      sapIngQosPStatsFwdOutProfOcts    ,
      sapIngQosPStatsFwdOutProfOctsLo  ,
      sapIngQosPStatsFwdOutProfOctsHi  ,
      sapIngQosPStatsUncolPktsOff      ,
      sapIngQosPStatsUncolPktsOffLo    ,
      sapIngQosPStatsUncolPktsOffHi    ,
      sapIngQosPStatsUncolOctsOff      ,
      sapIngQosPStatsUncolOctsOffLo    ,
      sapIngQosPStatsUncolOctsOffHi    ,      
      sapEgrQosPStatsCustId            ,
      sapEgrQosPStatsMode              ,
      sapEgrQosPStatsOffInProfPkts     ,
      sapEgrQosPStatsOffInProfPktsLo   ,
      sapEgrQosPStatsOffInProfPktsHi   ,
      sapEgrQosPStatsFwdInProfPkts     ,
      sapEgrQosPStatsFwdInProfPktsLo   ,
      sapEgrQosPStatsFwdInProfPktsHi   ,
      sapEgrQosPStatsDrpInProfPkts     ,
      sapEgrQosPStatsDrpInProfPktsLo   ,
      sapEgrQosPStatsDrpInProfPktsHi   ,
      sapEgrQosPStatsOffOutProfPkts    ,
      sapEgrQosPStatsOffOutProfPktsLo  ,
      sapEgrQosPStatsOffOutProfPktsHi  ,
      sapEgrQosPStatsFwdOutProfPkts    ,
      sapEgrQosPStatsFwdOutProfPktsLo  ,
      sapEgrQosPStatsFwdOutProfPktsHi  ,
      sapEgrQosPStatsDrpOutProfPkts    ,
      sapEgrQosPStatsDrpOutProfPktsLo  ,
      sapEgrQosPStatsDrpOutProfPktsHi  ,
      sapEgrQosPStatsOffInProfOcts     ,
      sapEgrQosPStatsOffInProfOctsLo   ,
      sapEgrQosPStatsOffInProfOctsHi   ,
      sapEgrQosPStatsFwdInProfOcts     ,
      sapEgrQosPStatsFwdInProfOctsLo   ,
      sapEgrQosPStatsFwdInProfOctsHi   ,
      sapEgrQosPStatsDrpInProfOcts     ,
      sapEgrQosPStatsDrpInProfOctsLo   ,
      sapEgrQosPStatsDrpInProfOctsHi   ,
      sapEgrQosPStatsOffOutProfOcts    ,
      sapEgrQosPStatsOffOutProfOctsLo  ,
      sapEgrQosPStatsOffOutProfOctsHi  ,
      sapEgrQosPStatsFwdOutProfOcts    ,
      sapEgrQosPStatsFwdOutProfOctsLo  ,
      sapEgrQosPStatsFwdOutProfOctsHi  ,
      sapEgrQosPStatsDrpOutProfOcts    ,
      sapEgrQosPStatsDrpOutProfOctsLo  ,
      sapEgrQosPStatsDrpOutProfOctsHi  ,
      sapEgrQosPStatsUncolPktsOff      ,
      sapEgrQosPStatsUncolPktsOffLo    ,
      sapEgrQosPStatsUncolPktsOffHi    ,
      sapEgrQosPStatsUncolOctsOff      ,
      sapEgrQosPStatsUncolOctsOffLo    ,
      sapEgrQosPStatsUncolOctsOffHi    ,      
      sapIgQosPlcyPStatCustId          ,
      sapIgQosPlcyPStatMode            ,
      sapIgQosPlcyPStatOffHiPrioPkts   ,
      sapIgQosPlcyPStatDrpHiPrioPkts   ,
      sapIgQosPlcyPStatOffLoPrioPkts   ,
      sapIgQosPlcyPStatDrpLoPrioPkts   ,
      sapIgQosPlcyPStatOffHiPrioOcts   ,
      sapIgQosPlcyPStatDrpHiPrioOcts   ,
      sapIgQosPlcyPStatOffLoPrioOcts   ,
      sapIgQosPlcyPStatDrpLoPrioOcts   ,
      sapIgQosPlcyPStatFwdInProfPkts   ,
      sapIgQosPlcyPStatFwdOutProfPkts  ,
      sapIgQosPlcyPStatFwdInProfOcts   ,
      sapIgQosPlcyPStatFwdOutProfOcts  ,
      sapIgQosPlcyPStatUncolPktsOff    ,
      sapIgQosPlcyPStatUncolOctsOff    ,
      sapIgQosPlcyPStatOffHiPrioPkts   ,
      sapIgQosPlcyPStatOffHiPrioPktsL  ,
      sapIgQosPlcyPStatOffHiPrioPktsH  ,
      sapIgQosPlcyPStatDrpHiPrioPkts   ,
      sapIgQosPlcyPStatDrpHiPrioPktsL  ,
      sapIgQosPlcyPStatDrpHiPrioPktsH  ,
      sapIgQosPlcyPStatOffLoPrioPkts   ,
      sapIgQosPlcyPStatOffLoPrioPktsL  ,
      sapIgQosPlcyPStatOffLoPrioPktsH  ,
      sapIgQosPlcyPStatDrpLoPrioPkts   ,
      sapIgQosPlcyPStatDrpLoPrioPktsL  ,
      sapIgQosPlcyPStatDrpLoPrioPktsH  ,
      sapIgQosPlcyPStatOffHiPrioOcts   ,
      sapIgQosPlcyPStatOffHiPrioOctsL  ,
      sapIgQosPlcyPStatOffHiPrioOctsH  ,
      sapIgQosPlcyPStatDrpHiPrioOcts   ,
      sapIgQosPlcyPStatDrpHiPrioOctsL  ,
      sapIgQosPlcyPStatDrpHiPrioOctsH  ,
      sapIgQosPlcyPStatOffLoPrioOcts   ,
      sapIgQosPlcyPStatOffLoPrioOctsL  ,
      sapIgQosPlcyPStatOffLoPrioOctsH  ,
      sapIgQosPlcyPStatDrpLoPrioOcts   ,
      sapIgQosPlcyPStatDrpLoPrioOctsL  ,
      sapIgQosPlcyPStatDrpLoPrioOctsH  ,
      sapIgQosPlcyPStatFwdInProfPkts   ,
      sapIgQosPlcyPStatFwdInProfPktsL  ,
      sapIgQosPlcyPStatFwdInProfPktsH  ,
      sapIgQosPlcyPStatFwdOutProfPkts  ,
      sapIgQosPlcyPStatFwdOutProfPktsL ,
      sapIgQosPlcyPStatFwdOutProfPktsH ,
      sapIgQosPlcyPStatFwdInProfOcts   ,
      sapIgQosPlcyPStatFwdInProfOctsL  ,
      sapIgQosPlcyPStatFwdInProfOctsH  ,
      sapIgQosPlcyPStatFwdOutProfOcts  ,
      sapIgQosPlcyPStatFwdOutProfOctsL ,
      sapIgQosPlcyPStatFwdOutProfOctsH ,
      sapIgQosPlcyPStatUncolPktsOff    ,
      sapIgQosPlcyPStatUncolPktsOffL   ,
      sapIgQosPlcyPStatUncolPktsOffH   ,
      sapIgQosPlcyPStatUncolOctsOff    ,
      sapIgQosPlcyPStatUncolOctsOffL   ,
      sapIgQosPlcyPStatUncolOctsOffH   ,      
--      sapEgQosPlcyPStatPlcyId          ,
--      sapEgQosPlcyPStatPolId           ,
      sapEgQosPlcyPStatCustId          ,
      sapEgQosPlcyPStatMode            ,
      sapEgQosPlcyPStatOffInProfPkts   ,
      sapEgQosPlcyPStatOffInProfPktsL  ,
      sapEgQosPlcyPStatOffInProfPktsH  ,
      sapEgQosPlcyPStatFwdInProfPkts   ,
      sapEgQosPlcyPStatFwdInProfPktsL  ,
      sapEgQosPlcyPStatFwdInProfPktsH  ,
      sapEgQosPlcyPStatDrpInProfPkts   ,
      sapEgQosPlcyPStatDrpInProfPktsL  ,
      sapEgQosPlcyPStatDrpInProfPktsH  ,
      sapEgQosPlcyPStatOffOutProfPkts  ,
      sapEgQosPlcyPStatOffOutProfPktsL ,
      sapEgQosPlcyPStatOffOutProfPktsH ,
      sapEgQosPlcyPStatFwdOutProfPkts  ,
      sapEgQosPlcyPStatFwdOutProfPktsL ,
      sapEgQosPlcyPStatFwdOutProfPktsH ,
      sapEgQosPlcyPStatDrpOutProfPkts  ,
      sapEgQosPlcyPStatDrpOutProfPktsL ,
      sapEgQosPlcyPStatDrpOutProfPktsH ,
      sapEgQosPlcyPStatOffInProfOcts   ,
      sapEgQosPlcyPStatOffInProfOctsL  ,
      sapEgQosPlcyPStatOffInProfOctsH  ,
      sapEgQosPlcyPStatFwdInProfOcts   ,
      sapEgQosPlcyPStatFwdInProfOctsL  ,
      sapEgQosPlcyPStatFwdInProfOctsH  ,
      sapEgQosPlcyPStatDrpInProfOcts   ,
      sapEgQosPlcyPStatDrpInProfOctsL  ,
      sapEgQosPlcyPStatDrpInProfOctsH  ,
      sapEgQosPlcyPStatOffOutProfOcts  ,
      sapEgQosPlcyPStatOffOutProfOctsL ,
      sapEgQosPlcyPStatOffOutProfOctsH ,
      sapEgQosPlcyPStatFwdOutProfOcts  ,
      sapEgQosPlcyPStatFwdOutProfOctsL ,
      sapEgQosPlcyPStatFwdOutProfOctsH ,
      sapEgQosPlcyPStatDrpOutProfOcts  ,
      sapEgQosPlcyPStatDrpOutProfOctsL ,
      sapEgQosPlcyPStatDrpOutProfOctsH ,
      sapEgrQosArbitStatsFwdOcts, 
      sapEgrQosArbitStatsFwdOctsHi, 
      sapEgrQosArbitStatsFwdOctsLo, 
      sapEgrQosArbitStatsFwdPkts, 
      sapEgrQosArbitStatsFwdPktsHi, 
      sapEgrQosArbitStatsFwdPktsLo, 
      sapIngQosArbitStatsFwdOcts, 
      sapIngQosArbitStatsFwdOctsHi, 
      sapIngQosArbitStatsFwdOctsLo, 
      sapIngQosArbitStatsFwdPkts, 
      sapIngQosArbitStatsFwdPktsHi, 
      sapIngQosArbitStatsFwdPktsLo, 
      sapPortIdEgrQosArbitFwdOcts, 
      sapPortIdEgrQosArbitFwdOctsHi, 
      sapPortIdEgrQosArbitFwdOctsLo, 
      sapPortIdEgrQosArbitFwdPkts, 
      sapPortIdEgrQosArbitFwdPktsHi, 
      sapPortIdEgrQosArbitFwdPktsLo, 
      sapPortIdIngQosArbitFwdOcts, 
      sapPortIdIngQosArbitFwdOctsHi, 
      sapPortIdIngQosArbitFwdOctsLo, 
      sapPortIdIngQosArbitFwdPkts, 
      sapPortIdIngQosArbitFwdPktsHi, 
      sapPortIdIngQosArbitFwdPktsLo
    }
    STATUS      current
    DESCRIPTION
        "The group of objects supporting management of SAP
         Ingress/Egress QoS capabilities on Nokia SROS series systems."
    ::= { tmnxSapGroups 432 }

tmnxSapQosObsoletedV11v0Group OBJECT-GROUP
    OBJECTS {
        sapIngQosSPIR,
        sapIngQosSCIR,
        sapEgrQosSPIR,
        sapEgrQosSCIR
   }
    STATUS      current
    DESCRIPTION
        "The group of objects obsoleted supporting management of SAP
         Ingress/Egress QoS capabilities on Nokia SROS series systems
         release 11.0."
    ::= { tmnxSapGroups 433 }  

tmnxSapCflowdGroupV11v0          OBJECT-GROUP
    OBJECTS {
        sapCflowd
    }
    STATUS      current
    DESCRIPTION
        "The group of additional objects for the management of Cflowd sampling
         on SAPs for release 11.0 of the SROS series systems."
    ::= { tmnxSapGroups 435 }

sapTlsFdbMacStatsGroup          OBJECT-GROUP
    OBJECTS {
        sapTlsFdbMacStatsNumEntries
    }
    STATUS      current
    DESCRIPTION
        "The group of additional objects for the management of Cflowd sampling
         on SAPs for release 11.0 of the SROS series systems."
    ::= { tmnxSapGroups 436 }


sapTlsEtreeGroup OBJECT-GROUP
    OBJECTS {
        sapEtreeRootLeafTag,
        sapEtreeLeafTag,
        sapEtreeLeafAc
    }
    STATUS     current
    DESCRIPTION
        "The group of objects supporting E-Tree feature for SAPs on
         Nokia SROS series systems."
    ::= { tmnxSapGroups 437 }

tmnxMsapPlcyCpmProtV12v0Group  OBJECT-GROUP
    OBJECTS {
        msapPlcyCpmProtMonitorIP
    }
    STATUS current
    DESCRIPTION
        "The group of objects supporting management of CPM Protection on MSAP
         Policy for release 12.0 of the SROS series systems."
    ::= { tmnxSapGroups 438 }

tmnxSapTlsV12v0Group  OBJECT-GROUP
    OBJECTS {
        tmnxSapTlsExLastChanged,
        tmnxSapTlsExDhcpPythonPolicy,
        tmnxSapTlsExDhcp6PythonPolicy,
        tmnxSapTlsExRtrSolMsapTrigger,
        tmnxSapTlsExRtrSolUserDb
    }
    STATUS current
    DESCRIPTION
        "The group of new objects supporting management of 
         SAPS for release 12.0 of the SROS series systems."
    ::= { tmnxSapGroups 439 }

tmnxSapQosV12v0Group  OBJECT-GROUP
    OBJECTS {
        sapEgressAggRateLUB,
        sapEgrEncapGroupAggRateLUB,
        sapTmplEgrAggRateLUB
    }
    STATUS current
    DESCRIPTION
        "The group of objects supporting management of SAP QoS capabilities for 
         release 12.0 on Nokia SROS series systems."
    ::= { tmnxSapGroups 440 }

tmnxSapEthCfmV12v0Group OBJECT-GROUP
    OBJECTS {
        sapEthCfmSquelchIngress,
        sapTmplEthCfmSquelchIngress,
        sapEthCfmCollectLmmStats
    }
    STATUS      current
    DESCRIPTION
        "The group of additional objects supporting Ethernet Connectivity 
         Fault Management (ETH-CFM) for the SAP feature on Nokia SROS 
         series systems for release 12.0."
    ::= { tmnxSapGroups 441 }

tmnxIpTunnelV12v0Group OBJECT-GROUP
    OBJECTS {
        tmnxIpTunnelEncapIpMtu,
        tmnxIpTunnelIcmp6Pkt2Big,
        tmnxIpTunnelIcmp6NumPkt2Big,
        tmnxIpTunnelIcmp6Pkt2BigTime,
        tmnxIpTnlDstAddrResolved
    }
    STATUS current
    DESCRIPTION
        "The group of objects for IP Tunnel feature on Nokia SROS 
         series systems in 12.0 release."
    ::= { tmnxSapGroups 442 }

sapLagV12v0Group OBJECT-GROUP
    OBJECTS {
        sapLagPerLinkHashClass,
        sapLagPerLinkHashWeight,
        sapLagPerLinkHashOperClass,
        sapLagPerLinkHashOperWeight,
        sapLagPerLinkHashIsOverriden,
        sapLagPerLinkHashLastChanged,
        sapLagPerLinkHashTableLastChgd
    }
    STATUS current
    DESCRIPTION
        "The group of objects for SAP per-link-hash feature on Nokia 
         SROS series systems in 12.0 release."
    ::= { tmnxSapGroups 444 }

tmnxIPTunnelGreKeyV12v0Group OBJECT-GROUP
    OBJECTS {
        tmnxIpTunnelGreHeaderSendKey,
        tmnxIpTunnelGreHeaderRcvKey, 
        tmnxIpTunnelGreHeaderKeysSet,
        tmnxIpTunnelKeyMismatchRx 
    }
    STATUS current
    DESCRIPTION
        "The group of objects for SAP gre key feature on Nokia 
         SROS series systems in 12.0 release."
    ::= { tmnxSapGroups 445 }

tmnxIpTunnelFragStatV12v0Group OBJECT-GROUP
    OBJECTS {
        tmnxIpTunnelEncapOverhead,
        tmnxIpTunnelPreEncapFragCount,
        tmnxIpTunnelPreEncapFragLastSize,
        tmnxIpTunnelPostEncapFragCount,
        tmnxIpTunnelPostEncapFragLstSize
    }
    STATUS current
    DESCRIPTION
        "The group of objects for fragmentation statistics for Gre IP-in-IP 
        tunnel feature on Nokia SROS series systems in 12.0 release."
    ::= { tmnxSapGroups 446 }

tmnxIpTunnelEncapNotifyGroup   NOTIFICATION-GROUP
    NOTIFICATIONS {
       sapTunnelEncapIpMtuTooSmall 
    }
    STATUS      current
    DESCRIPTION
        "The group of notifications supporting Gre/IP-in-IP Tunnels 
        encapsulation feature on Nokia SROS series systems in release
        12.0."
    ::= { tmnxSapGroups 447 }

tmnxIpTunnelEncaNotifyObjsGroup  OBJECT-GROUP
    OBJECTS {
       sapTunnelNotifyConfigIpMtu,
       sapTunnelNotifyEncapOverhead,
       sapTunnelNotifyConfigEncapIpMtu
    }
    STATUS current
    DESCRIPTION
        "The group of objects for Gre IP-in-IP tunnel encapsulation trap 
        on Nokia SROS series systems in 12.0 release."
    ::= { tmnxSapGroups 448 }

tmnxSapPbbV12v0Group OBJECT-GROUP
    OBJECTS {
       sapPbbMldSnpgMRouter
      }
    STATUS      current
    DESCRIPTION
        "The group of objects supporting management of
         Provider Backbone Bridging (PBB/IEEE 802.1ah) capabilities for SAP's 
         on Nokia SROS series systems in 12.0 release."
    ::= { tmnxSapGroups 449 }

tmnxMsapQosV12v0Group OBJECT-GROUP
    OBJECTS {
        msapTlsPlcyIngQosPolicyId,
        msapTlsPlcyIngQosQueueingType,
        msapL3PlcyIngQosPolicyId,
        msapL3PlcyIngQosQueueingType
    }
    STATUS current
    DESCRIPTION
        "The group of objects supporting management of MSAP QoS capabilities for
         release 12.0 on Nokia SROS series systems."
    ::= { tmnxSapGroups 450 }

tmnxIpTnlOperChgGroup OBJECT-GROUP
    OBJECTS {
        tmnxIpTunnelOperChanged
    }
    STATUS current
    DESCRIPTION
        "The group of objects for new statistics of outbound SA feature on 
        Nokia SROS series systems in 10.0 release."
    ::= { tmnxSapGroups 451 }

tmnxSapMsapV12v0Group OBJECT-GROUP
    OBJECTS {
        msapTlsPlcyIgmpSnpgMcacUsePortWt
            }
    STATUS current
    DESCRIPTION
        "The group of objects supporting management of MSAP
         added in release 12.0 on Nokia SROS series systems."
    ::= { tmnxSapGroups 452 }

tmnxSapIpoeV13v0Group OBJECT-GROUP
    OBJECTS {
        tmnxSapIpoeTableLastChanged,
        tmnxSapIpoeLastChanged,
        tmnxSapIpoeAdminState,
        tmnxSapIpoeDescription,
        tmnxSapIpoePolicy,
        tmnxSapIpoeUserDb                    
            }
    STATUS current
    DESCRIPTION
        "The group of objects supporting management of IPoE session on SAP
         added in release 13.0 on Nokia SROS series systems."
    ::= { tmnxSapGroups 453 }

tmnxSapStatHost6Group OBJECT-GROUP
    OBJECTS {
        sapStatHostMacLearnOptions,
        sapStatHost6TableLastChanged,
        sapStatHost6LastChanged,
        sapStatHost6RowStatus,
        sapStatHost6AdminStatus,
        sapStatHost6PrefixLen,
        sapStatHost6NextHopAddrType ,
        sapStatHost6NextHopAddr,
        sapStatHost6SubscrIdent,
        sapStatHost6SubProfile,
        sapStatHost6SlaProfile,
        sapStatHost6ShcvOperState,
        sapStatHost6ShcvChecks,
        sapStatHost6ShcvReplies,
        sapStatHost6ShcvReplyTime,
        sapStatHost6DynMacAddress,
        sapStatHost6RetailerSvcId,
        sapStatHost6RetailerIf,
        sapStatHost6FwdingState,
        sapStatHost6AncpString,
        sapStatHost6SubIdIsSapId,
        sapStatHost6AppProfile,
        sapStatHost6IntermediateDestId,
        sapStatHost6MRtTblLastChgd,
        sapStatHost6MRtRowStatus,
        sapStatHost6MRtLastMgmtChange, 
        sapStatHost6MRtStatus,
        sapStatHost6MRtMetric,
        sapIpv6HostInfoStaticHostsUp,
        tmnxSapDataTrigStatsName,
        tmnxSapDataTrigStatsVal
        
    }
    STATUS current
    DESCRIPTION
        "The group of objects supporting management of static IPv6 hosts
         on Nokia SROS series systems."
    ::= { tmnxSapGroups 454 }

tmnxSapDnGroup OBJECT-GROUP
    OBJECTS {
        tmnxSapTlsExProcCpmTrfcSapDn
    }
    STATUS current
    DESCRIPTION
        "The tmnxSapDnGroup maintains additional vpls sap information on
         Nokia SROS series systems."
    ::= { tmnxSapGroups 455 }

tmnxSapQosSchedV13v0Group OBJECT-GROUP
    OBJECTS {
        sapIngQosSParentWeight,
        sapIngQosSParentCIRWeight,
        sapEgrQosSParentWeight,
        sapEgrQosSParentCIRWeight
    }
    STATUS current
    DESCRIPTION
        "The group of objects supporting management of Qos scheduler overrides
         on SAP for release 13.0 on Nokia SROS series systems."
    ::= { tmnxSapGroups 456 }

tmnxSapIpipeFaultPropGroup OBJECT-GROUP
    OBJECTS {
        sapIpipeLegacyFaultNotification,
        sapIpipeRemainRecoveryTimer
    }
    STATUS current
    DESCRIPTION
        "The group of objects supporting management of IPIPE fault propagation
         on SAP for release 13.0 on Nokia SROS series systems."
    ::= { tmnxSapGroups 457 }

tmnxSapStaticHostRipV13v0Group OBJECT-GROUP
    OBJECTS {
        sapStaticHostRipPolicy,
        sapStaticHostRipPlcyName,
        sapStaticHostRipListenerStatus
      }
    STATUS      current
    DESCRIPTION
        "The group of objects supporting management of SAP
         static host RIP/RIP-NG policies on Nokia SROS series systems
         added in release 13.0."
    ::= { tmnxSapGroups 458 }

tmnxSapBaseStatsV13v0Group OBJECT-GROUP
    OBJECTS {
        sapBaseStatsIngPchipRcvdValidPkt,
        sapBaseStatsIngPchipRcvdValidOct
    }
    STATUS      current
    DESCRIPTION
        "The group of objects supporting management of SAP base statistics on
         Nokia SROS series systems release 13.0."
    ::= { tmnxSapGroups 459 }

tmnxSapQueueOvrV13v0Group          OBJECT-GROUP
    OBJECTS {
        sapIngQosQMonitorDepth,
        sapEgrQosQMonitorDepth,
        sapIngQosQueueDepthPollPrcnt1,
        sapIngQosQueueDepthPollPrcnt2,
        sapIngQosQueueDepthPollPrcnt3,
        sapIngQosQueueDepthPollPrcnt4,
        sapIngQosQueueDepthPollPrcnt5,
        sapIngQosQueueDepthPollPrcnt6,
        sapIngQosQueueDepthPollPrcnt7,
        sapIngQosQueueDepthPollPrcnt8,
        sapIngQosQueueDepthPollPrcnt9,
        sapIngQosQueueDepthPollPrcnt10,
        sapIngQosQueueDepthAvgPollInt,
        sapIngQosQueueDepthAvgElpsdTme,
        sapEgrQosQueueDepthPollPrcnt1,
        sapEgrQosQueueDepthPollPrcnt2,
        sapEgrQosQueueDepthPollPrcnt3,
        sapEgrQosQueueDepthPollPrcnt4,
        sapEgrQosQueueDepthPollPrcnt5,
        sapEgrQosQueueDepthPollPrcnt6,
        sapEgrQosQueueDepthPollPrcnt7,
        sapEgrQosQueueDepthPollPrcnt8,
        sapEgrQosQueueDepthPollPrcnt9,
        sapEgrQosQueueDepthPollPrcnt10,
        sapEgrQosQueueDepthAvgPollInt,
        sapEgrQosQueueDepthAvgElpsdTme
    }
    STATUS      current
    DESCRIPTION
        "The group of objects supporting QoS queue-overrides on SAP
         in release 13.0 of Nokia SROS series systems."
    ::= { tmnxSapGroups 460 }


tmnxSapStatHost6V13v0Group OBJECT-GROUP
    OBJECTS {
        sapStatHost6AdminRetailSvcId
    }
    STATUS current
    DESCRIPTION
        "The group of objects supporting management of static IPv6 hosts
         on release 13.0 Nokia SROS series systems."
    ::= { tmnxSapGroups 462 }
    

tmnxSapDiamNasreqGroup OBJECT-GROUP
    OBJECTS {
        tmnxSapTlsExDiameterAuthPolicy
    }
    STATUS current
    DESCRIPTION
        "The group of objects supporting management of static IPv6 hosts
         on release 13.0 Nokia SROS series systems."
    ::= { tmnxSapGroups 463 }
    

tmnxSapRipNotifyGroup NOTIFICATION-GROUP
    NOTIFICATIONS {
      sapHostRipListenerSetupFailed
    }
    STATUS      current
    DESCRIPTION
        "The group of notifications for the Rip Listener feature
         on Nokia SROS series systems."
    ::= { tmnxSapGroups 464 }

tmnxSapQosRateV13v0Group  OBJECT-GROUP
    OBJECTS {
        sapEgressAggRateLmt,
        sapTmplEgrAggRateLimit,
        sapEgrEncapGrpAggRateLimit
    }
    STATUS current
    DESCRIPTION
        "The group of objects supporting management of SAP QoS capabilities for
         release 13.0 on Nokia SROS series systems."
    ::= { tmnxSapGroups 465 }

tmnxSapDhcpV13v0Group  OBJECT-GROUP
    OBJECTS {
        sapTlsDhcpStatsClntProxNqPckts
    }
    STATUS current
    DESCRIPTION
        "The group of objects supporting management of SAP
         TLS DHCP capabilities on Nokia SROS series systems
         added in release 13.0."
    ::= { tmnxSapGroups 466 }

tmnxSapShcvPolicyGroup OBJECT-GROUP
    OBJECTS {
        sapTlsShcvPolicyIpv4
    }
    STATUS current
    DESCRIPTION
        "The group of objects supporting management of
         Subscriber Host Connectivity Verification (SHCV) policies
         on Nokia SROS series systems."
    ::= { tmnxSapGroups 467 }
    

tmnxSapNotificationV13v0Group NOTIFICATION-GROUP
    NOTIFICATIONS   {
        sapStatHost6DynMacConflict
    }
    STATUS      current
    DESCRIPTION
        "The group of notifications about SAP's
         added in release 13.0 of the Nokia SROS series systems."
    ::= { tmnxSapGroups 476 }

tmnxSapV13v0Group OBJECT-GROUP
    OBJECTS {
        sapNumEntries,
        sapPortId,
        sapEncapValue,
        sapRowStatus,
        sapType,
        sapDescription,
        sapAdminStatus,
        sapOperStatus,
        sapIngressQosPolicyId,
        sapIngressMacFilterId,
        sapIngressIpFilterId,
        sapIngressVlanTranslationId,
        sapEgressQosPolicyId,
        sapEgressMacFilterId,
        sapEgressIpFilterId,
        sapMirrorStatus,
        sapIesIfIndex,
        sapLastMgmtChange,
        sapCollectAcctStats,
        sapAccountingPolicyId,
        sapVpnId,
        sapCustId,
        sapCustMultSvcSite,
        sapIngressQosSchedulerPolicy,
        sapEgressQosSchedulerPolicy,
        sapSplitHorizonGrp,
        sapIngressSharedQueuePolicy,
        sapIngressMatchQinQDot1PBits,
        sapOperFlags,
        sapLastStatusChange,
        sapAntiSpoofing,
        sapTodSuite,
        sapIngUseMultipointShared,
        sapEgressQinQMarkTopOnly,
        sapEndPoint,
        sapIngressVlanTranslation,
        sapSubType,
        sapCpmProtPolicyId,
        sapCpmProtMonitorMac,
        sapEgressFrameBasedAccounting,
        sapEthernetLLFAdminStatus,
        sapEthernetLLFOperStatus,
        sapTlsMvplsRowStatus,
        sapEgressFrameBasedAccounting,
        sapCallingStationId,
        sapIngPolicerPolicy,
        sapEgrPolicerPolicy,
        sapIpv6HostInfoIpoeDhcp6Hosts,
        sapIpv6HostInfoPppDhcp6Hosts,
        sapIpv6HostInfoPppSLAACHosts,
        sapIngQosQMBSBytes,
        sapEgrQosQMBSBytes
    }
    STATUS      current
    DESCRIPTION
        "The group of objects supporting management of SAP capabilities for
         13.0 release on Nokia SROS series systems."
    ::= { tmnxSapGroups 477 }

tmnxSapMvrpV13v0Group OBJECT-GROUP
    OBJECTS {
       sapTmplLastChanged, 
       sapTmplRowStatus, 
       sapTmplSapCount, 
       sapTmplType, 
       sapTmplTblLastChanged,
       sapTmplTlsLastChanged, 
       sapTmplTlsMacAgeing, 
       sapTmplTlsTblLastChanged,
       sapTlsEsVidGrpEndVlanTag, 
       sapTlsEsVidGrpLastChgd, 
       sapTlsEsVidGrpRowStatus, 
       sapTlsEsVidGrpStartVlanTag, 
       sapTlsEsVidGrpTblLastChanged,
       sapTmplUsed,
       sapTmplUserCreationOrigin,
       sapTmplUserCreatorSvcId,
       sapTmplCollectAcctStats, 
       sapTmplEgrPolicerPolicy, 
       sapTmplEgressFrameBasedAcctg, 
       sapTmplEgressIpFilterId, 
       sapTmplEgressIpv6FilterId, 
       sapTmplEgressMacFilterId, 
       sapTmplEgressQinQMarkTopOnly, 
       sapTmplEgressQosPolicyId, 
       sapTmplEgressQosSchedulerPolicy, 
       sapTmplIngPolicerPolicy, 
       sapTmplIngUseMultipointShared, 
       sapTmplIngressIpFilterId, 
       sapTmplIngressIpv6FilterId, 
       sapTmplIngressMacFilterId, 
       sapTmplIngressMatchQinQDot1PBits, 
       sapTmplIngressQosPolicyId, 
       sapTmplIngressQosSchedulerPolicy, 
       sapTmplIngressSharedQueuePolicy, 
       sapTmplTlsBpduTranslation, 
       sapTmplTlsDiscardUnknownSource, 
       sapTmplTlsL2ptProtocols, 
       sapTmplTlsL2ptTermination, 
       sapTmplTlsLimitMacMove, 
       sapTmplTlsLimitMacMoveLevel, 
       sapTmplTlsMacAddressLimit, 
       sapTmplTlsMacLearning, 
       sapTmplTlsStpAdminPointToPoint, 
       sapTmplTlsStpAdminStatus, 
       sapTmplTlsStpAutoEdge, 
       sapTmplTlsStpBpduEncap, 
       sapTmplTlsStpPathCost, 
       sapTmplTlsStpPriority, 
       sapTmplTlsStpRapidStart, 
       sapTmplTlsStpRootGuard,
       sapTmplDot1agCfmMip,
       sapTmplCpmProtPolicyId,
       sapTmplCpmProtMonitorMac,
       sapTlsDataSapInstStatus,
       sapTlsDataSapInstLastErr,
       sapTlsMvrpDeclared, 
       sapTlsMvrpEndStation, 
       sapTlsMvrpRegistered,
       sapTlsMvrpAdminStatus,
       sapTlsMvrpOperStatus,
       sapTlsInTcBitBpdus,
       sapTlsOutTcBitBpdus
    }
    STATUS      current
    DESCRIPTION
        "The group of objects supporting management of SAP MVRP
         capabilities on release 13.0 of Nokia SROS series systems."
    ::= { tmnxSapGroups 478 }
    
tmnxSapEgrEncapGrpV13v0Group OBJECT-GROUP
    OBJECTS {
       sapEgrEncapGroupTblLastChgd,
       sapEgrEncapGroupRowStatus,
       sapEgrEncapGroupLastChanged,
       sapEgrEncapGroupType,
       sapEgrEncapGroupQosPerMember,
       sapEgrEncapGroupQosPolicyId,
       sapEgrEncapGroupSchedulerPolicy,
       sapEgrEncapGrpFrameBasedAccnt,
       sapEgrEncapGrpMemActTblLastChgd,
       sapEgrEncapGroupBeginMember,
       sapEgrEncapGroupEndMember,
       sapEgrEncapGroupMemberAction,
       sapEgrEncapGrpRangeEndId,
       sapEgrEncapGrpMemberLastChanged,
       sapEgrEGBaseStLastClearedTime,
       sapEgrEGBaseStCustId,  
       sapEgrEGBaseStQcDpdInPfPkts, 
       sapEgrEGBaseStQcDpdInPfPkts,         
       sapEgrEGBaseStQcDpdInPfPktsL, 
       sapEgrEGBaseStQcDpdInPfPktsH, 
       sapEgrEGBaseStQcDpdInPfOcts,  
       sapEgrEGBaseStQcDpdInPfOctsL, 
       sapEgrEGBaseStQcDpdInPfOctsH, 
       sapEgrEGBaseStQcDpdOutPfPkts, 
       sapEgrEGBaseStQcDpdOutPfPktsL,
       sapEgrEGBaseStQcDpdOutPfPktsH,
       sapEgrEGBaseStQcDpdOutPfOcts, 
       sapEgrEGBaseStQcDpdOutPfOctsL,
       sapEgrEGBaseStQcDpdOutPfOctsH,
       sapEgrEGBaseStQcFwdInPfPkts,  
       sapEgrEGBaseStQcFwdInPfPktsL, 
       sapEgrEGBaseStQcFwdInPfPktsH, 
       sapEgrEGBaseStQcFwdInPfOcts,  
       sapEgrEGBaseStQcFwdInPfOctsL, 
       sapEgrEGBaseStQcFwdInPfOctsH, 
       sapEgrEGBaseStQcFwdOutPfPkts, 
       sapEgrEGBaseStQcFwdOutPfPktsL,
       sapEgrEGBaseStQcFwdOutPfPktsH,
       sapEgrEGBaseStQcFwdOutPfOcts, 
       sapEgrEGBaseStQcFwdOutPfOctsL,
       sapEgrEGBaseStQcFwdOutPfOctsH,
       sapEgrEGMbrBaseStQcDpdInPfPkts,  
       sapEgrEGMbrBaseStQcDpdInPfPktsL, 
       sapEgrEGMbrBaseStQcDpdInPfPktsH, 
       sapEgrEGMbrBaseStQcDpdInPfOcts,  
       sapEgrEGMbrBaseStQcDpdInPfOctsL, 
       sapEgrEGMbrBaseStQcDpdInPfOctsH, 
       sapEgrEGMbrBaseStQcDpdOutPfPkts, 
       sapEgrEGMbrBaseStQcDpdOutPfPktsL,
       sapEgrEGMbrBaseStQcDpdOutPfPktsH,
       sapEgrEGMbrBaseStQcDpdOutPfOcts, 
       sapEgrEGMbrBaseStQcDpdOutPfOctsL,
       sapEgrEGMbrBaseStQcDpdOutPfOctsH,
       sapEgrEGMbrBaseStQcFwdInPfPkts,  
       sapEgrEGMbrBaseStQcFwdInPfPktsL, 
       sapEgrEGMbrBaseStQcFwdInPfPktsH,
       sapEgrEGMbrBaseStQcFwdInPfOcts,  
       sapEgrEGMbrBaseStQcFwdInPfOctsL, 
       sapEgrEGMbrBaseStQcFwdInPfOctsH, 
       sapEgrEGMbrBaseStQcFwdOutPfPkts, 
       sapEgrEGMbrBaseStQcFwdOutPfPktsL,
       sapEgrEGMbrBaseStQcFwdOutPfPktsH,
       sapEgrEGMbrBaseStQcFwdOutPfOcts, 
       sapEgrEGMbrBaseStQcFwdOutPfOctsL,
       sapEgrEGMbrBaseStQcFwdOutPfOctsH,
       sapEgrEGMbrBaseStLstClearedTime, 
       sapEgrEGMbrBaseStCustId,     
       sapEgrEGQueueStFwdInPfPkts,  
       sapEgrEGQueueStFwdInPfPktsL, 
       sapEgrEGQueueStFwdInPfPktsH, 
       sapEgrEGQueueStDpdInPfPkts,  
       sapEgrEGQueueStDpdInPfPktsL, 
       sapEgrEGQueueStDpdInPfPktsH, 
       sapEgrEGQueueStFwdOutPfPkts, 
       sapEgrEGQueueStFwdOutPfPktsL,
       sapEgrEGQueueStFwdOutPfPktsH,
       sapEgrEGQueueStDpdOutPfPkts, 
       sapEgrEGQueueStDpdOutPfPktsL,
       sapEgrEGQueueStDpdOutPfPktsH,
       sapEgrEGQueueStFwdInPfOcts,  
       sapEgrEGQueueStFwdInPfOctsL, 
       sapEgrEGQueueStFwdInPfOctsH, 
       sapEgrEGQueueStDpdInPfOcts,  
       sapEgrEGQueueStDpdInPfOctsL, 
       sapEgrEGQueueStDpdInPfOctsH, 
       sapEgrEGQueueStFwdOutPfOcts, 
       sapEgrEGQueueStFwdOutPfOctsL,
       sapEgrEGQueueStFwdOutPfOctsH,
       sapEgrEGQueueStDpdOutPfOcts, 
       sapEgrEGQueueStDpdOutPfOctsL,
       sapEgrEGQueueStDpdOutPfOctsH,
       sapEgrEGCustId,   
       sapEgrEGMbrQueueStFwdInPfPkts,   
       sapEgrEGMbrQueueStFwdInPfPktsL,  
       sapEgrEGMbrQueueStFwdInPfPktsH,  
       sapEgrEGMbrQueueStDpdInPfPkts,   
       sapEgrEGMbrQueueStDpdInPfPktsL,  
       sapEgrEGMbrQueueStDpdInPfPktsH,  
       sapEgrEGMbrQueueStFwdOutPfPkts,  
       sapEgrEGMbrQueueStFwdOutPfPktsL, 
       sapEgrEGMbrQueueStFwdOutPfPktsH, 
       sapEgrEGMbrQueueStDpdOutPfPkts,  
       sapEgrEGMbrQueueStDpdOutPfPktsL, 
       sapEgrEGMbrQueueStDpdOutPfPktsH, 
       sapEgrEGMbrQueueStFwdInPfOcts,   
       sapEgrEGMbrQueueStFwdInPfOctsL,  
       sapEgrEGMbrQueueStFwdInPfOctsH,  
       sapEgrEGMbrQueueStDpdInPfOcts,  
       sapEgrEGMbrQueueStDpdInPfOctsL,  
       sapEgrEGMbrQueueStDpdInPfOctsH,  
       sapEgrEGMbrQueueStFwdOutPfOcts,  
       sapEgrEGMbrQueueStFwdOutPfOctsL, 
       sapEgrEGMbrQueueStFwdOutPfOctsH, 
       sapEgrEGMbrQueueStDpdOutPfOcts,  
       sapEgrEGMbrQueueStDpdOutPfOctsL, 
       sapEgrEGMbrQueueStDpdOutPfOctsH, 
       sapEgrEGMbrQueueCustId,           
       sapEgrEGSchedStFwdPkts,  
       sapEgrEGSchedStFwdPktsL, 
       sapEgrEGSchedStFwdPktsH, 
       sapEgrEGSchedStFwdOcts, 
       sapEgrEGSchedStFwdOctsL, 
       sapEgrEGSchedStFwdOctsH, 
       sapEgrEGSchedCustId,      
       sapEgrEGMbrSchedStFwdPkts, 
       sapEgrEGMbrSchedStFwdPktsL,
       sapEgrEGMbrSchedStFwdPktsH,
       sapEgrEGMbrSchedStFwdOcts, 
       sapEgrEGMbrSchedStFwdOctsL,
       sapEgrEGMbrSchedStFwdOctsH,
       sapEgrEGMbrSchedCustId,     
       sapPortIdEgrEGSchedFwdPkts,  
       sapPortIdEgrEGSchedFwdPktsL, 
       sapPortIdEgrEGSchedFwdPktsH, 
       sapPortIdEgrEGSchedFwdOcts,  
       sapPortIdEgrEGSchedFwdOctsL, 
       sapPortIdEgrEGSchedFwdOctsH, 
       sapPortIdEgrEGSchedCustId, 
       sapPortIdEgrEGMbrSchedFwdPkts,  
       sapPortIdEgrEGMbrSchedFwdPktsL, 
       sapPortIdEgrEGMbrSchedFwdPktsH, 
       sapPortIdEgrEGMbrSchedFwdOcts,  
       sapPortIdEgrEGMbrSchedFwdOctsL, 
       sapPortIdEgrEGMbrSchedFwdOctsH, 
       sapPortIdEgrEGMbrSchedCustId
       }
    STATUS      current
    DESCRIPTION
        "The group of objects supporting management of SAP
         encapsulation group on Nokia SROS series systems in
         release 13.0."
    ::= { tmnxSapGroups 479 }
    
tmnxSapObsoletedV13v0Group OBJECT-GROUP
    OBJECTS {
        sapEgressAggRateLimit,
        sapTmplEgressAggRateLimit, 
        sapEgrEncapGroupAggRateLimit
    }
    STATUS      current
    DESCRIPTION
        "The group of obsoleted objects supporting management of SAP
         capabilities for 13.0 release on Nokia SROS series systems."
    ::= { tmnxSapGroups 480 }

sapBgpEvpnMplsMhGroup OBJECT-GROUP
    OBJECTS {
        sapEvpnMHEthSegName
    }
    STATUS current
    DESCRIPTION
        "The group of objects supporting SAP BGP EVPN (Ethernet - VPN)
         MPLS Multi Home feature on Nokia SROS series systems
         release 13.0."
    ::={ tmnxSapGroups 481 }

END
