--  The capabilities of SAS product variants are described using
--  tmnx%*V9v0 AGENT-CAPABILITY statements, where % represents a
--  platform name (e.g. 7450).
--
--  The AGENT-CAPABILITY statements must be interpreted using the following
--  agent hierarchy:
--    tmnxSAS*V9v0              - All SAS platforms
--        tmnx7210*V9v0           - 7210 (generic platforms)
--            tmnx7210SASR*V9v0   - 7210 SASR platform 
--            tmnx7210SASX*V9v0   - 7210 SASX platform 
--            tmnx7210SAST*V9v0   - 7210 SAST platform 
--            tmnx7210SASMxp*V9v0 - 7210 SASMxp platform 
--            tmnx7210SASSx*V9v0  - 7210 SASSx platform 
--            tmnx7210SASK*V9v0   - 7210 SASK platform 
--
--  For example, if a tmnx7210SASR*V9v0 AGENT-CAPABILITY statement does
--  not exist, the tmnx210*V9v0 takes effect. If, however, a
--  tmnx7210SASR*V9v0 AGENT-CAPABILITY statement does exist, the
--  tmnx7210*V9v0 AGENT-CAPABILITY statement does not apply to the
--  7210-SASR agent.
--
--  When a platform specific AGENT-CAPABILITIES INCLUDES list contains a
--  EXCLUDE group statement, it indicates that the objects in that group are
--  not supported on that specific platform. 
--
--  When a platform specific AGENT-CAPABILITIES statement consists of a
--  commented out SUPPORTS statement with an empty INCLUDES list and no
--  VARIATION statements, it indicates that the feature is not implemented
--  on that specific platform.  An empty INCLUDES list contains no group
--  names and no EXCLUDE statements.  

TIMETRA-CAPABILITY-SAS-SAS-V9v0 DEFINITIONS ::= BEGIN

IMPORTS
    MODULE-IDENTITY, OBJECT-IDENTITY,
    enterprises, Integer32, Unsigned32      FROM SNMPv2-SMI

    RowStatus, TimeInterval, StorageType    FROM SNMPv2-TC

    AGENT-CAPABILITIES,
    MODULE-COMPLIANCE                       FROM SNMPv2-CONF

    DisplayString,
    TruthValue                              FROM SNMPv2-TC

    SnmpAdminString                         FROM SNMP-FRAMEWORK-MIB

    InterfaceIndex                          FROM IF-MIB

    DefaultMetric                           FROM ISIS-MIB

    Dot1agCfmMhfCreation,
    Dot1agCfmIdPermission                   FROM IEEE8021-CFM-MIB

    InetAddress, InetAddressPrefixLength,
    InetAddressType                         FROM INET-ADDRESS-MIB

    OwnerString                             FROM RMON-MIB

    LldpPortIdSubtype                       FROM LLDP-MIB 

    TmnxBsxOperator,
    TmnxBsxActionStatus,
    TmnxBsxAaSubscriberType                 FROM TIMETRA-BSX-NG-MIB

    TmnxSETSRefSource, TmnxSSMQualityLevel,
    TmnxChassisMode, TmnxBITSIfType,
    TmnxChassisIndex                        FROM TIMETRA-CHASSIS-MIB

    TEntryId                                FROM TIMETRA-FILTER-MIB

    TmnxOtuAlarms                           FROM TIMETRA-OTU-MIB

    TmnxL2tpTunnelSessionLimit              FROM TIMETRA-L2TP-MIB

    timetraSASCapModule,
    tmnxSASCapability                      FROM TIMETRA-SAS-GLOBAL-MIB

    TmnxPtpPriority                         FROM TIMETRA-PTP-MIB

    TmnxEnabledDisabled, TIpProtocol,
    TmnxServId, TNamedItemOrEmpty,
    TmnxSubRadServAlgorithm                 FROM TIMETRA-TC-MIB;

--
-- Capability statements for SAS release 9.0
--
--
timetraSASV9v0CapModule   MODULE-IDENTITY
    LAST-UPDATED "201609161027Z"
    ORGANIZATION "Nokia"
    CONTACT-INFO
        "Nokia SAS Support
        Web: http://www.nokia.com "
    DESCRIPTION
        "This document is the SNMP MIB module for agent capability clauses
         defined under the Nokia timetra object identifier branch for
         the Nokia SAS release R9.0.  These capability clauses
         specify details about the SNMP agent implementation for this release.

         Copyright 2005-2015 Nokia. All rights reserved.
         Reproduction of this document is authorized on the condition that the
         foregoing copyright notice is included.

         This SNMP MIB module (Specification) embodies Nokia's
         proprietary intellectual property.  Nokia retains all title
         and ownership in the Specification, including any revisions.

         Nokia grants all interested parties a non-exclusive license to
         use and distribute an unmodified copy of this Specification in
         connection with management of Nokia products, and without fee,
         provided this copyright notice and license appear on all copies.

         This Specification is supplied as is, and Nokia makes no
         warranty, either express or implied, as to the use, operation,
         condition, or performance of the Specification."
--
--  Revision History
--
    REVISION        "201609161027Z"
    DESCRIPTION     "Rev 0.0                16 Sep 2016 10:27
        This is the initial version of the TIMETRA-CAPABILITY-SAS-V9v0
         mib for Nokia SAS series Release 9.0."
        ::= { timetraSASCapModule 9 }



--
--  Parent-tree for ALcatel-Lucent SAS SNMP agent capability objects
--
--  tmnxSASCapability      OBJECT IDENTIFIER ::= { tmnxProductCapability 5 }
    tmnxSASV9v0          OBJECT IDENTIFIER ::= { tmnxSASCapability 9 }

-- Supported SAS Agents and capabilities defined by this SNMP MODULE:
tmnxCapsTestObjectV9v0     OBJECT IDENTIFIER ::= { tmnxSASV9v0 1 }
tmnxSASAgentCapsV9v0      OBJECT IDENTIFIER ::= { tmnxSASV9v0 2 }

  tmnxSASAgentV9v0         OBJECT IDENTIFIER ::= { tmnxSASAgentCapsV9v0  2 }
-- tmnxSASIeee8021PaeV9v0         OBJECT IDENTIFIER ::= { tmnxSASAgentV9v0   1 }
-- tmnxSASIeee8021PaeV9v0         OBJECT IDENTIFIER ::= { tmnxSASAgentV9v0   1 }
-- tmnxSASIgmpSnoopingV9v0        OBJECT IDENTIFIER ::= { tmnxSASAgentV9v0   2 }
-- tmnxSASIgmpSnoopingV9v0        OBJECT IDENTIFIER ::= { tmnxSASAgentV9v0   2 }
-- tmnxSASEtherLikeV9v0           OBJECT IDENTIFIER ::= { tmnxSASAgentV9v0   3 }
-- tmnxSASEtherLikeV9v0           OBJECT IDENTIFIER ::= { tmnxSASAgentV9v0   3 }
-- tmnxSASRmonV9v0                OBJECT IDENTIFIER ::= { tmnxSASAgentV9v0   4 }
-- tmnxSASRmonV9v0                OBJECT IDENTIFIER ::= { tmnxSASAgentV9v0   4 }
-- tmnxSASLagV9v0                 OBJECT IDENTIFIER ::= { tmnxSASAgentV9v0   5 }
-- tmnxSASLagV9v0                 OBJECT IDENTIFIER ::= { tmnxSASAgentV9v0   5 }
-- tmnxSASInterfaceV9v0           OBJECT IDENTIFIER ::= { tmnxSASAgentV9v0   6 }
-- tmnxSASInterfaceV9v0           OBJECT IDENTIFIER ::= { tmnxSASAgentV9v0   6 }
-- tmnxSASIpV9v0                  OBJECT IDENTIFIER ::= { tmnxSASAgentV9v0   7 }
-- tmnxSASIpV9v0                  OBJECT IDENTIFIER ::= { tmnxSASAgentV9v0   7 }
-- tmnxSASMplsV9v0                OBJECT IDENTIFIER ::= { tmnxSASAgentV9v0  10 }
-- tmnxSASMplsV9v0                OBJECT IDENTIFIER ::= { tmnxSASAgentV9v0  10 }
-- tmnxSASLogV9v0                 OBJECT IDENTIFIER ::= { tmnxSASAgentV9v0  11 }
-- tmnxSASLogV9v0                 OBJECT IDENTIFIER ::= { tmnxSASAgentV9v0  11 }
-- tmnxSASRsvpV9v0                OBJECT IDENTIFIER ::= { tmnxSASAgentV9v0  13 }
-- tmnxSASRsvpV9v0                OBJECT IDENTIFIER ::= { tmnxSASAgentV9v0  13 }
-- tmnxSASSnmpV9v0                OBJECT IDENTIFIER ::= { tmnxSASAgentV9v0  14 }
-- tmnxSASSnmpV9v0                OBJECT IDENTIFIER ::= { tmnxSASAgentV9v0  14 }
-- tmnxSASChassisV9v0             OBJECT IDENTIFIER ::= { tmnxSASAgentV9v0  15 }
-- tmnxSASChassisV9v0             OBJECT IDENTIFIER ::= { tmnxSASAgentV9v0  15 }
-- tmnxSASServicesV9v0            OBJECT IDENTIFIER ::= { tmnxSASAgentV9v0  16 }
-- tmnxSASServicesV9v0            OBJECT IDENTIFIER ::= { tmnxSASAgentV9v0  16 }
-- tmnxSASSystemV9v0              OBJECT IDENTIFIER ::= { tmnxSASAgentV9v0  17 }
-- tmnxSASSystemV9v0              OBJECT IDENTIFIER ::= { tmnxSASAgentV9v0  17 }
-- tmnxSASVrtrV9v0                OBJECT IDENTIFIER ::= { tmnxSASAgentV9v0  18 }
-- tmnxSASVrtrV9v0                OBJECT IDENTIFIER ::= { tmnxSASAgentV9v0  18 }
-- tmnxSASCronV9v0                OBJECT IDENTIFIER ::= { tmnxSASAgentV9v0  19 }
-- tmnxSASCronV9v0                OBJECT IDENTIFIER ::= { tmnxSASAgentV9v0  19 }
-- tmnxSASNtpV9v0                 OBJECT IDENTIFIER ::= { tmnxSASAgentV9v0  20 }
-- tmnxSASNtpV9v0                 OBJECT IDENTIFIER ::= { tmnxSASAgentV9v0  20 }
-- tmnxSASSchedulerV9v0           OBJECT IDENTIFIER ::= { tmnxSASAgentV9v0  21 }
-- tmnxSASSchedulerV9v0           OBJECT IDENTIFIER ::= { tmnxSASAgentV9v0  21 }
-- tmnxSASDot3OamV9v0             OBJECT IDENTIFIER ::= { tmnxSASAgentV9v0  22 }
-- tmnxSASDot3OamV9v0             OBJECT IDENTIFIER ::= { tmnxSASAgentV9v0  22 }
-- tmnxSASDot1agCfmV9v0           OBJECT IDENTIFIER ::= { tmnxSASAgentV9v0  23 }
-- tmnxSASDot1agCfmV9v0           OBJECT IDENTIFIER ::= { tmnxSASAgentV9v0  23 }
-- tmnxSASSapV9v0                 OBJECT IDENTIFIER ::= { tmnxSASAgentV9v0  24 }
-- tmnxSASSapV9v0                 OBJECT IDENTIFIER ::= { tmnxSASAgentV9v0  24 }
-- tmnxSASSdpV9v0                 OBJECT IDENTIFIER ::= { tmnxSASAgentV9v0  25 }
-- tmnxSASSdpV9v0                 OBJECT IDENTIFIER ::= { tmnxSASAgentV9v0  25 }
-- tmnxSASLldpV9v0                OBJECT IDENTIFIER ::= { tmnxSASAgentV9v0  28 }
-- tmnxSASLldpV9v0                OBJECT IDENTIFIER ::= { tmnxSASAgentV9v0  28 }
-- tmnxSASAlarmInputV9v0          OBJECT IDENTIFIER ::= { tmnxSASAgentV9v0  29 }
-- tmnxSASAlarmInputV9v0          OBJECT IDENTIFIER ::= { tmnxSASAgentV9v0  29 }
-- tmnxSASTwampV9v0               OBJECT IDENTIFIER ::= { tmnxSASAgentV9v0  32 }
-- tmnxSASTwampV9v0               OBJECT IDENTIFIER ::= { tmnxSASAgentV9v0  32 }

  tmnxSASAgentV9v0         OBJECT IDENTIFIER ::= { tmnxSASAgentCapsV9v0  2 }
-- tmnxSASIeee8021PaeV9v0         OBJECT IDENTIFIER ::= { tmnxSASAgentV9v0   1 }
-- tmnxSASIeee8021PaeV9v0         OBJECT IDENTIFIER ::= { tmnxSASAgentV9v0   1 }
-- tmnxSASIgmpSnoopingV9v0        OBJECT IDENTIFIER ::= { tmnxSASAgentV9v0   2 }
-- tmnxSASIgmpSnoopingV9v0        OBJECT IDENTIFIER ::= { tmnxSASAgentV9v0   2 }
-- tmnxSASEtherLikeV9v0           OBJECT IDENTIFIER ::= { tmnxSASAgentV9v0   3 }
-- tmnxSASEtherLikeV9v0           OBJECT IDENTIFIER ::= { tmnxSASAgentV9v0   3 }
-- tmnxSASRmonV9v0                OBJECT IDENTIFIER ::= { tmnxSASAgentV9v0   4 }
-- tmnxSASRmonV9v0                OBJECT IDENTIFIER ::= { tmnxSASAgentV9v0   4 }
-- tmnxSASLagV9v0                 OBJECT IDENTIFIER ::= { tmnxSASAgentV9v0   5 }
-- tmnxSASLagV9v0                 OBJECT IDENTIFIER ::= { tmnxSASAgentV9v0   5 }
-- tmnxSASInterfaceV9v0           OBJECT IDENTIFIER ::= { tmnxSASAgentV9v0   6 }
-- tmnxSASInterfaceV9v0           OBJECT IDENTIFIER ::= { tmnxSASAgentV9v0   6 }
-- tmnxSASIpV9v0                  OBJECT IDENTIFIER ::= { tmnxSASAgentV9v0   7 }
-- tmnxSASIpV9v0                  OBJECT IDENTIFIER ::= { tmnxSASAgentV9v0   7 }
-- tmnxSASMplsV9v0                OBJECT IDENTIFIER ::= { tmnxSASAgentV9v0  10 }
-- tmnxSASMplsV9v0                OBJECT IDENTIFIER ::= { tmnxSASAgentV9v0  10 }
-- tmnxSASLogV9v0                 OBJECT IDENTIFIER ::= { tmnxSASAgentV9v0  11 }
-- tmnxSASLogV9v0                 OBJECT IDENTIFIER ::= { tmnxSASAgentV9v0  11 }
-- tmnxSASRsvpV9v0                OBJECT IDENTIFIER ::= { tmnxSASAgentV9v0  13 }
-- tmnxSASRsvpV9v0                OBJECT IDENTIFIER ::= { tmnxSASAgentV9v0  13 }
-- tmnxSASSnmpV9v0                OBJECT IDENTIFIER ::= { tmnxSASAgentV9v0  14 }
-- tmnxSASSnmpV9v0                OBJECT IDENTIFIER ::= { tmnxSASAgentV9v0  14 }
-- tmnxSASChassisV9v0             OBJECT IDENTIFIER ::= { tmnxSASAgentV9v0  15 }
-- tmnxSASChassisV9v0             OBJECT IDENTIFIER ::= { tmnxSASAgentV9v0  15 }
-- tmnxSASServicesV9v0            OBJECT IDENTIFIER ::= { tmnxSASAgentV9v0  16 }
-- tmnxSASServicesV9v0            OBJECT IDENTIFIER ::= { tmnxSASAgentV9v0  16 }
-- tmnxSASSystemV9v0              OBJECT IDENTIFIER ::= { tmnxSASAgentV9v0  17 }
-- tmnxSASSystemV9v0              OBJECT IDENTIFIER ::= { tmnxSASAgentV9v0  17 }
-- tmnxSASVrtrV9v0                OBJECT IDENTIFIER ::= { tmnxSASAgentV9v0  18 }
-- tmnxSASVrtrV9v0                OBJECT IDENTIFIER ::= { tmnxSASAgentV9v0  18 }
-- tmnxSASCronV9v0                OBJECT IDENTIFIER ::= { tmnxSASAgentV9v0  19 }
-- tmnxSASCronV9v0                OBJECT IDENTIFIER ::= { tmnxSASAgentV9v0  19 }
-- tmnxSASNtpV9v0                 OBJECT IDENTIFIER ::= { tmnxSASAgentV9v0  20 }
-- tmnxSASNtpV9v0                 OBJECT IDENTIFIER ::= { tmnxSASAgentV9v0  20 }
-- tmnxSASSchedulerV9v0           OBJECT IDENTIFIER ::= { tmnxSASAgentV9v0  21 }
-- tmnxSASSchedulerV9v0           OBJECT IDENTIFIER ::= { tmnxSASAgentV9v0  21 }
-- tmnxSASDot3OamV9v0             OBJECT IDENTIFIER ::= { tmnxSASAgentV9v0  22 }
-- tmnxSASDot3OamV9v0             OBJECT IDENTIFIER ::= { tmnxSASAgentV9v0  22 }
-- tmnxSASDot1agCfmV9v0           OBJECT IDENTIFIER ::= { tmnxSASAgentV9v0  23 }
-- tmnxSASDot1agCfmV9v0           OBJECT IDENTIFIER ::= { tmnxSASAgentV9v0  23 }
-- tmnxSASSapV9v0                 OBJECT IDENTIFIER ::= { tmnxSASAgentV9v0  24 }
-- tmnxSASSapV9v0                 OBJECT IDENTIFIER ::= { tmnxSASAgentV9v0  24 }
-- tmnxSASSdpV9v0                 OBJECT IDENTIFIER ::= { tmnxSASAgentV9v0  25 }
-- tmnxSASSdpV9v0                 OBJECT IDENTIFIER ::= { tmnxSASAgentV9v0  25 }
-- tmnxSASLldpV9v0                OBJECT IDENTIFIER ::= { tmnxSASAgentV9v0  28 }
-- tmnxSASLldpV9v0                OBJECT IDENTIFIER ::= { tmnxSASAgentV9v0  28 }
-- tmnxSASAlarmInputV9v0          OBJECT IDENTIFIER ::= { tmnxSASAgentV9v0  29 }
-- tmnxSASAlarmInputV9v0          OBJECT IDENTIFIER ::= { tmnxSASAgentV9v0  29 }
-- tmnxSASTwampV9v0               OBJECT IDENTIFIER ::= { tmnxSASAgentV9v0  32 }
-- tmnxSASTwampV9v0               OBJECT IDENTIFIER ::= { tmnxSASAgentV9v0  32 }

  tmnxSASRAgentV9v0        OBJECT IDENTIFIER ::= { tmnxSASAgentCapsV9v0  3 }
-- tmnxSASRIgmpSnoopingV9v0       OBJECT IDENTIFIER ::= { tmnxSASRAgentV9v0   2 }
-- tmnxSASRIsisV9v0               OBJECT IDENTIFIER ::= { tmnxSASRAgentV9v0   8 }
-- tmnxSASRLdpV9v0                OBJECT IDENTIFIER ::= { tmnxSASRAgentV9v0   9 }
-- tmnxSASROspfV9v0               OBJECT IDENTIFIER ::= { tmnxSASRAgentV9v0  12 }
-- tmnxSASRDot3OamV9v0            OBJECT IDENTIFIER ::= { tmnxSASRAgentV9v0  22 }
-- tmnxSASRDs0V9v0                OBJECT IDENTIFIER ::= { tmnxSASRAgentV9v0  26 }
-- tmnxSASRDs1V9v0                OBJECT IDENTIFIER ::= { tmnxSASRAgentV9v0  27 }
-- tmnxSASRMcRedundancyV9v0       OBJECT IDENTIFIER ::= { tmnxSASRAgentV9v0  30 }
-- tmnxSASRBgpV9v0                OBJECT IDENTIFIER ::= { tmnxSASRAgentV9v0  31 }
-- tmnxSASRPimV9v0                OBJECT IDENTIFIER ::= { tmnxSASRAgentV9v0  33 }
-- tmnxSASRIgmpV9v0               OBJECT IDENTIFIER ::= { tmnxSASRAgentV9v0  34 }
-- tmnxSASRVrrpV9v0               OBJECT IDENTIFIER ::= { tmnxSASRAgentV9v0  35 }

  tmnxSASXAgentV9v0        OBJECT IDENTIFIER ::= { tmnxSASAgentCapsV9v0  4 }
-- tmnxSASXIgmpSnoopingV9v0       OBJECT IDENTIFIER ::= { tmnxSASXAgentV9v0   2 }
-- tmnxSASXIsisV9v0               OBJECT IDENTIFIER ::= { tmnxSASXAgentV9v0   8 }
-- tmnxSASXLdpV9v0                OBJECT IDENTIFIER ::= { tmnxSASXAgentV9v0   9 }
-- tmnxSASXOspfV9v0               OBJECT IDENTIFIER ::= { tmnxSASXAgentV9v0  12 }
-- tmnxSASXDot3OamV9v0            OBJECT IDENTIFIER ::= { tmnxSASXAgentV9v0  22 }
-- tmnxSASXDs0V9v0                OBJECT IDENTIFIER ::= { tmnxSASXAgentV9v0  26 }
-- tmnxSASXMcRedundancyV9v0       OBJECT IDENTIFIER ::= { tmnxSASXAgentV9v0  30 }
-- tmnxSASXBgpV9v0                OBJECT IDENTIFIER ::= { tmnxSASXAgentV9v0  31 }
-- tmnxSASXPimV9v0                OBJECT IDENTIFIER ::= { tmnxSASXAgentV9v0  33 }
-- tmnxSASXIgmpV9v0               OBJECT IDENTIFIER ::= { tmnxSASXAgentV9v0  34 }

  tmnxSASTAgentV9v0        OBJECT IDENTIFIER ::= { tmnxSASAgentCapsV9v0  5 }
-- tmnxSASTIgmpSnoopingV9v0       OBJECT IDENTIFIER ::= { tmnxSASTAgentV9v0   2 }
-- tmnxSASTDot1agCfmV9v0          OBJECT IDENTIFIER ::= { tmnxSASTAgentV9v0  23 }

  tmnxSASMAgentV9v0        OBJECT IDENTIFIER ::= { tmnxSASAgentCapsV9v0  6 }
-- tmnxSASMIgmpSnoopingV9v0       OBJECT IDENTIFIER ::= { tmnxSASMAgentV9v0   2 }
-- tmnxSASMIsisV9v0               OBJECT IDENTIFIER ::= { tmnxSASMAgentV9v0   8 }
-- tmnxSASMLdpV9v0                OBJECT IDENTIFIER ::= { tmnxSASMAgentV9v0   9 }
-- tmnxSASMOspfV9v0               OBJECT IDENTIFIER ::= { tmnxSASMAgentV9v0  12 }
-- tmnxSASMDot3OamV9v0            OBJECT IDENTIFIER ::= { tmnxSASMAgentV9v0  22 }
-- tmnxSASMDs0V9v0                OBJECT IDENTIFIER ::= { tmnxSASMAgentV9v0  26 }
-- tmnxSASMDs1V9v0                OBJECT IDENTIFIER ::= { tmnxSASMAgentV9v0  27 }
-- tmnxSASMMcRedundancyV9v0       OBJECT IDENTIFIER ::= { tmnxSASMAgentV9v0  30 }
-- tmnxSASMBgpV9v0                OBJECT IDENTIFIER ::= { tmnxSASMAgentV9v0  31 }
-- tmnxSASMPimV9v0                OBJECT IDENTIFIER ::= { tmnxSASMAgentV9v0  33 }
-- tmnxSASMIgmpV9v0               OBJECT IDENTIFIER ::= { tmnxSASMAgentV9v0  34 }

  tmnxSASMxpAgentV9v0      OBJECT IDENTIFIER ::= { tmnxSASAgentCapsV9v0  7 }
-- tmnxSASMxpIgmpSnoopingV9v0     OBJECT IDENTIFIER ::= { tmnxSASMxpAgentV9v0   2 }
-- tmnxSASMxpIsisV9v0             OBJECT IDENTIFIER ::= { tmnxSASMxpAgentV9v0   8 }
-- tmnxSASMxpLdpV9v0              OBJECT IDENTIFIER ::= { tmnxSASMxpAgentV9v0   9 }
-- tmnxSASMxpOspfV9v0             OBJECT IDENTIFIER ::= { tmnxSASMxpAgentV9v0  12 }
-- tmnxSASMxpDot1agCfmV9v0        OBJECT IDENTIFIER ::= { tmnxSASMxpAgentV9v0  23 }
-- tmnxSASMxpBgpV9v0              OBJECT IDENTIFIER ::= { tmnxSASMxpAgentV9v0  31 }

  tmnxSASSxAgentV9v0       OBJECT IDENTIFIER ::= { tmnxSASAgentCapsV9v0  8 }
-- tmnxSASSxIgmpSnoopingV9v0      OBJECT IDENTIFIER ::= { tmnxSASSxAgentV9v0   2 }
-- tmnxSASSxDot1agCfmV9v0         OBJECT IDENTIFIER ::= { tmnxSASSxAgentV9v0  23 }

  tmnxSASKAgentV9v0        OBJECT IDENTIFIER ::= { tmnxSASAgentCapsV9v0  9 }
-- tmnxSASKIgmpSnoopingV9v0       OBJECT IDENTIFIER ::= { tmnxSASKAgentV9v0   2 }
-- tmnxSASKRsvpV9v0               OBJECT IDENTIFIER ::= { tmnxSASKAgentV9v0  13 }
-- tmnxSASKDot1agCfmV9v0          OBJECT IDENTIFIER ::= { tmnxSASKAgentV9v0  23 }
--
-- SAS ALARM_INPUT CAPABILITIES
--
tmnxSASAlarmInputV9v0             AGENT-CAPABILITIES
    PRODUCT-RELEASE "Alcatel-Lucent SAS"
    STATUS          current
    DESCRIPTION
         "Implementation of alarm input capabilities for Alcatel-Lucent SAS
          systems release 9.0."

    SUPPORTS        TIMETRA-SAS-ALARM-INPUT-MIB
        INCLUDES {
           tmnxAlarmInputNotificationV2v0Group,
           tmnxSASAlarmInputV2v0Group
        }

        VARIATION   tmnxSasAlarmInputPowerStatus
            ACCESS  not-implemented
            DESCRIPTION
                 "Not supported.

                  Not supported."

        VARIATION   tmnxSasAlarmOutputSeverity
            SYNTAX  INTEGER {
                       none(1),
                       major(3),
                       critical(4)
                    }
            DESCRIPTION
                 "SAS-E and SAS-R do not support minor(2).

                  SAS-E and SAS-R do not support minor(2)."

    ::= { tmnxSASAgentV9v0  29 }

--
-- SAS ALARM_INPUT CAPABILITIES
--
tmnxSASAlarmInputV9v0             AGENT-CAPABILITIES
    PRODUCT-RELEASE "Alcatel-Lucent SAS"
    STATUS          current
    DESCRIPTION
         "Implementation of alarm input capabilities for Alcatel-Lucent SAS
          systems release 9.0."

    SUPPORTS        TIMETRA-SAS-ALARM-INPUT-MIB
        INCLUDES {
           tmnxAlarmInputNotificationV2v0Group,
           tmnxSASAlarmInputV2v0Group
        }

        VARIATION   tmnxSasAlarmInputPowerStatus
            ACCESS  not-implemented
            DESCRIPTION
                 "Not supported.

                  Not supported."

        VARIATION   tmnxSasAlarmOutputSeverity
            SYNTAX  INTEGER {
                       none(1),
                       major(3),
                       critical(4)
                    }
            DESCRIPTION
                 "SAS-E and SAS-R do not support minor(2).

                  SAS-E and SAS-R do not support minor(2)."

    ::= { tmnxSASAgentV9v0  29 }

--
-- SASR BGP CAPABILITIES
--
tmnxSASRBgpV9v0                   AGENT-CAPABILITIES
    PRODUCT-RELEASE "Alcatel-Lucent SAS"
    STATUS          current
    DESCRIPTION
         "Implementation of BGP functions for Alcatel-Lucent SASR systems
          release 9.0."

    SUPPORTS        BGP4-MIB
        INCLUDES {
           bgp4MIBGlobalsGroup,
           bgp4MIBNotificationGroup,
           bgp4MIBPathAttrGroup,
           bgp4MIBPeerGroup
        }

        VARIATION   bgpBackwardTransition
            DESCRIPTION
                 "The bgpBackwardTransition notification has vRtrID appended to
                  the variable list."

        VARIATION   bgpEstablished
            DESCRIPTION
                 "The bgpEstablished notification has vRtrID appended to the
                  variable list."

        VARIATION   bgpPeerMinASOriginationInterval
            SYNTAX  INTEGER (1..255)
            DESCRIPTION
                 "The maximum supported value for
                  bgpPeerMinASOriginationInterval is 255 seconds."

        VARIATION   bgpPeerMinRouteAdvertisementInterval
            SYNTAX  INTEGER (1..255)
            DESCRIPTION
                 "The maximum supported value for
                  bgpPeerMinRouteAdvertisementInterval is 255 seconds."

    SUPPORTS        TIMETRA-BGP-MIB
        INCLUDES {
           tmnxBgp4ByteASNV7v0Group,
           tmnxBgp4PathAttrGroup,
           tmnxBgpAddPathV9v0R4Group,
           tmnxBgpDisableCapNegoV9v0Group,
           tmnxBgpFlowSpecV9v0Group,
           tmnxBgpGlobalV10v0Group,
           tmnxBgpInstanceParamsV5v0Group,
           tmnxBgpInstanceParamsV6v0Group,
           tmnxBgpInstanceV8v0Group,
           tmnxBgpNotificationV7v0Group,
           tmnxBgpNotifyObjsV7v0Group,
           tmnxBgpPeerGroupParamsV5v0Group,
           tmnxBgpPeerGroupParamsV6v0Group,
           tmnxBgpPeerGroupV11v0Group,
           tmnxBgpPeerParamsV5v0Group,
           tmnxBgpPeerParamsV6v0Group,
           tmnxBgpPeerV8v0Group,
           tmnxBgpPeerV9v0Group,
           tmnxBgpPeeringPlcyV10v0Group,
           tmnxBgpPeeringPolicyV10v0Group,
           tmnxBgpRTConstraintV10v0Group
        }

        VARIATION   tBgpConfederation4BytTblLstChngd
            ACCESS  not-implemented
            DESCRIPTION
                 "tBgpConfederation4BytTblLstChngd is not implemented."

        VARIATION   tBgpConfederation4ByteTable
            ACCESS  not-implemented
            DESCRIPTION
                 "tBgpConfederation4ByteTable is not implemented."

        VARIATION   tBgpConfederationTable
            ACCESS  not-implemented
            DESCRIPTION
                 "tBgpConfederationTable is not implemented."

        VARIATION   tBgpConfederationTableLastChanged
            ACCESS  not-implemented
            DESCRIPTION
                 "tBgpConfederationTableLastChanged is not implemented."

        VARIATION   tBgpInstRemovePrivateSkipPeerAs
            ACCESS  not-implemented
            DESCRIPTION
                 "Not supported."

        VARIATION   tBgpInstRteTargetTable
            ACCESS  not-implemented
            DESCRIPTION
                 "tBgpInstRteTargetTable is not implemented."

        VARIATION   tBgpInstanceAllowInterAsVpn
            ACCESS  not-implemented
            DESCRIPTION
                 "Not supported."

        VARIATION   tBgpInstanceClusterId
            ACCESS  not-implemented
            DESCRIPTION
                 "tBgpInstanceClusterId is not implemented."

        VARIATION   tBgpInstanceConfederationAS4Byte
            ACCESS  not-implemented
            DESCRIPTION
                 "tBgpInstanceConfederationAS4Byte is not implemented."

        VARIATION   tBgpInstanceDisableClientReflect
            ACCESS  not-implemented
            DESCRIPTION
                 "tBgpInstanceDisableClientReflect is not implemented."

        VARIATION   tBgpInstanceDisallowIgp
            ACCESS  not-implemented
            DESCRIPTION
                 "tBgpInstanceDisallowIgp is not implemented."

        VARIATION   tBgpInstanceGRAdminState
            ACCESS  read-only
            DESCRIPTION
                 "tBgpInstanceGRAdminState is implemented as read only.

                  Not supported."

        VARIATION   tBgpInstanceGROperState
            ACCESS  not-implemented
            DESCRIPTION
                 "Not supported."

        VARIATION   tBgpInstanceGRPathSelectDefer
            ACCESS  read-only
            DESCRIPTION
                 "tBgpInstanceGRPathSelectDefer is implemented as read only.

                  Not supported."

        VARIATION   tBgpInstanceGRRestartTime
            ACCESS  read-only
            DESCRIPTION
                 "tBgpInstanceGRRestartTime is implemented as read only.

                  Not supported."

        VARIATION   tBgpInstanceGRStaleRoute
            ACCESS  not-implemented
            DESCRIPTION
                 "Not supported."

        VARIATION   tBgpInstanceGracefulRestart
            ACCESS  not-implemented
            DESCRIPTION
                 "Not supported."

        VARIATION   tBgpInstanceIBgpMultipath
            ACCESS  not-implemented
            DESCRIPTION
                 "tBgpInstanceIBgpMultipath is not implemented.

                  tBgpInstanceIBgpMultipath is not implemented."

        VARIATION   tBgpInstanceIgnoreNextHopMetric
            ACCESS  not-implemented
            DESCRIPTION
                 "Not supported."

        VARIATION   tBgpInstanceIgnoreRouterId
            ACCESS  not-implemented
            DESCRIPTION
                 "Not supported."

        VARIATION   tBgpInstanceIgpShortcut
            ACCESS  not-implemented
            DESCRIPTION
                 "tBgpInstanceIgpShortcut is not implemented."

        VARIATION   tBgpInstanceMpBgpKeep
            ACCESS  not-implemented
            DESCRIPTION
                 "Not supported."

        VARIATION   tBgpInstanceMultipath
            ACCESS  not-implemented
            DESCRIPTION
                 "tBgpInstanceMultipath is not implemented."

        VARIATION   tBgpInstanceMultipathEiBgpState
            ACCESS  not-implemented
            DESCRIPTION
                 "tBgpInstanceMultipathEiBgpState is not implemented."

        VARIATION   tBgpInstanceNHResUseBgpRoutes
            ACCESS  not-implemented
            DESCRIPTION
                 "Not supported."

        VARIATION   tBgpNgBackwardTransition
            DESCRIPTION
                 "The tBgpNgBackwardTransition notification has vRtrID appended
                  to the variable list."

        VARIATION   tBgpNgEstablished
            DESCRIPTION
                 "The tBgpNgEstablished notification has vRtrID appended to the
                  variable list."

        VARIATION   tBgpPGAigp
            ACCESS  not-implemented
            DESCRIPTION
                 "Not supported."

        VARIATION   tBgpPGDefaultRouteTarget
            ACCESS  not-implemented
            DESCRIPTION
                 "Not supported."

        VARIATION   tBgpPGMinTTLValue
            ACCESS  not-implemented
            DESCRIPTION
                 "Not supported."

        VARIATION   tBgpPGRemovePrivateSkipPeerAs
            ACCESS  not-implemented
            DESCRIPTION
                 "Not supported."

        VARIATION   tBgpPGTTLLogId
            ACCESS  not-implemented
            DESCRIPTION
                 "tBgpPGTTLLogId is not implemented."

        VARIATION   tBgpPeerGRAdminState
            ACCESS  read-only
            DESCRIPTION
                 "tBgpPeerNgGRAdminState is implemented as read only.

                  Not supported."

        VARIATION   tBgpPeerGROperState
            ACCESS  not-implemented
            DESCRIPTION
                 "Not supported."

        VARIATION   tBgpPeerGRRestartTime
            ACCESS  not-implemented
            DESCRIPTION
                 "Not supported."

        VARIATION   tBgpPeerGRStaleRoute
            ACCESS  not-implemented
            DESCRIPTION
                 "Not supported."

        VARIATION   tBgpPeerGracefulRestart
            ACCESS  not-implemented
            DESCRIPTION
                 "Not supported."

        VARIATION   tBgpPeerGroupClusterId
            ACCESS  not-implemented
            DESCRIPTION
                 "tBgpPeerGroupClusterId is not implemented."

        VARIATION   tBgpPeerGroupDisableClientReflect
            ACCESS  not-implemented
            DESCRIPTION
                 "tBgpPeerGroupDisableClientReflect is not implemented."

        VARIATION   tBgpPeerGroupGRAdminState
            ACCESS  read-only
            DESCRIPTION
                 "tBgpPeerGroupGRAdminState is implemented as read only.

                  Not supported."

        VARIATION   tBgpPeerGroupGROperState
            ACCESS  not-implemented
            DESCRIPTION
                 "Not supported."

        VARIATION   tBgpPeerGroupGRRestartTime
            ACCESS  not-implemented
            DESCRIPTION
                 "Not supported."

        VARIATION   tBgpPeerGroupGRStaleRoute
            ACCESS  not-implemented
            DESCRIPTION
                 "Not supported."

        VARIATION   tBgpPeerGroupGracefulRestart
            ACCESS  not-implemented
            DESCRIPTION
                 "Not supported."

        VARIATION   tBgpPeerNgAigp
            ACCESS  not-implemented
            DESCRIPTION
                 "Not supported."

        VARIATION   tBgpPeerNgClusterId
            ACCESS  not-implemented
            DESCRIPTION
                 "tBgpPeerNgClusterId is not implemented."

        VARIATION   tBgpPeerNgDefaultRouteTarget
            ACCESS  not-implemented
            DESCRIPTION
                 "Not supported."

        VARIATION   tBgpPeerNgDisableClientReflect
            ACCESS  not-implemented
            DESCRIPTION
                 "tBgpPeerNgDisableClientReflect is not implemented."

        VARIATION   tBgpPeerNgGRAdminState
            ACCESS  not-implemented
            DESCRIPTION
                 "Not supported."

        VARIATION   tBgpPeerNgGROperState
            ACCESS  not-implemented
            DESCRIPTION
                 "Not supported."

        VARIATION   tBgpPeerNgGRRestartTime
            ACCESS  not-implemented
            DESCRIPTION
                 "Not supported."

        VARIATION   tBgpPeerNgGRStaleRoute
            ACCESS  not-implemented
            DESCRIPTION
                 "Not supported."

        VARIATION   tBgpPeerNgGracefulRestart
            ACCESS  not-implemented
            DESCRIPTION
                 "Not supported."

        VARIATION   tBgpPeerNgMinTTLValue
            ACCESS  not-implemented
            DESCRIPTION
                 "Not supported."

        VARIATION   tBgpPeerNgOperGRFamilyFwding
            ACCESS  not-implemented
            DESCRIPTION
                 "Not supported."

        VARIATION   tBgpPeerNgOperGRFamilyNegotiated
            ACCESS  not-implemented
            DESCRIPTION
                 "Not supported."

        VARIATION   tBgpPeerNgOperGRFamilyRestart
            ACCESS  not-implemented
            DESCRIPTION
                 "Not supported."

        VARIATION   tBgpPeerNgOperGRRecvEOR
            ACCESS  not-implemented
            DESCRIPTION
                 "Not supported."

        VARIATION   tBgpPeerNgOperGRReqRestartTime
            ACCESS  not-implemented
            DESCRIPTION
                 "Not supported."

        VARIATION   tBgpPeerNgOperGRSendEOR
            ACCESS  not-implemented
            DESCRIPTION
                 "Not supported."

        VARIATION   tBgpPeerNgOperGRStaleRoutesTime
            ACCESS  not-implemented
            DESCRIPTION
                 "Not supported."

        VARIATION   tBgpPeerNgOperGRStatus
            ACCESS  not-implemented
            DESCRIPTION
                 "Not supported."

        VARIATION   tBgpPeerNgOperGRSupport
            ACCESS  not-implemented
            DESCRIPTION
                 "Not supported."

        VARIATION   tBgpPeerNgOperMCastV4ActivePfxs
            ACCESS  not-implemented
            DESCRIPTION
                 "tBgpPeerNgOperMCastV4ActivePfxs is not implemented."

        VARIATION   tBgpPeerNgOperMCastV4RecvPfxs
            ACCESS  not-implemented
            DESCRIPTION
                 "tBgpPeerNgOperMCastV4RecvPfxs is not implemented."

        VARIATION   tBgpPeerNgOperMCastV4SentPfxs
            ACCESS  not-implemented
            DESCRIPTION
                 "tBgpPeerNgOperMCastV4SentPfxs is not implemented."

        VARIATION   tBgpPeerNgOperMCastV4SuppPfxDamp
            ACCESS  not-implemented
            DESCRIPTION
                 "tBgpPeerNgOperMCastV4SuppPfxDamp is not implemented."

        VARIATION   tBgpPeerNgOperMcastVpnV4ActPfxs
            ACCESS  not-implemented
            DESCRIPTION
                 "Not supported."

        VARIATION   tBgpPeerNgOperMcastVpnV4RecvPfxs
            ACCESS  not-implemented
            DESCRIPTION
                 "Not supported."

        VARIATION   tBgpPeerNgOperMcastVpnV4SentPfxs
            ACCESS  not-implemented
            DESCRIPTION
                 "Not supported."

        VARIATION   tBgpPeerNgOperMvpnV4ActivePfxs
            ACCESS  not-implemented
            DESCRIPTION
                 "tBgpPeerNgOperMvpnV4ActivePfxs is not implemented."

        VARIATION   tBgpPeerNgOperMvpnV4RecvPfxs
            ACCESS  not-implemented
            DESCRIPTION
                 "tBgpPeerNgOperMvpnV4RecvPfxs is not implemented."

        VARIATION   tBgpPeerNgOperMvpnV4SentPfxs
            ACCESS  not-implemented
            DESCRIPTION
                 "tBgpPeerNgOperMvpnV4SentPfxs is not implemented."

        VARIATION   tBgpPeerNgOperMvpnV4SuppPfxDamp
            ACCESS  not-implemented
            DESCRIPTION
                 "tBgpPeerNgOperMvpnV4SuppPfxDamp is not implemented."

        VARIATION   tBgpPeerNgOperRtTgtActivePfxs
            ACCESS  not-implemented
            DESCRIPTION
                 "Not supported."

        VARIATION   tBgpPeerNgOperRtTgtRecvPfxs
            ACCESS  not-implemented
            DESCRIPTION
                 "Not supported."

        VARIATION   tBgpPeerNgOperRtTgtSentPfxs
            ACCESS  not-implemented
            DESCRIPTION
                 "Not supported."

        VARIATION   tBgpPeerNgOperRtTgtSuppPfxDamp
            ACCESS  not-implemented
            DESCRIPTION
                 "Not supported."

        VARIATION   tBgpPeerNgOperV6ActivePrefixes
            ACCESS  not-implemented
            DESCRIPTION
                 "tBgpPeerNgOperV6ActivePrefixes is not implemented."

        VARIATION   tBgpPeerNgOperV6ReceivedPaths
            ACCESS  not-implemented
            DESCRIPTION
                 "tBgpPeerNgOperV6ReceivedPaths is not implemented."

        VARIATION   tBgpPeerNgOperV6ReceivedPrefixes
            ACCESS  not-implemented
            DESCRIPTION
                 "tBgpPeerNgOperV6ReceivedPrefixes is not implemented."

        VARIATION   tBgpPeerNgOperV6SentPrefixes
            ACCESS  not-implemented
            DESCRIPTION
                 "tBgpPeerNgOperV6SentPrefixes is not implemented."

        VARIATION   tBgpPeerNgOperV6SuppPathsDamping
            ACCESS  not-implemented
            DESCRIPTION
                 "tBgpPeerNgOperV6SuppPathsDamping is not implemented."

        VARIATION   tBgpPeerNgOperV6SuppPfxDamp
            ACCESS  not-implemented
            DESCRIPTION
                 "tBgpPeerNgOperV6SuppPfxDamp is not implemented."

        VARIATION   tBgpPeerNgOperVpnIpv6ActivePfxs
            ACCESS  not-implemented
            DESCRIPTION
                 "tBgpPeerNgOperVpnIpv6ActivePfxs is not implemented."

        VARIATION   tBgpPeerNgOperVpnIpv6RecvPfxs
            ACCESS  not-implemented
            DESCRIPTION
                 "tBgpPeerNgOperVpnIpv6RecvPfxs is not implemented."

        VARIATION   tBgpPeerNgOperVpnIpv6SentPfxs
            ACCESS  not-implemented
            DESCRIPTION
                 "tBgpPeerNgOperVpnIpv6SentPfxs is not implemented."

        VARIATION   tBgpPeerNgOperVpnIpv6SuppPfxDamp
            ACCESS  not-implemented
            DESCRIPTION
                 "tBgpPeerNgOperVpnIpv6SuppPfxDamp is not implemented."

        VARIATION   tBgpPeerNgOperVpnV4BackupPfxs
            ACCESS  not-implemented
            DESCRIPTION
                 "Not supported."

        VARIATION   tBgpPeerNgOperVpnV6BackupPfxs
            ACCESS  not-implemented
            DESCRIPTION
                 "Not supported."

        VARIATION   tBgpPeerNgRemPrivateSkipPeerAs
            ACCESS  not-implemented
            DESCRIPTION
                 "Not supported."

        VARIATION   tBgpPeerNgSplitHorizon
            ACCESS  not-implemented
            DESCRIPTION
                 "Not supported."

        VARIATION   tBgpPeerOperGRFamilyFwding
            ACCESS  not-implemented
            DESCRIPTION
                 "Not supported."

        VARIATION   tBgpPeerOperGRFamilyNegotiated
            ACCESS  not-implemented
            DESCRIPTION
                 "Not supported."

        VARIATION   tBgpPeerOperGRFamilyRestart
            ACCESS  not-implemented
            DESCRIPTION
                 "Not supported."

        VARIATION   tBgpPeerOperGRRecvEOR
            ACCESS  not-implemented
            DESCRIPTION
                 "Not supported."

        VARIATION   tBgpPeerOperGRRequestRestartTime
            ACCESS  not-implemented
            DESCRIPTION
                 "Not supported."

        VARIATION   tBgpPeerOperGRSendEOR
            ACCESS  not-implemented
            DESCRIPTION
                 "Not supported."

        VARIATION   tBgpPeerOperGRStaleRoutesTime
            ACCESS  not-implemented
            DESCRIPTION
                 "Not supported."

        VARIATION   tBgpPeerOperGRStatus
            ACCESS  not-implemented
            DESCRIPTION
                 "Not supported."

        VARIATION   tBgpPeerOperGRSupport
            ACCESS  not-implemented
            DESCRIPTION
                 "Not supported."

    ::= { tmnxSASRAgentV9v0  31 }

--
-- SASX BGP CAPABILITIES
--
tmnxSASXBgpV9v0                   AGENT-CAPABILITIES
    PRODUCT-RELEASE "Alcatel-Lucent SAS"
    STATUS          current
    DESCRIPTION
         "Implementation of BGP functions for Alcatel-Lucent SASX systems
          release 9.0."

    SUPPORTS        BGP4-MIB
        INCLUDES {
           bgp4MIBGlobalsGroup,
           bgp4MIBNotificationGroup,
           bgp4MIBPathAttrGroup,
           bgp4MIBPeerGroup
        }

        VARIATION   bgpBackwardTransition
            DESCRIPTION
                 "The bgpBackwardTransition notification has vRtrID appended to
                  the variable list."

        VARIATION   bgpEstablished
            DESCRIPTION
                 "The bgpEstablished notification has vRtrID appended to the
                  variable list."

        VARIATION   bgpPeerMinASOriginationInterval
            SYNTAX  INTEGER (1..255)
            DESCRIPTION
                 "The maximum supported value for
                  bgpPeerMinASOriginationInterval is 255 seconds."

        VARIATION   bgpPeerMinRouteAdvertisementInterval
            SYNTAX  INTEGER (1..255)
            DESCRIPTION
                 "The maximum supported value for
                  bgpPeerMinRouteAdvertisementInterval is 255 seconds."

    SUPPORTS        TIMETRA-BGP-MIB
        INCLUDES {
           tmnxBgp4ByteASNV7v0Group,
           tmnxBgp4PathAttrGroup,
           tmnxBgpAddPathV9v0R4Group,
           tmnxBgpDisableCapNegoV9v0Group,
           tmnxBgpFlowSpecV9v0Group,
           tmnxBgpGlobalV10v0Group,
           tmnxBgpInstanceParamsV5v0Group,
           tmnxBgpInstanceParamsV6v0Group,
           tmnxBgpInstanceV8v0Group,
           tmnxBgpNotificationV7v0Group,
           tmnxBgpNotifyObjsV7v0Group,
           tmnxBgpPeerGroupParamsV5v0Group,
           tmnxBgpPeerGroupParamsV6v0Group,
           tmnxBgpPeerGroupV11v0Group,
           tmnxBgpPeerParamsV5v0Group,
           tmnxBgpPeerParamsV6v0Group,
           tmnxBgpPeerV8v0Group,
           tmnxBgpPeerV9v0Group,
           tmnxBgpPeeringPlcyV10v0Group,
           tmnxBgpPeeringPolicyV10v0Group,
           tmnxBgpRTConstraintV10v0Group
        }

        VARIATION   tBgpConfederation4BytTblLstChngd
            ACCESS  not-implemented
            DESCRIPTION
                 "tBgpConfederation4BytTblLstChngd is not implemented."

        VARIATION   tBgpConfederation4ByteTable
            ACCESS  not-implemented
            DESCRIPTION
                 "tBgpConfederation4ByteTable is not implemented."

        VARIATION   tBgpConfederationTable
            ACCESS  not-implemented
            DESCRIPTION
                 "tBgpConfederationTable is not implemented."

        VARIATION   tBgpConfederationTableLastChanged
            ACCESS  not-implemented
            DESCRIPTION
                 "tBgpConfederationTableLastChanged is not implemented."

        VARIATION   tBgpInstRemovePrivateSkipPeerAs
            ACCESS  not-implemented
            DESCRIPTION
                 "Not supported."

        VARIATION   tBgpInstRteTargetTable
            ACCESS  not-implemented
            DESCRIPTION
                 "tBgpInstRteTargetTable is not implemented."

        VARIATION   tBgpInstanceAllowInterAsVpn
            ACCESS  not-implemented
            DESCRIPTION
                 "Not supported."

        VARIATION   tBgpInstanceClusterId
            ACCESS  not-implemented
            DESCRIPTION
                 "tBgpInstanceClusterId is not implemented."

        VARIATION   tBgpInstanceConfederationAS4Byte
            ACCESS  not-implemented
            DESCRIPTION
                 "tBgpInstanceConfederationAS4Byte is not implemented."

        VARIATION   tBgpInstanceDisableClientReflect
            ACCESS  not-implemented
            DESCRIPTION
                 "tBgpInstanceDisableClientReflect is not implemented."

        VARIATION   tBgpInstanceDisallowIgp
            ACCESS  not-implemented
            DESCRIPTION
                 "tBgpInstanceDisallowIgp is not implemented."

        VARIATION   tBgpInstanceGRAdminState
            ACCESS  read-only
            DESCRIPTION
                 "tBgpInstanceGRAdminState is implemented as read only.

                  Not supported."

        VARIATION   tBgpInstanceGROperState
            ACCESS  not-implemented
            DESCRIPTION
                 "Not supported."

        VARIATION   tBgpInstanceGRPathSelectDefer
            ACCESS  read-only
            DESCRIPTION
                 "tBgpInstanceGRPathSelectDefer is implemented as read only.

                  Not supported."

        VARIATION   tBgpInstanceGRRestartTime
            ACCESS  read-only
            DESCRIPTION
                 "tBgpInstanceGRRestartTime is implemented as read only.

                  Not supported."

        VARIATION   tBgpInstanceGRStaleRoute
            ACCESS  not-implemented
            DESCRIPTION
                 "Not supported."

        VARIATION   tBgpInstanceGracefulRestart
            ACCESS  not-implemented
            DESCRIPTION
                 "Not supported."

        VARIATION   tBgpInstanceIBgpMultipath
            ACCESS  not-implemented
            DESCRIPTION
                 "tBgpInstanceIBgpMultipath is not implemented.

                  tBgpInstanceIBgpMultipath is not implemented."

        VARIATION   tBgpInstanceIgnoreNextHopMetric
            ACCESS  not-implemented
            DESCRIPTION
                 "Not supported."

        VARIATION   tBgpInstanceIgnoreRouterId
            ACCESS  not-implemented
            DESCRIPTION
                 "Not supported."

        VARIATION   tBgpInstanceIgpShortcut
            ACCESS  not-implemented
            DESCRIPTION
                 "tBgpInstanceIgpShortcut is not implemented."

        VARIATION   tBgpInstanceMpBgpKeep
            ACCESS  not-implemented
            DESCRIPTION
                 "Not supported."

        VARIATION   tBgpInstanceMultipath
            ACCESS  not-implemented
            DESCRIPTION
                 "tBgpInstanceMultipath is not implemented."

        VARIATION   tBgpInstanceMultipathEiBgpState
            ACCESS  not-implemented
            DESCRIPTION
                 "tBgpInstanceMultipathEiBgpState is not implemented."

        VARIATION   tBgpInstanceNHResUseBgpRoutes
            ACCESS  not-implemented
            DESCRIPTION
                 "Not supported."

        VARIATION   tBgpNgBackwardTransition
            DESCRIPTION
                 "The tBgpNgBackwardTransition notification has vRtrID appended
                  to the variable list."

        VARIATION   tBgpNgEstablished
            DESCRIPTION
                 "The tBgpNgEstablished notification has vRtrID appended to the
                  variable list."

        VARIATION   tBgpPGAigp
            ACCESS  not-implemented
            DESCRIPTION
                 "Not supported."

        VARIATION   tBgpPGDefaultRouteTarget
            ACCESS  not-implemented
            DESCRIPTION
                 "Not supported."

        VARIATION   tBgpPGMinTTLValue
            ACCESS  not-implemented
            DESCRIPTION
                 "Not supported."

        VARIATION   tBgpPGRemovePrivateSkipPeerAs
            ACCESS  not-implemented
            DESCRIPTION
                 "Not supported."

        VARIATION   tBgpPGTTLLogId
            ACCESS  not-implemented
            DESCRIPTION
                 "tBgpPGTTLLogId is not implemented."

        VARIATION   tBgpPeerGRAdminState
            ACCESS  read-only
            DESCRIPTION
                 "tBgpPeerNgGRAdminState is implemented as read only.

                  Not supported."

        VARIATION   tBgpPeerGROperState
            ACCESS  not-implemented
            DESCRIPTION
                 "Not supported."

        VARIATION   tBgpPeerGRRestartTime
            ACCESS  not-implemented
            DESCRIPTION
                 "Not supported."

        VARIATION   tBgpPeerGRStaleRoute
            ACCESS  not-implemented
            DESCRIPTION
                 "Not supported."

        VARIATION   tBgpPeerGracefulRestart
            ACCESS  not-implemented
            DESCRIPTION
                 "Not supported."

        VARIATION   tBgpPeerGroupClusterId
            ACCESS  not-implemented
            DESCRIPTION
                 "tBgpPeerGroupClusterId is not implemented."

        VARIATION   tBgpPeerGroupDisableClientReflect
            ACCESS  not-implemented
            DESCRIPTION
                 "tBgpPeerGroupDisableClientReflect is not implemented."

        VARIATION   tBgpPeerGroupGRAdminState
            ACCESS  read-only
            DESCRIPTION
                 "tBgpPeerGroupGRAdminState is implemented as read only.

                  Not supported."

        VARIATION   tBgpPeerGroupGROperState
            ACCESS  not-implemented
            DESCRIPTION
                 "Not supported."

        VARIATION   tBgpPeerGroupGRRestartTime
            ACCESS  not-implemented
            DESCRIPTION
                 "Not supported."

        VARIATION   tBgpPeerGroupGRStaleRoute
            ACCESS  not-implemented
            DESCRIPTION
                 "Not supported."

        VARIATION   tBgpPeerGroupGracefulRestart
            ACCESS  not-implemented
            DESCRIPTION
                 "Not supported."

        VARIATION   tBgpPeerNgAigp
            ACCESS  not-implemented
            DESCRIPTION
                 "Not supported."

        VARIATION   tBgpPeerNgClusterId
            ACCESS  not-implemented
            DESCRIPTION
                 "tBgpPeerNgClusterId is not implemented."

        VARIATION   tBgpPeerNgDefaultRouteTarget
            ACCESS  not-implemented
            DESCRIPTION
                 "Not supported."

        VARIATION   tBgpPeerNgDisableClientReflect
            ACCESS  not-implemented
            DESCRIPTION
                 "tBgpPeerNgDisableClientReflect is not implemented."

        VARIATION   tBgpPeerNgGRAdminState
            ACCESS  not-implemented
            DESCRIPTION
                 "Not supported."

        VARIATION   tBgpPeerNgGROperState
            ACCESS  not-implemented
            DESCRIPTION
                 "Not supported."

        VARIATION   tBgpPeerNgGRRestartTime
            ACCESS  not-implemented
            DESCRIPTION
                 "Not supported."

        VARIATION   tBgpPeerNgGRStaleRoute
            ACCESS  not-implemented
            DESCRIPTION
                 "Not supported."

        VARIATION   tBgpPeerNgGracefulRestart
            ACCESS  not-implemented
            DESCRIPTION
                 "Not supported."

        VARIATION   tBgpPeerNgMinTTLValue
            ACCESS  not-implemented
            DESCRIPTION
                 "Not supported."

        VARIATION   tBgpPeerNgOperGRFamilyFwding
            ACCESS  not-implemented
            DESCRIPTION
                 "Not supported."

        VARIATION   tBgpPeerNgOperGRFamilyNegotiated
            ACCESS  not-implemented
            DESCRIPTION
                 "Not supported."

        VARIATION   tBgpPeerNgOperGRFamilyRestart
            ACCESS  not-implemented
            DESCRIPTION
                 "Not supported."

        VARIATION   tBgpPeerNgOperGRRecvEOR
            ACCESS  not-implemented
            DESCRIPTION
                 "Not supported."

        VARIATION   tBgpPeerNgOperGRReqRestartTime
            ACCESS  not-implemented
            DESCRIPTION
                 "Not supported."

        VARIATION   tBgpPeerNgOperGRSendEOR
            ACCESS  not-implemented
            DESCRIPTION
                 "Not supported."

        VARIATION   tBgpPeerNgOperGRStaleRoutesTime
            ACCESS  not-implemented
            DESCRIPTION
                 "Not supported."

        VARIATION   tBgpPeerNgOperGRStatus
            ACCESS  not-implemented
            DESCRIPTION
                 "Not supported."

        VARIATION   tBgpPeerNgOperGRSupport
            ACCESS  not-implemented
            DESCRIPTION
                 "Not supported."

        VARIATION   tBgpPeerNgOperMCastV4ActivePfxs
            ACCESS  not-implemented
            DESCRIPTION
                 "tBgpPeerNgOperMCastV4ActivePfxs is not implemented."

        VARIATION   tBgpPeerNgOperMCastV4RecvPfxs
            ACCESS  not-implemented
            DESCRIPTION
                 "tBgpPeerNgOperMCastV4RecvPfxs is not implemented."

        VARIATION   tBgpPeerNgOperMCastV4SentPfxs
            ACCESS  not-implemented
            DESCRIPTION
                 "tBgpPeerNgOperMCastV4SentPfxs is not implemented."

        VARIATION   tBgpPeerNgOperMCastV4SuppPfxDamp
            ACCESS  not-implemented
            DESCRIPTION
                 "tBgpPeerNgOperMCastV4SuppPfxDamp is not implemented."

        VARIATION   tBgpPeerNgOperMcastVpnV4ActPfxs
            ACCESS  not-implemented
            DESCRIPTION
                 "Not supported."

        VARIATION   tBgpPeerNgOperMcastVpnV4RecvPfxs
            ACCESS  not-implemented
            DESCRIPTION
                 "Not supported."

        VARIATION   tBgpPeerNgOperMcastVpnV4SentPfxs
            ACCESS  not-implemented
            DESCRIPTION
                 "Not supported."

        VARIATION   tBgpPeerNgOperMvpnV4ActivePfxs
            ACCESS  not-implemented
            DESCRIPTION
                 "tBgpPeerNgOperMvpnV4ActivePfxs is not implemented."

        VARIATION   tBgpPeerNgOperMvpnV4RecvPfxs
            ACCESS  not-implemented
            DESCRIPTION
                 "tBgpPeerNgOperMvpnV4RecvPfxs is not implemented."

        VARIATION   tBgpPeerNgOperMvpnV4SentPfxs
            ACCESS  not-implemented
            DESCRIPTION
                 "tBgpPeerNgOperMvpnV4SentPfxs is not implemented."

        VARIATION   tBgpPeerNgOperMvpnV4SuppPfxDamp
            ACCESS  not-implemented
            DESCRIPTION
                 "tBgpPeerNgOperMvpnV4SuppPfxDamp is not implemented."

        VARIATION   tBgpPeerNgOperRtTgtActivePfxs
            ACCESS  not-implemented
            DESCRIPTION
                 "Not supported."

        VARIATION   tBgpPeerNgOperRtTgtRecvPfxs
            ACCESS  not-implemented
            DESCRIPTION
                 "Not supported."

        VARIATION   tBgpPeerNgOperRtTgtSentPfxs
            ACCESS  not-implemented
            DESCRIPTION
                 "Not supported."

        VARIATION   tBgpPeerNgOperRtTgtSuppPfxDamp
            ACCESS  not-implemented
            DESCRIPTION
                 "Not supported."

        VARIATION   tBgpPeerNgOperV6ActivePrefixes
            ACCESS  not-implemented
            DESCRIPTION
                 "tBgpPeerNgOperV6ActivePrefixes is not implemented."

        VARIATION   tBgpPeerNgOperV6ReceivedPaths
            ACCESS  not-implemented
            DESCRIPTION
                 "tBgpPeerNgOperV6ReceivedPaths is not implemented."

        VARIATION   tBgpPeerNgOperV6ReceivedPrefixes
            ACCESS  not-implemented
            DESCRIPTION
                 "tBgpPeerNgOperV6ReceivedPrefixes is not implemented."

        VARIATION   tBgpPeerNgOperV6SentPrefixes
            ACCESS  not-implemented
            DESCRIPTION
                 "tBgpPeerNgOperV6SentPrefixes is not implemented."

        VARIATION   tBgpPeerNgOperV6SuppPathsDamping
            ACCESS  not-implemented
            DESCRIPTION
                 "tBgpPeerNgOperV6SuppPathsDamping is not implemented."

        VARIATION   tBgpPeerNgOperV6SuppPfxDamp
            ACCESS  not-implemented
            DESCRIPTION
                 "tBgpPeerNgOperV6SuppPfxDamp is not implemented."

        VARIATION   tBgpPeerNgOperVpnIpv6ActivePfxs
            ACCESS  not-implemented
            DESCRIPTION
                 "tBgpPeerNgOperVpnIpv6ActivePfxs is not implemented."

        VARIATION   tBgpPeerNgOperVpnIpv6RecvPfxs
            ACCESS  not-implemented
            DESCRIPTION
                 "tBgpPeerNgOperVpnIpv6RecvPfxs is not implemented."

        VARIATION   tBgpPeerNgOperVpnIpv6SentPfxs
            ACCESS  not-implemented
            DESCRIPTION
                 "tBgpPeerNgOperVpnIpv6SentPfxs is not implemented."

        VARIATION   tBgpPeerNgOperVpnIpv6SuppPfxDamp
            ACCESS  not-implemented
            DESCRIPTION
                 "tBgpPeerNgOperVpnIpv6SuppPfxDamp is not implemented."

        VARIATION   tBgpPeerNgOperVpnV4BackupPfxs
            ACCESS  not-implemented
            DESCRIPTION
                 "Not supported."

        VARIATION   tBgpPeerNgOperVpnV6BackupPfxs
            ACCESS  not-implemented
            DESCRIPTION
                 "Not supported."

        VARIATION   tBgpPeerNgRemPrivateSkipPeerAs
            ACCESS  not-implemented
            DESCRIPTION
                 "Not supported."

        VARIATION   tBgpPeerNgSplitHorizon
            ACCESS  not-implemented
            DESCRIPTION
                 "Not supported."

        VARIATION   tBgpPeerOperGRFamilyFwding
            ACCESS  not-implemented
            DESCRIPTION
                 "Not supported."

        VARIATION   tBgpPeerOperGRFamilyNegotiated
            ACCESS  not-implemented
            DESCRIPTION
                 "Not supported."

        VARIATION   tBgpPeerOperGRFamilyRestart
            ACCESS  not-implemented
            DESCRIPTION
                 "Not supported."

        VARIATION   tBgpPeerOperGRRecvEOR
            ACCESS  not-implemented
            DESCRIPTION
                 "Not supported."

        VARIATION   tBgpPeerOperGRRequestRestartTime
            ACCESS  not-implemented
            DESCRIPTION
                 "Not supported."

        VARIATION   tBgpPeerOperGRSendEOR
            ACCESS  not-implemented
            DESCRIPTION
                 "Not supported."

        VARIATION   tBgpPeerOperGRStaleRoutesTime
            ACCESS  not-implemented
            DESCRIPTION
                 "Not supported."

        VARIATION   tBgpPeerOperGRStatus
            ACCESS  not-implemented
            DESCRIPTION
                 "Not supported."

        VARIATION   tBgpPeerOperGRSupport
            ACCESS  not-implemented
            DESCRIPTION
                 "Not supported."

    ::= { tmnxSASXAgentV9v0  31 }

--
-- SASM BGP CAPABILITIES
--
tmnxSASMBgpV9v0                   AGENT-CAPABILITIES
    PRODUCT-RELEASE "Alcatel-Lucent SAS"
    STATUS          current
    DESCRIPTION
         "Implementation of BGP functions for Alcatel-Lucent SASM systems
          release 9.0."

    SUPPORTS        BGP4-MIB
        INCLUDES {
           bgp4MIBGlobalsGroup,
           bgp4MIBNotificationGroup,
           bgp4MIBPathAttrGroup,
           bgp4MIBPeerGroup
        }

        VARIATION   bgpBackwardTransition
            DESCRIPTION
                 "The bgpBackwardTransition notification has vRtrID appended to
                  the variable list."

        VARIATION   bgpEstablished
            DESCRIPTION
                 "The bgpEstablished notification has vRtrID appended to the
                  variable list."

        VARIATION   bgpPeerMinASOriginationInterval
            SYNTAX  INTEGER (1..255)
            DESCRIPTION
                 "The maximum supported value for
                  bgpPeerMinASOriginationInterval is 255 seconds."

        VARIATION   bgpPeerMinRouteAdvertisementInterval
            SYNTAX  INTEGER (1..255)
            DESCRIPTION
                 "The maximum supported value for
                  bgpPeerMinRouteAdvertisementInterval is 255 seconds."

    SUPPORTS        TIMETRA-BGP-MIB
        INCLUDES {
           tmnxBgp4ByteASNV7v0Group,
           tmnxBgp4PathAttrGroup,
           tmnxBgpAddPathV9v0R4Group,
           tmnxBgpDisableCapNegoV9v0Group,
           tmnxBgpFlowSpecV9v0Group,
           tmnxBgpGlobalV10v0Group,
           tmnxBgpInstanceParamsV5v0Group,
           tmnxBgpInstanceParamsV6v0Group,
           tmnxBgpInstanceV8v0Group,
           tmnxBgpNotificationV7v0Group,
           tmnxBgpNotifyObjsV7v0Group,
           tmnxBgpPeerGroupParamsV5v0Group,
           tmnxBgpPeerGroupParamsV6v0Group,
           tmnxBgpPeerGroupV11v0Group,
           tmnxBgpPeerParamsV5v0Group,
           tmnxBgpPeerParamsV6v0Group,
           tmnxBgpPeerV8v0Group,
           tmnxBgpPeerV9v0Group,
           tmnxBgpPeeringPlcyV10v0Group,
           tmnxBgpPeeringPolicyV10v0Group,
           tmnxBgpRTConstraintV10v0Group
        }

        VARIATION   tBgpConfederation4BytTblLstChngd
            ACCESS  not-implemented
            DESCRIPTION
                 "tBgpConfederation4BytTblLstChngd is not implemented."

        VARIATION   tBgpConfederation4ByteTable
            ACCESS  not-implemented
            DESCRIPTION
                 "tBgpConfederation4ByteTable is not implemented."

        VARIATION   tBgpConfederationTable
            ACCESS  not-implemented
            DESCRIPTION
                 "tBgpConfederationTable is not implemented."

        VARIATION   tBgpConfederationTableLastChanged
            ACCESS  not-implemented
            DESCRIPTION
                 "tBgpConfederationTableLastChanged is not implemented."

        VARIATION   tBgpInstRemovePrivateSkipPeerAs
            ACCESS  not-implemented
            DESCRIPTION
                 "Not supported."

        VARIATION   tBgpInstRteTargetTable
            ACCESS  not-implemented
            DESCRIPTION
                 "tBgpInstRteTargetTable is not implemented."

        VARIATION   tBgpInstanceAllowInterAsVpn
            ACCESS  not-implemented
            DESCRIPTION
                 "Not supported."

        VARIATION   tBgpInstanceClusterId
            ACCESS  not-implemented
            DESCRIPTION
                 "tBgpInstanceClusterId is not implemented."

        VARIATION   tBgpInstanceConfederationAS4Byte
            ACCESS  not-implemented
            DESCRIPTION
                 "tBgpInstanceConfederationAS4Byte is not implemented."

        VARIATION   tBgpInstanceDisableClientReflect
            ACCESS  not-implemented
            DESCRIPTION
                 "tBgpInstanceDisableClientReflect is not implemented."

        VARIATION   tBgpInstanceDisallowIgp
            ACCESS  not-implemented
            DESCRIPTION
                 "tBgpInstanceDisallowIgp is not implemented."

        VARIATION   tBgpInstanceGRAdminState
            ACCESS  read-only
            DESCRIPTION
                 "tBgpInstanceGRAdminState is implemented as read only.

                  Not supported."

        VARIATION   tBgpInstanceGROperState
            ACCESS  not-implemented
            DESCRIPTION
                 "Not supported."

        VARIATION   tBgpInstanceGRPathSelectDefer
            ACCESS  read-only
            DESCRIPTION
                 "tBgpInstanceGRPathSelectDefer is implemented as read only.

                  Not supported."

        VARIATION   tBgpInstanceGRRestartTime
            ACCESS  read-only
            DESCRIPTION
                 "tBgpInstanceGRRestartTime is implemented as read only.

                  Not supported."

        VARIATION   tBgpInstanceGRStaleRoute
            ACCESS  not-implemented
            DESCRIPTION
                 "Not supported."

        VARIATION   tBgpInstanceGracefulRestart
            ACCESS  not-implemented
            DESCRIPTION
                 "Not supported."

        VARIATION   tBgpInstanceIBgpMultipath
            ACCESS  not-implemented
            DESCRIPTION
                 "tBgpInstanceIBgpMultipath is not implemented.

                  tBgpInstanceIBgpMultipath is not implemented."

        VARIATION   tBgpInstanceIgnoreNextHopMetric
            ACCESS  not-implemented
            DESCRIPTION
                 "Not supported."

        VARIATION   tBgpInstanceIgnoreRouterId
            ACCESS  not-implemented
            DESCRIPTION
                 "Not supported."

        VARIATION   tBgpInstanceIgpShortcut
            ACCESS  not-implemented
            DESCRIPTION
                 "tBgpInstanceIgpShortcut is not implemented."

        VARIATION   tBgpInstanceMpBgpKeep
            ACCESS  not-implemented
            DESCRIPTION
                 "Not supported."

        VARIATION   tBgpInstanceMultipath
            ACCESS  not-implemented
            DESCRIPTION
                 "tBgpInstanceMultipath is not implemented."

        VARIATION   tBgpInstanceMultipathEiBgpState
            ACCESS  not-implemented
            DESCRIPTION
                 "tBgpInstanceMultipathEiBgpState is not implemented."

        VARIATION   tBgpInstanceNHResUseBgpRoutes
            ACCESS  not-implemented
            DESCRIPTION
                 "Not supported."

        VARIATION   tBgpNgBackwardTransition
            DESCRIPTION
                 "The tBgpNgBackwardTransition notification has vRtrID appended
                  to the variable list."

        VARIATION   tBgpNgEstablished
            DESCRIPTION
                 "The tBgpNgEstablished notification has vRtrID appended to the
                  variable list."

        VARIATION   tBgpPGAigp
            ACCESS  not-implemented
            DESCRIPTION
                 "Not supported."

        VARIATION   tBgpPGDefaultRouteTarget
            ACCESS  not-implemented
            DESCRIPTION
                 "Not supported."

        VARIATION   tBgpPGMinTTLValue
            ACCESS  not-implemented
            DESCRIPTION
                 "Not supported."

        VARIATION   tBgpPGRemovePrivateSkipPeerAs
            ACCESS  not-implemented
            DESCRIPTION
                 "Not supported."

        VARIATION   tBgpPGTTLLogId
            ACCESS  not-implemented
            DESCRIPTION
                 "tBgpPGTTLLogId is not implemented."

        VARIATION   tBgpPeerGRAdminState
            ACCESS  read-only
            DESCRIPTION
                 "tBgpPeerNgGRAdminState is implemented as read only.

                  Not supported."

        VARIATION   tBgpPeerGROperState
            ACCESS  not-implemented
            DESCRIPTION
                 "Not supported."

        VARIATION   tBgpPeerGRRestartTime
            ACCESS  not-implemented
            DESCRIPTION
                 "Not supported."

        VARIATION   tBgpPeerGRStaleRoute
            ACCESS  not-implemented
            DESCRIPTION
                 "Not supported."

        VARIATION   tBgpPeerGracefulRestart
            ACCESS  not-implemented
            DESCRIPTION
                 "Not supported."

        VARIATION   tBgpPeerGroupClusterId
            ACCESS  not-implemented
            DESCRIPTION
                 "tBgpPeerGroupClusterId is not implemented."

        VARIATION   tBgpPeerGroupDisableClientReflect
            ACCESS  not-implemented
            DESCRIPTION
                 "tBgpPeerGroupDisableClientReflect is not implemented."

        VARIATION   tBgpPeerGroupGRAdminState
            ACCESS  read-only
            DESCRIPTION
                 "tBgpPeerGroupGRAdminState is implemented as read only.

                  Not supported."

        VARIATION   tBgpPeerGroupGROperState
            ACCESS  not-implemented
            DESCRIPTION
                 "Not supported."

        VARIATION   tBgpPeerGroupGRRestartTime
            ACCESS  not-implemented
            DESCRIPTION
                 "Not supported."

        VARIATION   tBgpPeerGroupGRStaleRoute
            ACCESS  not-implemented
            DESCRIPTION
                 "Not supported."

        VARIATION   tBgpPeerGroupGracefulRestart
            ACCESS  not-implemented
            DESCRIPTION
                 "Not supported."

        VARIATION   tBgpPeerNgAigp
            ACCESS  not-implemented
            DESCRIPTION
                 "Not supported."

        VARIATION   tBgpPeerNgClusterId
            ACCESS  not-implemented
            DESCRIPTION
                 "tBgpPeerNgClusterId is not implemented."

        VARIATION   tBgpPeerNgDefaultRouteTarget
            ACCESS  not-implemented
            DESCRIPTION
                 "Not supported."

        VARIATION   tBgpPeerNgDisableClientReflect
            ACCESS  not-implemented
            DESCRIPTION
                 "tBgpPeerNgDisableClientReflect is not implemented."

        VARIATION   tBgpPeerNgGRAdminState
            ACCESS  not-implemented
            DESCRIPTION
                 "Not supported."

        VARIATION   tBgpPeerNgGROperState
            ACCESS  not-implemented
            DESCRIPTION
                 "Not supported."

        VARIATION   tBgpPeerNgGRRestartTime
            ACCESS  not-implemented
            DESCRIPTION
                 "Not supported."

        VARIATION   tBgpPeerNgGRStaleRoute
            ACCESS  not-implemented
            DESCRIPTION
                 "Not supported."

        VARIATION   tBgpPeerNgGracefulRestart
            ACCESS  not-implemented
            DESCRIPTION
                 "Not supported."

        VARIATION   tBgpPeerNgMinTTLValue
            ACCESS  not-implemented
            DESCRIPTION
                 "Not supported."

        VARIATION   tBgpPeerNgOperGRFamilyFwding
            ACCESS  not-implemented
            DESCRIPTION
                 "Not supported."

        VARIATION   tBgpPeerNgOperGRFamilyNegotiated
            ACCESS  not-implemented
            DESCRIPTION
                 "Not supported."

        VARIATION   tBgpPeerNgOperGRFamilyRestart
            ACCESS  not-implemented
            DESCRIPTION
                 "Not supported."

        VARIATION   tBgpPeerNgOperGRRecvEOR
            ACCESS  not-implemented
            DESCRIPTION
                 "Not supported."

        VARIATION   tBgpPeerNgOperGRReqRestartTime
            ACCESS  not-implemented
            DESCRIPTION
                 "Not supported."

        VARIATION   tBgpPeerNgOperGRSendEOR
            ACCESS  not-implemented
            DESCRIPTION
                 "Not supported."

        VARIATION   tBgpPeerNgOperGRStaleRoutesTime
            ACCESS  not-implemented
            DESCRIPTION
                 "Not supported."

        VARIATION   tBgpPeerNgOperGRStatus
            ACCESS  not-implemented
            DESCRIPTION
                 "Not supported."

        VARIATION   tBgpPeerNgOperGRSupport
            ACCESS  not-implemented
            DESCRIPTION
                 "Not supported."

        VARIATION   tBgpPeerNgOperMCastV4ActivePfxs
            ACCESS  not-implemented
            DESCRIPTION
                 "tBgpPeerNgOperMCastV4ActivePfxs is not implemented."

        VARIATION   tBgpPeerNgOperMCastV4RecvPfxs
            ACCESS  not-implemented
            DESCRIPTION
                 "tBgpPeerNgOperMCastV4RecvPfxs is not implemented."

        VARIATION   tBgpPeerNgOperMCastV4SentPfxs
            ACCESS  not-implemented
            DESCRIPTION
                 "tBgpPeerNgOperMCastV4SentPfxs is not implemented."

        VARIATION   tBgpPeerNgOperMCastV4SuppPfxDamp
            ACCESS  not-implemented
            DESCRIPTION
                 "tBgpPeerNgOperMCastV4SuppPfxDamp is not implemented."

        VARIATION   tBgpPeerNgOperMcastVpnV4ActPfxs
            ACCESS  not-implemented
            DESCRIPTION
                 "Not supported."

        VARIATION   tBgpPeerNgOperMcastVpnV4RecvPfxs
            ACCESS  not-implemented
            DESCRIPTION
                 "Not supported."

        VARIATION   tBgpPeerNgOperMcastVpnV4SentPfxs
            ACCESS  not-implemented
            DESCRIPTION
                 "Not supported."

        VARIATION   tBgpPeerNgOperMvpnV4ActivePfxs
            ACCESS  not-implemented
            DESCRIPTION
                 "tBgpPeerNgOperMvpnV4ActivePfxs is not implemented."

        VARIATION   tBgpPeerNgOperMvpnV4RecvPfxs
            ACCESS  not-implemented
            DESCRIPTION
                 "tBgpPeerNgOperMvpnV4RecvPfxs is not implemented."

        VARIATION   tBgpPeerNgOperMvpnV4SentPfxs
            ACCESS  not-implemented
            DESCRIPTION
                 "tBgpPeerNgOperMvpnV4SentPfxs is not implemented."

        VARIATION   tBgpPeerNgOperMvpnV4SuppPfxDamp
            ACCESS  not-implemented
            DESCRIPTION
                 "tBgpPeerNgOperMvpnV4SuppPfxDamp is not implemented."

        VARIATION   tBgpPeerNgOperRtTgtActivePfxs
            ACCESS  not-implemented
            DESCRIPTION
                 "Not supported."

        VARIATION   tBgpPeerNgOperRtTgtRecvPfxs
            ACCESS  not-implemented
            DESCRIPTION
                 "Not supported."

        VARIATION   tBgpPeerNgOperRtTgtSentPfxs
            ACCESS  not-implemented
            DESCRIPTION
                 "Not supported."

        VARIATION   tBgpPeerNgOperRtTgtSuppPfxDamp
            ACCESS  not-implemented
            DESCRIPTION
                 "Not supported."

        VARIATION   tBgpPeerNgOperV6ActivePrefixes
            ACCESS  not-implemented
            DESCRIPTION
                 "tBgpPeerNgOperV6ActivePrefixes is not implemented."

        VARIATION   tBgpPeerNgOperV6ReceivedPaths
            ACCESS  not-implemented
            DESCRIPTION
                 "tBgpPeerNgOperV6ReceivedPaths is not implemented."

        VARIATION   tBgpPeerNgOperV6ReceivedPrefixes
            ACCESS  not-implemented
            DESCRIPTION
                 "tBgpPeerNgOperV6ReceivedPrefixes is not implemented."

        VARIATION   tBgpPeerNgOperV6SentPrefixes
            ACCESS  not-implemented
            DESCRIPTION
                 "tBgpPeerNgOperV6SentPrefixes is not implemented."

        VARIATION   tBgpPeerNgOperV6SuppPathsDamping
            ACCESS  not-implemented
            DESCRIPTION
                 "tBgpPeerNgOperV6SuppPathsDamping is not implemented."

        VARIATION   tBgpPeerNgOperV6SuppPfxDamp
            ACCESS  not-implemented
            DESCRIPTION
                 "tBgpPeerNgOperV6SuppPfxDamp is not implemented."

        VARIATION   tBgpPeerNgOperVpnIpv6ActivePfxs
            ACCESS  not-implemented
            DESCRIPTION
                 "tBgpPeerNgOperVpnIpv6ActivePfxs is not implemented."

        VARIATION   tBgpPeerNgOperVpnIpv6RecvPfxs
            ACCESS  not-implemented
            DESCRIPTION
                 "tBgpPeerNgOperVpnIpv6RecvPfxs is not implemented."

        VARIATION   tBgpPeerNgOperVpnIpv6SentPfxs
            ACCESS  not-implemented
            DESCRIPTION
                 "tBgpPeerNgOperVpnIpv6SentPfxs is not implemented."

        VARIATION   tBgpPeerNgOperVpnIpv6SuppPfxDamp
            ACCESS  not-implemented
            DESCRIPTION
                 "tBgpPeerNgOperVpnIpv6SuppPfxDamp is not implemented."

        VARIATION   tBgpPeerNgOperVpnV4BackupPfxs
            ACCESS  not-implemented
            DESCRIPTION
                 "Not supported."

        VARIATION   tBgpPeerNgOperVpnV6BackupPfxs
            ACCESS  not-implemented
            DESCRIPTION
                 "Not supported."

        VARIATION   tBgpPeerNgRemPrivateSkipPeerAs
            ACCESS  not-implemented
            DESCRIPTION
                 "Not supported."

        VARIATION   tBgpPeerNgSplitHorizon
            ACCESS  not-implemented
            DESCRIPTION
                 "Not supported."

        VARIATION   tBgpPeerOperGRFamilyFwding
            ACCESS  not-implemented
            DESCRIPTION
                 "Not supported."

        VARIATION   tBgpPeerOperGRFamilyNegotiated
            ACCESS  not-implemented
            DESCRIPTION
                 "Not supported."

        VARIATION   tBgpPeerOperGRFamilyRestart
            ACCESS  not-implemented
            DESCRIPTION
                 "Not supported."

        VARIATION   tBgpPeerOperGRRecvEOR
            ACCESS  not-implemented
            DESCRIPTION
                 "Not supported."

        VARIATION   tBgpPeerOperGRRequestRestartTime
            ACCESS  not-implemented
            DESCRIPTION
                 "Not supported."

        VARIATION   tBgpPeerOperGRSendEOR
            ACCESS  not-implemented
            DESCRIPTION
                 "Not supported."

        VARIATION   tBgpPeerOperGRStaleRoutesTime
            ACCESS  not-implemented
            DESCRIPTION
                 "Not supported."

        VARIATION   tBgpPeerOperGRStatus
            ACCESS  not-implemented
            DESCRIPTION
                 "Not supported."

        VARIATION   tBgpPeerOperGRSupport
            ACCESS  not-implemented
            DESCRIPTION
                 "Not supported."

    ::= { tmnxSASMAgentV9v0  31 }

--
-- SASMxp BGP CAPABILITIES
--
tmnxSASMxpBgpV9v0                 AGENT-CAPABILITIES
    PRODUCT-RELEASE "Alcatel-Lucent SAS"
    STATUS          current
    DESCRIPTION
         "Implementation of BGP functions for Alcatel-Lucent SASM xp systems
          release 9.0."

    SUPPORTS        BGP4-MIB
        INCLUDES {
           bgp4MIBGlobalsGroup,
           bgp4MIBNotificationGroup,
           bgp4MIBPathAttrGroup,
           bgp4MIBPeerGroup
        }

        VARIATION   bgpBackwardTransition
            DESCRIPTION
                 "The bgpBackwardTransition notification has vRtrID appended to
                  the variable list."

        VARIATION   bgpEstablished
            DESCRIPTION
                 "The bgpEstablished notification has vRtrID appended to the
                  variable list."

        VARIATION   bgpPeerMinASOriginationInterval
            SYNTAX  INTEGER (1..255)
            DESCRIPTION
                 "The maximum supported value for
                  bgpPeerMinASOriginationInterval is 255 seconds."

        VARIATION   bgpPeerMinRouteAdvertisementInterval
            SYNTAX  INTEGER (1..255)
            DESCRIPTION
                 "The maximum supported value for
                  bgpPeerMinRouteAdvertisementInterval is 255 seconds."

    SUPPORTS        TIMETRA-BGP-MIB
        INCLUDES {
           tmnxBgp4ByteASNV7v0Group,
           tmnxBgp4PathAttrGroup,
           tmnxBgpAddPathV9v0R4Group,
           tmnxBgpDisableCapNegoV9v0Group,
           tmnxBgpFlowSpecV9v0Group,
           tmnxBgpGlobalV10v0Group,
           tmnxBgpInstanceParamsV5v0Group,
           tmnxBgpInstanceParamsV6v0Group,
           tmnxBgpInstanceV8v0Group,
           tmnxBgpNotificationV7v0Group,
           tmnxBgpNotifyObjsV7v0Group,
           tmnxBgpPeerGroupParamsV5v0Group,
           tmnxBgpPeerGroupParamsV6v0Group,
           tmnxBgpPeerGroupV11v0Group,
           tmnxBgpPeerParamsV5v0Group,
           tmnxBgpPeerParamsV6v0Group,
           tmnxBgpPeerV8v0Group,
           tmnxBgpPeerV9v0Group,
           tmnxBgpPeeringPlcyV10v0Group,
           tmnxBgpPeeringPolicyV10v0Group,
           tmnxBgpRTConstraintV10v0Group
        }

        VARIATION   tBgpConfederation4BytTblLstChngd
            ACCESS  not-implemented
            DESCRIPTION
                 "tBgpConfederation4BytTblLstChngd is not implemented."

        VARIATION   tBgpConfederation4ByteTable
            ACCESS  not-implemented
            DESCRIPTION
                 "tBgpConfederation4ByteTable is not implemented."

        VARIATION   tBgpConfederationTable
            ACCESS  not-implemented
            DESCRIPTION
                 "tBgpConfederationTable is not implemented."

        VARIATION   tBgpConfederationTableLastChanged
            ACCESS  not-implemented
            DESCRIPTION
                 "tBgpConfederationTableLastChanged is not implemented."

        VARIATION   tBgpInstRemovePrivateSkipPeerAs
            ACCESS  not-implemented
            DESCRIPTION
                 "Not supported."

        VARIATION   tBgpInstRteTargetTable
            ACCESS  not-implemented
            DESCRIPTION
                 "tBgpInstRteTargetTable is not implemented."

        VARIATION   tBgpInstanceAllowInterAsVpn
            ACCESS  not-implemented
            DESCRIPTION
                 "Not supported."

        VARIATION   tBgpInstanceClusterId
            ACCESS  not-implemented
            DESCRIPTION
                 "tBgpInstanceClusterId is not implemented."

        VARIATION   tBgpInstanceConfederationAS4Byte
            ACCESS  not-implemented
            DESCRIPTION
                 "tBgpInstanceConfederationAS4Byte is not implemented."

        VARIATION   tBgpInstanceDisableClientReflect
            ACCESS  not-implemented
            DESCRIPTION
                 "tBgpInstanceDisableClientReflect is not implemented."

        VARIATION   tBgpInstanceDisallowIgp
            ACCESS  not-implemented
            DESCRIPTION
                 "tBgpInstanceDisallowIgp is not implemented."

        VARIATION   tBgpInstanceGRAdminState
            ACCESS  read-only
            DESCRIPTION
                 "tBgpInstanceGRAdminState is implemented as read only.

                  Not supported."

        VARIATION   tBgpInstanceGROperState
            ACCESS  not-implemented
            DESCRIPTION
                 "Not supported."

        VARIATION   tBgpInstanceGRPathSelectDefer
            ACCESS  read-only
            DESCRIPTION
                 "tBgpInstanceGRPathSelectDefer is implemented as read only.

                  Not supported."

        VARIATION   tBgpInstanceGRRestartTime
            ACCESS  read-only
            DESCRIPTION
                 "tBgpInstanceGRRestartTime is implemented as read only.

                  Not supported."

        VARIATION   tBgpInstanceGRStaleRoute
            ACCESS  not-implemented
            DESCRIPTION
                 "Not supported."

        VARIATION   tBgpInstanceGracefulRestart
            ACCESS  not-implemented
            DESCRIPTION
                 "Not supported."

        VARIATION   tBgpInstanceIBgpMultipath
            ACCESS  not-implemented
            DESCRIPTION
                 "tBgpInstanceIBgpMultipath is not implemented.

                  tBgpInstanceIBgpMultipath is not implemented."

        VARIATION   tBgpInstanceIgnoreNextHopMetric
            ACCESS  not-implemented
            DESCRIPTION
                 "Not supported."

        VARIATION   tBgpInstanceIgnoreRouterId
            ACCESS  not-implemented
            DESCRIPTION
                 "Not supported."

        VARIATION   tBgpInstanceIgpShortcut
            ACCESS  not-implemented
            DESCRIPTION
                 "tBgpInstanceIgpShortcut is not implemented."

        VARIATION   tBgpInstanceMpBgpKeep
            ACCESS  not-implemented
            DESCRIPTION
                 "Not supported."

        VARIATION   tBgpInstanceMultipath
            ACCESS  not-implemented
            DESCRIPTION
                 "tBgpInstanceMultipath is not implemented."

        VARIATION   tBgpInstanceMultipathEiBgpState
            ACCESS  not-implemented
            DESCRIPTION
                 "tBgpInstanceMultipathEiBgpState is not implemented."

        VARIATION   tBgpInstanceNHResUseBgpRoutes
            ACCESS  not-implemented
            DESCRIPTION
                 "Not supported."

        VARIATION   tBgpNgBackwardTransition
            DESCRIPTION
                 "The tBgpNgBackwardTransition notification has vRtrID appended
                  to the variable list."

        VARIATION   tBgpNgEstablished
            DESCRIPTION
                 "The tBgpNgEstablished notification has vRtrID appended to the
                  variable list."

        VARIATION   tBgpPGAigp
            ACCESS  not-implemented
            DESCRIPTION
                 "Not supported."

        VARIATION   tBgpPGDefaultRouteTarget
            ACCESS  not-implemented
            DESCRIPTION
                 "Not supported."

        VARIATION   tBgpPGMinTTLValue
            ACCESS  not-implemented
            DESCRIPTION
                 "Not supported."

        VARIATION   tBgpPGRemovePrivateSkipPeerAs
            ACCESS  not-implemented
            DESCRIPTION
                 "Not supported."

        VARIATION   tBgpPGTTLLogId
            ACCESS  not-implemented
            DESCRIPTION
                 "tBgpPGTTLLogId is not implemented."

        VARIATION   tBgpPeerGRAdminState
            ACCESS  read-only
            DESCRIPTION
                 "tBgpPeerNgGRAdminState is implemented as read only.

                  Not supported."

        VARIATION   tBgpPeerGROperState
            ACCESS  not-implemented
            DESCRIPTION
                 "Not supported."

        VARIATION   tBgpPeerGRRestartTime
            ACCESS  not-implemented
            DESCRIPTION
                 "Not supported."

        VARIATION   tBgpPeerGRStaleRoute
            ACCESS  not-implemented
            DESCRIPTION
                 "Not supported."

        VARIATION   tBgpPeerGracefulRestart
            ACCESS  not-implemented
            DESCRIPTION
                 "Not supported."

        VARIATION   tBgpPeerGroupClusterId
            ACCESS  not-implemented
            DESCRIPTION
                 "tBgpPeerGroupClusterId is not implemented."

        VARIATION   tBgpPeerGroupDisableClientReflect
            ACCESS  not-implemented
            DESCRIPTION
                 "tBgpPeerGroupDisableClientReflect is not implemented."

        VARIATION   tBgpPeerGroupGRAdminState
            ACCESS  read-only
            DESCRIPTION
                 "tBgpPeerGroupGRAdminState is implemented as read only.

                  Not supported."

        VARIATION   tBgpPeerGroupGROperState
            ACCESS  not-implemented
            DESCRIPTION
                 "Not supported."

        VARIATION   tBgpPeerGroupGRRestartTime
            ACCESS  not-implemented
            DESCRIPTION
                 "Not supported."

        VARIATION   tBgpPeerGroupGRStaleRoute
            ACCESS  not-implemented
            DESCRIPTION
                 "Not supported."

        VARIATION   tBgpPeerGroupGracefulRestart
            ACCESS  not-implemented
            DESCRIPTION
                 "Not supported."

        VARIATION   tBgpPeerNgAigp
            ACCESS  not-implemented
            DESCRIPTION
                 "Not supported."

        VARIATION   tBgpPeerNgClusterId
            ACCESS  not-implemented
            DESCRIPTION
                 "tBgpPeerNgClusterId is not implemented."

        VARIATION   tBgpPeerNgDefaultRouteTarget
            ACCESS  not-implemented
            DESCRIPTION
                 "Not supported."

        VARIATION   tBgpPeerNgDisableClientReflect
            ACCESS  not-implemented
            DESCRIPTION
                 "tBgpPeerNgDisableClientReflect is not implemented."

        VARIATION   tBgpPeerNgGRAdminState
            ACCESS  not-implemented
            DESCRIPTION
                 "Not supported."

        VARIATION   tBgpPeerNgGROperState
            ACCESS  not-implemented
            DESCRIPTION
                 "Not supported."

        VARIATION   tBgpPeerNgGRRestartTime
            ACCESS  not-implemented
            DESCRIPTION
                 "Not supported."

        VARIATION   tBgpPeerNgGRStaleRoute
            ACCESS  not-implemented
            DESCRIPTION
                 "Not supported."

        VARIATION   tBgpPeerNgGracefulRestart
            ACCESS  not-implemented
            DESCRIPTION
                 "Not supported."

        VARIATION   tBgpPeerNgMinTTLValue
            ACCESS  not-implemented
            DESCRIPTION
                 "Not supported."

        VARIATION   tBgpPeerNgOperGRFamilyFwding
            ACCESS  not-implemented
            DESCRIPTION
                 "Not supported."

        VARIATION   tBgpPeerNgOperGRFamilyNegotiated
            ACCESS  not-implemented
            DESCRIPTION
                 "Not supported."

        VARIATION   tBgpPeerNgOperGRFamilyRestart
            ACCESS  not-implemented
            DESCRIPTION
                 "Not supported."

        VARIATION   tBgpPeerNgOperGRRecvEOR
            ACCESS  not-implemented
            DESCRIPTION
                 "Not supported."

        VARIATION   tBgpPeerNgOperGRReqRestartTime
            ACCESS  not-implemented
            DESCRIPTION
                 "Not supported."

        VARIATION   tBgpPeerNgOperGRSendEOR
            ACCESS  not-implemented
            DESCRIPTION
                 "Not supported."

        VARIATION   tBgpPeerNgOperGRStaleRoutesTime
            ACCESS  not-implemented
            DESCRIPTION
                 "Not supported."

        VARIATION   tBgpPeerNgOperGRStatus
            ACCESS  not-implemented
            DESCRIPTION
                 "Not supported."

        VARIATION   tBgpPeerNgOperGRSupport
            ACCESS  not-implemented
            DESCRIPTION
                 "Not supported."

        VARIATION   tBgpPeerNgOperMCastV4ActivePfxs
            ACCESS  not-implemented
            DESCRIPTION
                 "tBgpPeerNgOperMCastV4ActivePfxs is not implemented."

        VARIATION   tBgpPeerNgOperMCastV4RecvPfxs
            ACCESS  not-implemented
            DESCRIPTION
                 "tBgpPeerNgOperMCastV4RecvPfxs is not implemented."

        VARIATION   tBgpPeerNgOperMCastV4SentPfxs
            ACCESS  not-implemented
            DESCRIPTION
                 "tBgpPeerNgOperMCastV4SentPfxs is not implemented."

        VARIATION   tBgpPeerNgOperMCastV4SuppPfxDamp
            ACCESS  not-implemented
            DESCRIPTION
                 "tBgpPeerNgOperMCastV4SuppPfxDamp is not implemented."

        VARIATION   tBgpPeerNgOperMcastVpnV4ActPfxs
            ACCESS  not-implemented
            DESCRIPTION
                 "Not supported."

        VARIATION   tBgpPeerNgOperMcastVpnV4RecvPfxs
            ACCESS  not-implemented
            DESCRIPTION
                 "Not supported."

        VARIATION   tBgpPeerNgOperMcastVpnV4SentPfxs
            ACCESS  not-implemented
            DESCRIPTION
                 "Not supported."

        VARIATION   tBgpPeerNgOperMvpnV4ActivePfxs
            ACCESS  not-implemented
            DESCRIPTION
                 "tBgpPeerNgOperMvpnV4ActivePfxs is not implemented."

        VARIATION   tBgpPeerNgOperMvpnV4RecvPfxs
            ACCESS  not-implemented
            DESCRIPTION
                 "tBgpPeerNgOperMvpnV4RecvPfxs is not implemented."

        VARIATION   tBgpPeerNgOperMvpnV4SentPfxs
            ACCESS  not-implemented
            DESCRIPTION
                 "tBgpPeerNgOperMvpnV4SentPfxs is not implemented."

        VARIATION   tBgpPeerNgOperMvpnV4SuppPfxDamp
            ACCESS  not-implemented
            DESCRIPTION
                 "tBgpPeerNgOperMvpnV4SuppPfxDamp is not implemented."

        VARIATION   tBgpPeerNgOperRtTgtActivePfxs
            ACCESS  not-implemented
            DESCRIPTION
                 "Not supported."

        VARIATION   tBgpPeerNgOperRtTgtRecvPfxs
            ACCESS  not-implemented
            DESCRIPTION
                 "Not supported."

        VARIATION   tBgpPeerNgOperRtTgtSentPfxs
            ACCESS  not-implemented
            DESCRIPTION
                 "Not supported."

        VARIATION   tBgpPeerNgOperRtTgtSuppPfxDamp
            ACCESS  not-implemented
            DESCRIPTION
                 "Not supported."

        VARIATION   tBgpPeerNgOperV6ActivePrefixes
            ACCESS  not-implemented
            DESCRIPTION
                 "tBgpPeerNgOperV6ActivePrefixes is not implemented."

        VARIATION   tBgpPeerNgOperV6ReceivedPaths
            ACCESS  not-implemented
            DESCRIPTION
                 "tBgpPeerNgOperV6ReceivedPaths is not implemented."

        VARIATION   tBgpPeerNgOperV6ReceivedPrefixes
            ACCESS  not-implemented
            DESCRIPTION
                 "tBgpPeerNgOperV6ReceivedPrefixes is not implemented."

        VARIATION   tBgpPeerNgOperV6SentPrefixes
            ACCESS  not-implemented
            DESCRIPTION
                 "tBgpPeerNgOperV6SentPrefixes is not implemented."

        VARIATION   tBgpPeerNgOperV6SuppPathsDamping
            ACCESS  not-implemented
            DESCRIPTION
                 "tBgpPeerNgOperV6SuppPathsDamping is not implemented."

        VARIATION   tBgpPeerNgOperV6SuppPfxDamp
            ACCESS  not-implemented
            DESCRIPTION
                 "tBgpPeerNgOperV6SuppPfxDamp is not implemented."

        VARIATION   tBgpPeerNgOperVpnIpv6ActivePfxs
            ACCESS  not-implemented
            DESCRIPTION
                 "tBgpPeerNgOperVpnIpv6ActivePfxs is not implemented."

        VARIATION   tBgpPeerNgOperVpnIpv6RecvPfxs
            ACCESS  not-implemented
            DESCRIPTION
                 "tBgpPeerNgOperVpnIpv6RecvPfxs is not implemented."

        VARIATION   tBgpPeerNgOperVpnIpv6SentPfxs
            ACCESS  not-implemented
            DESCRIPTION
                 "tBgpPeerNgOperVpnIpv6SentPfxs is not implemented."

        VARIATION   tBgpPeerNgOperVpnIpv6SuppPfxDamp
            ACCESS  not-implemented
            DESCRIPTION
                 "tBgpPeerNgOperVpnIpv6SuppPfxDamp is not implemented."

        VARIATION   tBgpPeerNgOperVpnV4BackupPfxs
            ACCESS  not-implemented
            DESCRIPTION
                 "Not supported."

        VARIATION   tBgpPeerNgOperVpnV6BackupPfxs
            ACCESS  not-implemented
            DESCRIPTION
                 "Not supported."

        VARIATION   tBgpPeerNgRemPrivateSkipPeerAs
            ACCESS  not-implemented
            DESCRIPTION
                 "Not supported."

        VARIATION   tBgpPeerNgSplitHorizon
            ACCESS  not-implemented
            DESCRIPTION
                 "Not supported."

        VARIATION   tBgpPeerOperGRFamilyFwding
            ACCESS  not-implemented
            DESCRIPTION
                 "Not supported."

        VARIATION   tBgpPeerOperGRFamilyNegotiated
            ACCESS  not-implemented
            DESCRIPTION
                 "Not supported."

        VARIATION   tBgpPeerOperGRFamilyRestart
            ACCESS  not-implemented
            DESCRIPTION
                 "Not supported."

        VARIATION   tBgpPeerOperGRRecvEOR
            ACCESS  not-implemented
            DESCRIPTION
                 "Not supported."

        VARIATION   tBgpPeerOperGRRequestRestartTime
            ACCESS  not-implemented
            DESCRIPTION
                 "Not supported."

        VARIATION   tBgpPeerOperGRSendEOR
            ACCESS  not-implemented
            DESCRIPTION
                 "Not supported."

        VARIATION   tBgpPeerOperGRStaleRoutesTime
            ACCESS  not-implemented
            DESCRIPTION
                 "Not supported."

        VARIATION   tBgpPeerOperGRStatus
            ACCESS  not-implemented
            DESCRIPTION
                 "Not supported."

        VARIATION   tBgpPeerOperGRSupport
            ACCESS  not-implemented
            DESCRIPTION
                 "Not supported."

    ::= { tmnxSASMxpAgentV9v0  31 }

--
-- SAS CHASSIS CAPABILITIES
--
tmnxSASChassisV9v0                AGENT-CAPABILITIES
    PRODUCT-RELEASE "Alcatel-Lucent SAS"
    STATUS          current
    DESCRIPTION
         "Implementation of CHASSIS functions for Alcatel-Lucent SAS systems
          release 9.0."

    SUPPORTS        TIMETRA-CHASSIS-MIB
        INCLUDES {
           tmnx7710SETSRefSrcHwV6v0Group,
           tmnxCardV3v0Group,
           tmnxCardV6v0NamedPoolPlcyGroup,
           tmnxCardV7v0Group,
           tmnxChassisNotificationV7v0Group,
           tmnxChassisV5v0Group,
           tmnxChassisV6v1Group,
           tmnxMDACcagV6v1Group,
           tmnxMDAMcPathMgmtV6v0Group,
           tmnxMDAV6v1Group
        }

        VARIATION   tmnxCardAllowedTypes
            ACCESS  not-implemented
            DESCRIPTION
                 "tmnxCardAllowedTypes object is not implemented. This object
                  was made obsolete in the 3.0 release.

                  A bit-mask that specifies what IOM card types the
                  administrator has designated be allowed to be inserted into
                  this slot.If the slot has not-been pre-provisioned and a card
                  that does not match one of the allowed types is inserted into
                  this slot, a mis-match alarm will be raised. If a specific
                  value has not yet been SET by the manager,
                  tmnxCardAllowedTypes will return the same value to a GET
                  request as tmnxCardSupportedTypes.

                  tmnxCardAllowedTypes object is not implemented. This object
                  was made obsolete in the 3.0 release.

                  A bit-mask that specifies what IOM card types the
                  administrator has designated be allowed to be inserted into
                  this slot.If the slot has not-been pre-provisioned and a card
                  that does not match one of the allowed types is inserted into
                  this slot, a mis-match alarm will be raised. If a specific
                  value has not yet been SET by the manager,
                  tmnxCardAllowedTypes will return the same value to a GET
                  request as tmnxCardSupportedTypes."

        VARIATION   tmnxCardFailOnError
            ACCESS  not-implemented
            DESCRIPTION
                 "Not supported.

                  Not supported."

        VARIATION   tmnxChassisAdminMode
            SYNTAX  INTEGER {
                       modeA                (1),
                       modeB                (2),
                    -- modeC                (3) No modeC on SAS-R 7210
                       modeD                (4)
                    }
            DESCRIPTION
                 "The value 'modeC (3)' is invalid on a 7450 system, because
                  scaling and features corresponding to the IOM2-20g card are
                  not supported on Nokia 7450 systems.

                  The value 'modeC (3)' is invalid on a 7450 system, because
                  scaling and features corresponding to the IOM2-20g card are
                  not supported on Nokia 7450 systems."

        VARIATION   tmnxChassisMinorLEDState
            ACCESS  not-implemented
            DESCRIPTION
                 "Not supported.

                  Not supported."

        VARIATION   tmnxChassisPowerSupplyAssignedType
            ACCESS  read-only
            DESCRIPTION
                 "This object is read-only.

                  This object is read-only."

        VARIATION   tmnxChassisPowerSupplyPemType
            ACCESS  not-implemented
            DESCRIPTION
                 "Not supported.

                  Not supported."

        VARIATION   tmnxChassisRedForcedSingleSfm
            ACCESS  not-implemented
            DESCRIPTION
                 "Not supported.

                  Not supported."

        VARIATION   tmnxChassisRowStatus
            ACCESS  read-only
            DESCRIPTION
                 "tmnxChassisRowStatus is supported as read-only. Row entries
                  cannot be created by SNMP SET requests. Multiple chassises are
                  not supported on Nokia SAS-R 7210 systems.

                  tmnxChassisRowStatus is supported as read-only. Row entries
                  cannot be created by SNMP SET requests. Multiple chassises are
                  not supported on Nokia SAS-R 7210 systems."

        VARIATION   tmnxCpmCardAllowedTypes
            ACCESS  not-implemented
            DESCRIPTION
                 "tmnxCpmCardAllowedTypes object is not implemented. This object
                  was made obsolete in the 3.0 release.

                  A bit-mask that specifies what CPM card types the
                  administrator has designated be allowed to be inserted into
                  this slot. If the slot has not-been pre-provisioned and a card
                  that does not match one of the allowed types is inserted into
                  this slot, a mis-match alarm will be raised. IfEntry a
                  specific value has not yet been SET by the manager,
                  tmnxCpmCardAllowedTypes will return the same value to a GET
                  request as tmnxCpmCardSupportedTypes.

                  tmnxCpmCardAllowedTypes object is not implemented. This
                  object was made obsolete in the 3.0 release.

                  A bit-mask that specifies what CPM card types the
                  administrator has designated be allowed to be inserted into
                  this slot. If the slot has not-been pre-provisioned and a card
                  that does not match one of the allowed types is inserted into
                  this slot, a mis-match alarm will be raised. IfEntry a
                  specific value has not yet been SET by the manager,
                  tmnxCpmCardAllowedTypes will return the same value to a GET
                  request as tmnxCpmCardSupportedTypes."

        VARIATION   tmnxCpmCardAssignedType
            ACCESS  read-only
            DESCRIPTION
                 "tmnxCpmCardAssignedType is supported as read-only. Multiple
                  CPM card types are not supported on Nokia SAS-R 7210 systems.

                  tmnxCpmCardAssignedType is supported as read-only. Multiple
                  CPM card types are not supported on Nokia SAS-R 7210 systems."

        VARIATION   tmnxCpmCardSwitchToRedundantCard
            ACCESS  not-implemented
            DESCRIPTION
                 "Not supported.

                  Not supported."

        VARIATION   tmnxCpmCardSyncFileNotPresent
            ACCESS  not-implemented
            DESCRIPTION
                 "Not supported.

                  Not supported."

        VARIATION   tmnxEqBackdoorBusFailure
            ACCESS  not-implemented
            DESCRIPTION
                 "tmnxEqBackdoorBusFailure notification is not implemented. This
                  notification was made obsolete in the 2.1 release.

                  tmnxEqBackdoorBusFailure notification is not implemented.
                  This notification was made obsolete in the 2.1 release."

        VARIATION   tmnxHwContainedIndex
            ACCESS  not-implemented
            DESCRIPTION
                 "Not supported.

                  Not supported."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported.

                  The enumerations 'inServiceUpgrade (12)', 'inServiceDowngrade
                  (13)', and 'resetPending (14)' are no longer supported."

        VARIATION   tmnxMDAAllowedTypes
            ACCESS  not-implemented
            DESCRIPTION
                 "tmnxMDAAllowedTypes object is not implemented. This object was
                  made obsolete in the 3.0 release.

                  A bit-mask that specified what MDA card types the
                  administrator has designated be allowed to be inserted into
                  this slot. If the slot has not-been pre-provisioned and a MDA
                  card that does not match one of the allowed types is inserted
                  into this slot, a mis-match alarm will be raised. If a
                  specific value has not yet been SET by the manager, a GET to
                  tmnxMDAAllowedTypes returns the same value as
                  tmnxMDASupportedTypes.

                  tmnxMDAAllowedTypes object is not implemented. This object
                  was made obsolete in the 3.0 release.

                  A bit-mask that specified what MDA card types the
                  administrator has designated be allowed to be inserted into
                  this slot. If the slot has not-been pre-provisioned and a MDA
                  card that does not match one of the allowed types is inserted
                  into this slot, a mis-match alarm will be raised. If a
                  specific value has not yet been SET by the manager, a GET to
                  tmnxMDAAllowedTypes returns the same value as
                  tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  this is just the total number of equipped ports.

                  The value of tmnxMDAEquippedPorts indicates the number of
                  ports equipped on this MDA card. Previous to the 3.0 release
                  this object was defined to be a bit-mask of equipped ports.
                  However, the code implementation has always returned a value
                  this is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed.

                  tmnxPeConfigurationError notification is not implemented.
                  This notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SAS-R 7210 software architecture does
                  not restrict CPU cycles used by a specific code module.

                  tmnxPeCpuCyclesExceeded notification is not implemented. This
                  notification was made obsolete in the 2.1 release.

                  It does not apply. The SAS-R 7210 software architecture does
                  not restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed.

                  tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeStorageProblem
            ACCESS  not-implemented
            DESCRIPTION
                 "tmnxPeStorageProblem notification is not implemented. This
                  notification was made obsolete in the 2.1 release.

                  The only 'storage' devices on the SAS-R 7210 are the cflash
                  drives. Cflash write errors cause a tmnxEqFlashDataLoss
                  notification to be sent. The tmnxEqFlashDiskFull notification
                  is sent when the driver detects that the cflash device is
                  full.

                  tmnxPeStorageProblem notification is not implemented. This
                  notification was made obsolete in the 2.1 release.

                  The only 'storage' devices on the SAS-R 7210 are the cflash
                  drives. Cflash write errors cause a tmnxEqFlashDataLoss
                  notification to be sent. The tmnxEqFlashDiskFull notification
                  is sent when the driver detects that the cflash device is
                  full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed.

                  tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system.

                  tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted.

                  tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingFreqOffset
            ACCESS  not-implemented
            DESCRIPTION
                 "Not supported.

                  Not supported."

    ::= { tmnxSASAgentV9v0  15 }

--
-- SAS CHASSIS CAPABILITIES
--
tmnxSASChassisV9v0                AGENT-CAPABILITIES
    PRODUCT-RELEASE "Alcatel-Lucent SAS"
    STATUS          current
    DESCRIPTION
         "Implementation of CHASSIS functions for Alcatel-Lucent SAS systems
          release 9.0."

    SUPPORTS        TIMETRA-CHASSIS-MIB
        INCLUDES {
           tmnx7710SETSRefSrcHwV6v0Group,
           tmnxCardV3v0Group,
           tmnxCardV6v0NamedPoolPlcyGroup,
           tmnxCardV7v0Group,
           tmnxChassisNotificationV7v0Group,
           tmnxChassisV5v0Group,
           tmnxChassisV6v1Group,
           tmnxMDACcagV6v1Group,
           tmnxMDAMcPathMgmtV6v0Group,
           tmnxMDAV6v1Group
        }

        VARIATION   tmnxCardAllowedTypes
            ACCESS  not-implemented
            DESCRIPTION
                 "tmnxCardAllowedTypes object is not implemented. This object
                  was made obsolete in the 3.0 release.

                  A bit-mask that specifies what IOM card types the
                  administrator has designated be allowed to be inserted into
                  this slot.If the slot has not-been pre-provisioned and a card
                  that does not match one of the allowed types is inserted into
                  this slot, a mis-match alarm will be raised. If a specific
                  value has not yet been SET by the manager,
                  tmnxCardAllowedTypes will return the same value to a GET
                  request as tmnxCardSupportedTypes.

                  tmnxCardAllowedTypes object is not implemented. This object
                  was made obsolete in the 3.0 release.

                  A bit-mask that specifies what IOM card types the
                  administrator has designated be allowed to be inserted into
                  this slot.If the slot has not-been pre-provisioned and a card
                  that does not match one of the allowed types is inserted into
                  this slot, a mis-match alarm will be raised. If a specific
                  value has not yet been SET by the manager,
                  tmnxCardAllowedTypes will return the same value to a GET
                  request as tmnxCardSupportedTypes."

        VARIATION   tmnxCardFailOnError
            ACCESS  not-implemented
            DESCRIPTION
                 "Not supported.

                  Not supported."

        VARIATION   tmnxChassisAdminMode
            SYNTAX  INTEGER {
                       modeA                (1),
                       modeB                (2),
                    -- modeC                (3) No modeC on SAS-R 7210
                       modeD                (4)
                    }
            DESCRIPTION
                 "The value 'modeC (3)' is invalid on a 7450 system, because
                  scaling and features corresponding to the IOM2-20g card are
                  not supported on Nokia 7450 systems.

                  The value 'modeC (3)' is invalid on a 7450 system, because
                  scaling and features corresponding to the IOM2-20g card are
                  not supported on Nokia 7450 systems."

        VARIATION   tmnxChassisMinorLEDState
            ACCESS  not-implemented
            DESCRIPTION
                 "Not supported.

                  Not supported."

        VARIATION   tmnxChassisPowerSupplyAssignedType
            ACCESS  read-only
            DESCRIPTION
                 "This object is read-only.

                  This object is read-only."

        VARIATION   tmnxChassisPowerSupplyPemType
            ACCESS  not-implemented
            DESCRIPTION
                 "Not supported.

                  Not supported."

        VARIATION   tmnxChassisRedForcedSingleSfm
            ACCESS  not-implemented
            DESCRIPTION
                 "Not supported.

                  Not supported."

        VARIATION   tmnxChassisRowStatus
            ACCESS  read-only
            DESCRIPTION
                 "tmnxChassisRowStatus is supported as read-only. Row entries
                  cannot be created by SNMP SET requests. Multiple chassises are
                  not supported on Nokia SAS-R 7210 systems.

                  tmnxChassisRowStatus is supported as read-only. Row entries
                  cannot be created by SNMP SET requests. Multiple chassises are
                  not supported on Nokia SAS-R 7210 systems."

        VARIATION   tmnxCpmCardAllowedTypes
            ACCESS  not-implemented
            DESCRIPTION
                 "tmnxCpmCardAllowedTypes object is not implemented. This object
                  was made obsolete in the 3.0 release.

                  A bit-mask that specifies what CPM card types the
                  administrator has designated be allowed to be inserted into
                  this slot. If the slot has not-been pre-provisioned and a card
                  that does not match one of the allowed types is inserted into
                  this slot, a mis-match alarm will be raised. IfEntry a
                  specific value has not yet been SET by the manager,
                  tmnxCpmCardAllowedTypes will return the same value to a GET
                  request as tmnxCpmCardSupportedTypes.

                  tmnxCpmCardAllowedTypes object is not implemented. This
                  object was made obsolete in the 3.0 release.

                  A bit-mask that specifies what CPM card types the
                  administrator has designated be allowed to be inserted into
                  this slot. If the slot has not-been pre-provisioned and a card
                  that does not match one of the allowed types is inserted into
                  this slot, a mis-match alarm will be raised. IfEntry a
                  specific value has not yet been SET by the manager,
                  tmnxCpmCardAllowedTypes will return the same value to a GET
                  request as tmnxCpmCardSupportedTypes."

        VARIATION   tmnxCpmCardAssignedType
            ACCESS  read-only
            DESCRIPTION
                 "tmnxCpmCardAssignedType is supported as read-only. Multiple
                  CPM card types are not supported on Nokia SAS-R 7210 systems.

                  tmnxCpmCardAssignedType is supported as read-only. Multiple
                  CPM card types are not supported on Nokia SAS-R 7210 systems."

        VARIATION   tmnxCpmCardSwitchToRedundantCard
            ACCESS  not-implemented
            DESCRIPTION
                 "Not supported.

                  Not supported."

        VARIATION   tmnxCpmCardSyncFileNotPresent
            ACCESS  not-implemented
            DESCRIPTION
                 "Not supported.

                  Not supported."

        VARIATION   tmnxEqBackdoorBusFailure
            ACCESS  not-implemented
            DESCRIPTION
                 "tmnxEqBackdoorBusFailure notification is not implemented. This
                  notification was made obsolete in the 2.1 release.

                  tmnxEqBackdoorBusFailure notification is not implemented.
                  This notification was made obsolete in the 2.1 release."

        VARIATION   tmnxHwContainedIndex
            ACCESS  not-implemented
            DESCRIPTION
                 "Not supported.

                  Not supported."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported.

                  The enumerations 'inServiceUpgrade (12)', 'inServiceDowngrade
                  (13)', and 'resetPending (14)' are no longer supported."

        VARIATION   tmnxMDAAllowedTypes
            ACCESS  not-implemented
            DESCRIPTION
                 "tmnxMDAAllowedTypes object is not implemented. This object was
                  made obsolete in the 3.0 release.

                  A bit-mask that specified what MDA card types the
                  administrator has designated be allowed to be inserted into
                  this slot. If the slot has not-been pre-provisioned and a MDA
                  card that does not match one of the allowed types is inserted
                  into this slot, a mis-match alarm will be raised. If a
                  specific value has not yet been SET by the manager, a GET to
                  tmnxMDAAllowedTypes returns the same value as
                  tmnxMDASupportedTypes.

                  tmnxMDAAllowedTypes object is not implemented. This object
                  was made obsolete in the 3.0 release.

                  A bit-mask that specified what MDA card types the
                  administrator has designated be allowed to be inserted into
                  this slot. If the slot has not-been pre-provisioned and a MDA
                  card that does not match one of the allowed types is inserted
                  into this slot, a mis-match alarm will be raised. If a
                  specific value has not yet been SET by the manager, a GET to
                  tmnxMDAAllowedTypes returns the same value as
                  tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  this is just the total number of equipped ports.

                  The value of tmnxMDAEquippedPorts indicates the number of
                  ports equipped on this MDA card. Previous to the 3.0 release
                  this object was defined to be a bit-mask of equipped ports.
                  However, the code implementation has always returned a value
                  this is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed.

                  tmnxPeConfigurationError notification is not implemented.
                  This notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SAS-R 7210 software architecture does
                  not restrict CPU cycles used by a specific code module.

                  tmnxPeCpuCyclesExceeded notification is not implemented. This
                  notification was made obsolete in the 2.1 release.

                  It does not apply. The SAS-R 7210 software architecture does
                  not restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed.

                  tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeStorageProblem
            ACCESS  not-implemented
            DESCRIPTION
                 "tmnxPeStorageProblem notification is not implemented. This
                  notification was made obsolete in the 2.1 release.

                  The only 'storage' devices on the SAS-R 7210 are the cflash
                  drives. Cflash write errors cause a tmnxEqFlashDataLoss
                  notification to be sent. The tmnxEqFlashDiskFull notification
                  is sent when the driver detects that the cflash device is
                  full.

                  tmnxPeStorageProblem notification is not implemented. This
                  notification was made obsolete in the 2.1 release.

                  The only 'storage' devices on the SAS-R 7210 are the cflash
                  drives. Cflash write errors cause a tmnxEqFlashDataLoss
                  notification to be sent. The tmnxEqFlashDiskFull notification
                  is sent when the driver detects that the cflash device is
                  full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed.

                  tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system.

                  tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted.

                  tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingFreqOffset
            ACCESS  not-implemented
            DESCRIPTION
                 "Not supported.

                  Not supported."

    ::= { tmnxSASAgentV9v0  15 }

--
-- SAS CRON CAPABILITIES
--
tmnxSASCronV9v0                   AGENT-CAPABILITIES
    PRODUCT-RELEASE "Alcatel-Lucent SAS"
    STATUS          current
    DESCRIPTION
         "Implementation of CRON capabilities for Alcatel-Lucent SAS systems
          release 9.0."

    SUPPORTS        DISMAN-SCHEDULE-MIB
        INCLUDES {
           schedCalendarGroup,
           schedGroup2,
           schedNotificationsGroup
        }

        VARIATION   schedInterval
            SYNTAX  Unsigned32 (30..42949672)
            DESCRIPTION
                 "The values supported for schedInterval are between 30 and
                  42949672 seconds. 42949672 seconds creates a maximum interval
                  of 497 days, 2 hours, 27 minutes and 52 seconds.

                  The values supported for schedInterval are between 30 and
                  42949672 seconds. 42949672 seconds creates a maximum interval
                  of 497 days, 2 hours, 27 minutes and 52 seconds."

        VARIATION   schedOwner
            SYNTAX  SnmpAdminString (SIZE (1..32))
            DESCRIPTION
                 "The minimum length of schedOwner is 1 when creating new
                  entries in tables via SNMP SET requests.

                  The minimum length of schedOwner is 1 when creating new
                  entries in tables via SNMP SET requests."

    SUPPORTS        DISMAN-SCRIPT-MIB
        INCLUDES {
           smLanguageGroup,
           smLaunchGroup2,
           smNotificationsGroup2,
           smRunGroup2,
           smScriptGroup2
        }

        VARIATION   smLaunchAdminStatus
            SYNTAX  INTEGER {
                       enabled              (1),
                       disabled             (2)
                    -- autostart            (3)
                    }
            DESCRIPTION
                 "The 'autostart (3)' state is not supported.

                  The mib is not clear if smLaunchAdminStatus can be set to
                  'disabled (2)' if there are associated entries in the
                  smRunTable. This agent does not allow smLaunchAdminStatus to
                  be set to 'disabled (2)' if there are any associated entries
                  in the smRunTable. Any associated smRunEntry must be aborted
                  and aged out before smLaunchAdminStatus can be set to
                  'disabled'.

                  The 'autostart (3)' state is not supported.

                  The mib is not clear if smLaunchAdminStatus can be set to
                  'disabled (2)' if there are associated entries in the
                  smRunTable. This agent does not allow smLaunchAdminStatus to
                  be set to 'disabled (2)' if there are any associated entries
                  in the smRunTable. Any associated smRunEntry must be aborted
                  and aged out before smLaunchAdminStatus can be set to
                  'disabled'."

        VARIATION   smLaunchArgument
            DESCRIPTION
                 "This agent uses smLaunchArgument to specify the URL of the
                  file that is created to hold the CLI session output from the
                  'exec' of the CLI script specified in smScriptSource. The
                  script specified in smScriptSource is executed as if the
                  'exec' '-echo' switch was specified in a CLI CONSOLE/Telnet
                  session and the command echo and any display from CLI 'show'
                  commands specified in the script is redirected to the results
                  file specified in smLaunchArgument.

                  The smLaunchArgument URL should consist of the path and a
                  filename prefix. It refer to either the local cflash drives or
                  a remote file accessed through a remote ftp URL. When the exec
                  results file is created for a specific run of the script, a
                  timestamp of the form '_yyyymmdd-hhmmss.out' is appended on
                  the end of the smLaunchArgument filename prefix. For example,
                  setting smLaunchArgument to
                  'ftp://<user>:<passwd>@<a.b.c.d>/cron/results/test-res' causes
                  a script results file to be created named
                  'cron/results/test-res_yyyymmdd-hhmmss.out'.

                  NOTE: The agent does not have any capability to age out,
                  rotate, delete, or otherwise manage these script results
                  files. It is up to the SR system operator or manager to manage
                  retrieval and cleanup of these files.

                  This agent uses smLaunchArgument to specify the URL of the
                  file that is created to hold the CLI session output from the
                  'exec' of the CLI script specified in smScriptSource. The
                  script specified in smScriptSource is executed as if the
                  'exec' '-echo' switch was specified in a CLI CONSOLE/Telnet
                  session and the command echo and any display from CLI 'show'
                  commands specified in the script is redirected to the results
                  file specified in smLaunchArgument.

                  The smLaunchArgument URL should consist of the path and a
                  filename prefix. It refer to either the local cflash drives or
                  a remote file accessed through a remote ftp URL. When the exec
                  results file is created for a specific run of the script, a
                  timestamp of the form '_yyyymmdd-hhmmss.out' is appended on
                  the end of the smLaunchArgument filename prefix. For example,
                  setting smLaunchArgument to
                  'ftp://<user>:<passwd>@<a.b.c.d>/cron/results/test-res' causes
                  a script results file to be created named
                  'cron/results/test-res_yyyymmdd-hhmmss.out'.

                  NOTE: The agent does not have any capability to age out,
                  rotate, delete, or otherwise manage these script results
                  files. It is up to the SR system operator or manager to manage
                  retrieval and cleanup of these files."

        VARIATION   smLaunchControl
            SYNTAX  INTEGER {
                       abort                (1),
                    -- suspend              (2)
                    -- resume               (3)
                       nop                  (4)
                    }
            DESCRIPTION
                 "The 'suspend (2)' and 'resume (3)' controls are not supported.
                  An attempt to set either value results in an
                  'inconsistentValue' error.

                  The 'suspend (2)' and 'resume (3)' controls are not
                  supported. An attempt to set either value results in an
                  'inconsistentValue' error."

        VARIATION   smLaunchEntry
            DESCRIPTION
                 "A maximum of 255 smLaunchEntry rows are allowed to be created.

                  A maximum of 255 smLaunchEntry rows are allowed to be
                  created."

        VARIATION   smLaunchExpireTime
            DESCRIPTION
                 "Unlike smLaunchLifeTime, the mib does not specify a value for
                  smLaunchExpireTime that can be used to indicate that an
                  associated smRunEntry with a smRunState equal to 'terminated'
                  should be kept forever and never aged out. This agent uses the
                  maximum value (2147483647) to specify that a smRunEntry does
                  not age out after its smRunState transitions to 'terminated'.
                  A terminated smRunEntry with a maximum smRunExpireTime value
                  will never be removed from the table.

                  Unlike smLaunchLifeTime, the mib does not specify a value for
                  smLaunchExpireTime that can be used to indicate that an
                  associated smRunEntry with a smRunState equal to 'terminated'
                  should be kept forever and never aged out. This agent uses the
                  maximum value (2147483647) to specify that a smRunEntry does
                  not age out after its smRunState transitions to 'terminated'.
                  A terminated smRunEntry with a maximum smRunExpireTime value
                  will never be removed from the table."

        VARIATION   smLaunchMaxRunning
            SYNTAX  Unsigned32 (1)
            DESCRIPTION
                 "Concurrently running scripts are not supported by this agent.
                  Scripts are queued and executed one at a time. An attempt to
                  set smLaunchMaxRunning to any value other than 1 results in an
                  'inconsistentValue' error.

                  Concurrently running scripts are not supported by this agent.
                  Scripts are queued and executed one at a time. An attempt to
                  set smLaunchMaxRunning to any value other than 1 results in an
                  'inconsistentValue' error."

        VARIATION   smLaunchOwner
            SYNTAX  SnmpAdminString (SIZE (1..32))
            DESCRIPTION
                 "The minimum length of smLaunchOwner is 1 when creating new
                  entries in tables via SNMP SET requests.

                  The minimum length of smLaunchOwner is 1 when creating new
                  entries in tables via SNMP SET requests."

        VARIATION   smLaunchRowExpireTime
            ACCESS  read-only
            DESCRIPTION
                 "smLaunchRowExpireTime functionality is not supported. Its
                  value cannot be modified. The default value 2147483647 is
                  always returned to indicate that the smLaunchTable row entry
                  will never be aged out.

                  smLaunchRowExpireTime functionality is not supported. Its
                  value cannot be modified. The default value 2147483647 is
                  always returned to indicate that the smLaunchTable row entry
                  will never be aged out."

        VARIATION   smLaunchRunIndexNext
            DESCRIPTION
                 "The mib requires that subsequent reads of smLaunchRunIndexNext
                  must return different values. This agent does not increment
                  the value with every read. A read always returns the next
                  available index value.

                  The mib requires that subsequent reads of
                  smLaunchRunIndexNext must return different values. This agent
                  does not increment the value with every read. A read always
                  returns the next available index value."

        VARIATION   smLaunchStart
            DESCRIPTION
                 "In the 4.0 release there is no user access rights checking to
                  verify that the user setting smLaunchStart has read-access to
                  the script. A user command access profile with RADIUS/TACACS+
                  authentication will be associated to the script in a later
                  release.

                  The mib requires that in order for a set to smLaunchStart to
                  succede th number of concurrently executing scripts must be
                  less than the value of smLaunchMaxRunning. This agent does not
                  support execution of more than one script at a time. Instead,
                  a smRunEntry is created with smRunState equal to
                  'initializing' and sequentially queued for later execution.
                  The maximum number of smRunEntry rows is limited to 255
                  regardless of the value of smRunState.

                  The mib specifies that when the smRunEntry is created by
                  setting smLaunchStart, the smRunStartTime should be set to the
                  current time. Because of the one-at-a-time queuing for
                  execution there may be a long time between entering the
                  'initializing' state and transitioning to the 'executing'
                  state, this agent does not set smRunStartTime until smRunState
                  transitions to 'executing'.

                  In the 4.0 release there is no user access rights checking to
                  verify that the user setting smLaunchStart has read-access to
                  the script. A user command access profile with RADIUS/TACACS+
                  authentication will be associated to the script in a later
                  release.

                  The mib requires that in order for a set to smLaunchStart to
                  succede th number of concurrently executing scripts must be
                  less than the value of smLaunchMaxRunning. This agent does not
                  support execution of more than one script at a time. Instead,
                  a smRunEntry is created with smRunState equal to
                  'initializing' and sequentially queued for later execution.
                  The maximum number of smRunEntry rows is limited to 255
                  regardless of the value of smRunState.

                  The mib specifies that when the smRunEntry is created by
                  setting smLaunchStart, the smRunStartTime should be set to the
                  current time. Because of the one-at-a-time queuing for
                  execution there may be a long time between entering the
                  'initializing' state and transitioning to the 'executing'
                  state, this agent does not set smRunStartTime until smRunState
                  transitions to 'executing'."

        VARIATION   smLaunchStorageType
            SYNTAX  INTEGER {
                    -- other                (1)
                    -- volatile             (2)
                       nonVolatile          (3) -- e.g., in NVRAM
                    -- permanent            (4)
                    -- readOnly             (5)
                    }
            DEFVAL  { nonVolatile  }
            DESCRIPTION
                 "This agent supports only 'nonVolatile (3)' storage type. This
                  is interpreted to be the desired storage type for the
                  configuration of the launch entry.

                  When smLaunchStorageType has a value of 'nonVolatile' its
                  configuration is written to the configuration file upon a
                  'save configuration' operation. If the system reboots between
                  the time this row entry is created and before a 'save
                  configuration' operation is made, this row entry will NOT be
                  restored following the reboot.

                  This agent supports only 'nonVolatile (3)' storage type. This
                  is interpreted to be the desired storage type for the
                  configuration of the launch entry.

                  When smLaunchStorageType has a value of 'nonVolatile' its
                  configuration is written to the configuration file upon a
                  'save configuration' operation. If the system reboots between
                  the time this row entry is created and before a 'save
                  configuration' operation is made, this row entry will NOT be
                  restored following the reboot."

        VARIATION   smRunArgument
            SYNTAX  OCTET STRING (SIZE (0..255))
            DESCRIPTION
                 "The maximum size string returned by a read of smRunArgument is
                  255 octets.

                  The maximum size string returned by a read of smRunArgument
                  is 255 octets."

        VARIATION   smRunControl
            SYNTAX  INTEGER {
                       abort                (1),
                    -- suspend              (2)
                    -- resume               (3)
                       nop                  (4)
                    }
            DESCRIPTION
                 "The 'suspend (2)' and 'resume (3)' controls are not supported.
                  An attempt to set either value results in an
                  'inconsistentValue' error.

                  The 'suspend (2)' and 'resume (3)' controls are not
                  supported. An attempt to set either value results in an
                  'inconsistentValue' error."

        VARIATION   smRunEntry
            DESCRIPTION
                 "A maximum of 255 smRunEntry rows are allowed to be created
                  regardless of the value of smRunState.

                  A maximum of 255 smRunEntry rows are allowed to be created
                  regardless of the value of smRunState."

        VARIATION   smRunExpireTime
            DESCRIPTION
                 "Unlike smRunLifeTime, the mib does not specify a value for
                  smRunExpireTime that can be used to indicate this smRunEntry
                  should be kept forever and never aged out. This agent uses the
                  maximum value (2147483647) to specify that this smRunEntry
                  does not age out after its smRunState transitions to
                  'terminated'.

                  If smRunExpireTime is set to its maximum value (2147483647),
                  either by a set operation or by its initialization from the
                  smLaunchExpireTime object, then it does not tick backwards. A
                  terminated script with a maximum smRunExpireTime value thus is
                  never be aged out and removed from the table.

                  Unlike smRunLifeTime, the mib does not specify a value for
                  smRunExpireTime that can be used to indicate this smRunEntry
                  should be kept forever and never aged out. This agent uses the
                  maximum value (2147483647) to specify that this smRunEntry
                  does not age out after its smRunState transitions to
                  'terminated'.

                  If smRunExpireTime is set to its maximum value (2147483647),
                  either by a set operation or by its initialization from the
                  smLaunchExpireTime object, then it does not tick backwards. A
                  terminated script with a maximum smRunExpireTime value thus is
                  never be aged out and removed from the table."

        VARIATION   smRunLifeTime
            DESCRIPTION
                 "It is not clear from the mib if smRunLifeTime starts to tick
                  backwards when smRunState equals 'initializing' or when
                  smRunState equals 'executing'. This agent implementation
                  starts to decrement smRunLifeTime when smRunState transitions
                  to 'executing'.

                  It is not clear from the mib if smRunLifeTime starts to tick
                  backwards when smRunState equals 'initializing' or when
                  smRunState equals 'executing'. This agent implementation
                  starts to decrement smRunLifeTime when smRunState transitions
                  to 'executing'."

        VARIATION   smRunResult
            SYNTAX  OCTET STRING (SIZE (0..255))
            DESCRIPTION
                 "The maximum size string returned by a read of smRunResult is
                  255 octets.

                  The maximum size string returned by a read of smRunResult is
                  255 octets."

        VARIATION   smRunStartTime
            DESCRIPTION
                 "It is not clear from the mib if smRunStartTime is set when
                  smRunState transitions to 'initializing' or not until
                  smRunState transitions to 'executing'. This agent
                  implementation sets smRunStartTime when smRunState transitions
                  to 'executing'.

                  It is not clear from the mib if smRunStartTime is set when
                  smRunState transitions to 'initializing' or not until
                  smRunState transitions to 'executing'. This agent
                  implementation sets smRunStartTime when smRunState transitions
                  to 'executing'."

        VARIATION   smRunState
            SYNTAX  INTEGER {
                       initializing         (1),
                       executing            (2),
                    -- suspending           (3)
                    -- suspended            (4)
                    -- resuming             (5)
                       aborting             (6),
                       terminated           (7)
                    }
            DESCRIPTION
                 "The 'suspending (3)', 'suspended (4)', and 'resuming (5)'
                  states are not supported.

                  The 'suspending (3)', 'suspended (4)', and 'resuming (5)'
                  states are not supported."

        VARIATION   smScriptAdminStatus
            SYNTAX  INTEGER {
                       enabled              (1),
                       disabled             (2)
                    -- editing              (3)
                    }
            DESCRIPTION
                 "The smScriptAdminStatus state 'editing (3)' is not supported
                  because smCodeTable is not supported.

                  The smScriptAdminStatus state 'editing (3)' is not supported
                  because smCodeTable is not supported."

        VARIATION   smScriptDescr
            SYNTAX  SnmpAdminString (SIZE (0..80))
            DESCRIPTION
                 "The maximum size string supported for smScriptDescr is 80
                  octets.

                  The maximum size string supported for smScriptDescr is 80
                  octets."

        VARIATION   smScriptEntry
            DESCRIPTION
                 "A maximum of 255 smScriptEntry rows are allowed to be created.

                  A maximum of 255 smScriptEntry rows are allowed to be
                  created."

        VARIATION   smScriptLanguage
            SYNTAX  Integer32 (1)
            DESCRIPTION
                 "The only script language supported is the TiMOS CLI that has
                  an smLangIndex value equal 1. smScriptLanguage can only be set
                  to the value 1.

                  The only script language supported is the TiMOS CLI that has
                  an smLangIndex value equal 1. smScriptLanguage can only be set
                  to the value 1."

        VARIATION   smScriptOwner
            SYNTAX  SnmpAdminString (SIZE (1..32))
            DESCRIPTION
                 "The minimum length of smScriptOwner is 1 when creating new
                  entries in tables via SNMP SET requests.

                  The minimum length of smScriptOwner is 1 when creating new
                  entries in tables via SNMP SET requests."

        VARIATION   smScriptSource
            DESCRIPTION
                 "The mib requires that when smScriptAdminStatus is set to
                  'enabled', the agent at that point should 'pull' the script
                  from local cflash or remote URL if one is specified. This
                  agent does not 'pull' scripts to its local storage. The URL
                  specified in smScriptSource is passed as an argument to the
                  CLI 'exec' command when the smRunState transitions to
                  'executing'.

                  The mib states that an empty URL implies that the script
                  scource is already in local storage and are located by some
                  implementation specific mapping scheme between the local
                  storage file name and the smScriptName index. This agent does
                  not support this behavior. An empty smScriptSource URL causes
                  an attempt to set a value to smLaunchStart to return an
                  'inconsistentValue' error.

                  The mib requires that when smScriptAdminStatus is set to
                  'enabled', the agent at that point should 'pull' the script
                  from local cflash or remote URL if one is specified. This
                  agent does not 'pull' scripts to its local storage. The URL
                  specified in smScriptSource is passed as an argument to the
                  CLI 'exec' command when the smRunState transitions to
                  'executing'.

                  The mib states that an empty URL implies that the script
                  scource is already in local storage and are located by some
                  implementation specific mapping scheme between the local
                  storage file name and the smScriptName index. This agent does
                  not support this behavior. An empty smScriptSource URL causes
                  an attempt to set a value to smLaunchStart to return an
                  'inconsistentValue' error."

        VARIATION   smScriptStorageType
            DEFVAL  { nonVolatile  }
            DESCRIPTION
                 "This agent supports only 'nonVolatile' storage type. This is
                  interpreted to be the desired storage type for the
                  configuration of the script row entry.

                  When smLaunchStorageType has a value of 'nonVolatile' its
                  configuration is written to the configuration file upon a
                  'save configuration' operation. If the system reboots between
                  the time this row entry is created and before a 'save
                  configuration' operation is made, this row entry will NOT be
                  restored following the reboot.

                  This agent supports only 'nonVolatile' storage type. This is
                  interpreted to be the desired storage type for the
                  configuration of the script row entry.

                  When smLaunchStorageType has a value of 'nonVolatile' its
                  configuration is written to the configuration file upon a
                  'save configuration' operation. If the system reboots between
                  the time this row entry is created and before a 'save
                  configuration' operation is made, this row entry will NOT be
                  restored following the reboot."

    ::= { tmnxSASAgentV9v0  19 }

--
-- SAS CRON CAPABILITIES
--
tmnxSASCronV9v0                   AGENT-CAPABILITIES
    PRODUCT-RELEASE "Alcatel-Lucent SAS"
    STATUS          current
    DESCRIPTION
         "Implementation of CRON capabilities for Alcatel-Lucent SAS systems
          release 9.0."

    SUPPORTS        DISMAN-SCHEDULE-MIB
        INCLUDES {
           schedCalendarGroup,
           schedGroup2,
           schedNotificationsGroup
        }

        VARIATION   schedInterval
            SYNTAX  Unsigned32 (30..42949672)
            DESCRIPTION
                 "The values supported for schedInterval are between 30 and
                  42949672 seconds. 42949672 seconds creates a maximum interval
                  of 497 days, 2 hours, 27 minutes and 52 seconds.

                  The values supported for schedInterval are between 30 and
                  42949672 seconds. 42949672 seconds creates a maximum interval
                  of 497 days, 2 hours, 27 minutes and 52 seconds."

        VARIATION   schedOwner
            SYNTAX  SnmpAdminString (SIZE (1..32))
            DESCRIPTION
                 "The minimum length of schedOwner is 1 when creating new
                  entries in tables via SNMP SET requests.

                  The minimum length of schedOwner is 1 when creating new
                  entries in tables via SNMP SET requests."

    SUPPORTS        DISMAN-SCRIPT-MIB
        INCLUDES {
           smLanguageGroup,
           smLaunchGroup2,
           smNotificationsGroup2,
           smRunGroup2,
           smScriptGroup2
        }

        VARIATION   smLaunchAdminStatus
            SYNTAX  INTEGER {
                       enabled              (1),
                       disabled             (2)
                    -- autostart            (3)
                    }
            DESCRIPTION
                 "The 'autostart (3)' state is not supported.

                  The mib is not clear if smLaunchAdminStatus can be set to
                  'disabled (2)' if there are associated entries in the
                  smRunTable. This agent does not allow smLaunchAdminStatus to
                  be set to 'disabled (2)' if there are any associated entries
                  in the smRunTable. Any associated smRunEntry must be aborted
                  and aged out before smLaunchAdminStatus can be set to
                  'disabled'.

                  The 'autostart (3)' state is not supported.

                  The mib is not clear if smLaunchAdminStatus can be set to
                  'disabled (2)' if there are associated entries in the
                  smRunTable. This agent does not allow smLaunchAdminStatus to
                  be set to 'disabled (2)' if there are any associated entries
                  in the smRunTable. Any associated smRunEntry must be aborted
                  and aged out before smLaunchAdminStatus can be set to
                  'disabled'."

        VARIATION   smLaunchArgument
            DESCRIPTION
                 "This agent uses smLaunchArgument to specify the URL of the
                  file that is created to hold the CLI session output from the
                  'exec' of the CLI script specified in smScriptSource. The
                  script specified in smScriptSource is executed as if the
                  'exec' '-echo' switch was specified in a CLI CONSOLE/Telnet
                  session and the command echo and any display from CLI 'show'
                  commands specified in the script is redirected to the results
                  file specified in smLaunchArgument.

                  The smLaunchArgument URL should consist of the path and a
                  filename prefix. It refer to either the local cflash drives or
                  a remote file accessed through a remote ftp URL. When the exec
                  results file is created for a specific run of the script, a
                  timestamp of the form '_yyyymmdd-hhmmss.out' is appended on
                  the end of the smLaunchArgument filename prefix. For example,
                  setting smLaunchArgument to
                  'ftp://<user>:<passwd>@<a.b.c.d>/cron/results/test-res' causes
                  a script results file to be created named
                  'cron/results/test-res_yyyymmdd-hhmmss.out'.

                  NOTE: The agent does not have any capability to age out,
                  rotate, delete, or otherwise manage these script results
                  files. It is up to the SR system operator or manager to manage
                  retrieval and cleanup of these files.

                  This agent uses smLaunchArgument to specify the URL of the
                  file that is created to hold the CLI session output from the
                  'exec' of the CLI script specified in smScriptSource. The
                  script specified in smScriptSource is executed as if the
                  'exec' '-echo' switch was specified in a CLI CONSOLE/Telnet
                  session and the command echo and any display from CLI 'show'
                  commands specified in the script is redirected to the results
                  file specified in smLaunchArgument.

                  The smLaunchArgument URL should consist of the path and a
                  filename prefix. It refer to either the local cflash drives or
                  a remote file accessed through a remote ftp URL. When the exec
                  results file is created for a specific run of the script, a
                  timestamp of the form '_yyyymmdd-hhmmss.out' is appended on
                  the end of the smLaunchArgument filename prefix. For example,
                  setting smLaunchArgument to
                  'ftp://<user>:<passwd>@<a.b.c.d>/cron/results/test-res' causes
                  a script results file to be created named
                  'cron/results/test-res_yyyymmdd-hhmmss.out'.

                  NOTE: The agent does not have any capability to age out,
                  rotate, delete, or otherwise manage these script results
                  files. It is up to the SR system operator or manager to manage
                  retrieval and cleanup of these files."

        VARIATION   smLaunchControl
            SYNTAX  INTEGER {
                       abort                (1),
                    -- suspend              (2)
                    -- resume               (3)
                       nop                  (4)
                    }
            DESCRIPTION
                 "The 'suspend (2)' and 'resume (3)' controls are not supported.
                  An attempt to set either value results in an
                  'inconsistentValue' error.

                  The 'suspend (2)' and 'resume (3)' controls are not
                  supported. An attempt to set either value results in an
                  'inconsistentValue' error."

        VARIATION   smLaunchEntry
            DESCRIPTION
                 "A maximum of 255 smLaunchEntry rows are allowed to be created.

                  A maximum of 255 smLaunchEntry rows are allowed to be
                  created."

        VARIATION   smLaunchExpireTime
            DESCRIPTION
                 "Unlike smLaunchLifeTime, the mib does not specify a value for
                  smLaunchExpireTime that can be used to indicate that an
                  associated smRunEntry with a smRunState equal to 'terminated'
                  should be kept forever and never aged out. This agent uses the
                  maximum value (2147483647) to specify that a smRunEntry does
                  not age out after its smRunState transitions to 'terminated'.
                  A terminated smRunEntry with a maximum smRunExpireTime value
                  will never be removed from the table.

                  Unlike smLaunchLifeTime, the mib does not specify a value for
                  smLaunchExpireTime that can be used to indicate that an
                  associated smRunEntry with a smRunState equal to 'terminated'
                  should be kept forever and never aged out. This agent uses the
                  maximum value (2147483647) to specify that a smRunEntry does
                  not age out after its smRunState transitions to 'terminated'.
                  A terminated smRunEntry with a maximum smRunExpireTime value
                  will never be removed from the table."

        VARIATION   smLaunchMaxRunning
            SYNTAX  Unsigned32 (1)
            DESCRIPTION
                 "Concurrently running scripts are not supported by this agent.
                  Scripts are queued and executed one at a time. An attempt to
                  set smLaunchMaxRunning to any value other than 1 results in an
                  'inconsistentValue' error.

                  Concurrently running scripts are not supported by this agent.
                  Scripts are queued and executed one at a time. An attempt to
                  set smLaunchMaxRunning to any value other than 1 results in an
                  'inconsistentValue' error."

        VARIATION   smLaunchOwner
            SYNTAX  SnmpAdminString (SIZE (1..32))
            DESCRIPTION
                 "The minimum length of smLaunchOwner is 1 when creating new
                  entries in tables via SNMP SET requests.

                  The minimum length of smLaunchOwner is 1 when creating new
                  entries in tables via SNMP SET requests."

        VARIATION   smLaunchRowExpireTime
            ACCESS  read-only
            DESCRIPTION
                 "smLaunchRowExpireTime functionality is not supported. Its
                  value cannot be modified. The default value 2147483647 is
                  always returned to indicate that the smLaunchTable row entry
                  will never be aged out.

                  smLaunchRowExpireTime functionality is not supported. Its
                  value cannot be modified. The default value 2147483647 is
                  always returned to indicate that the smLaunchTable row entry
                  will never be aged out."

        VARIATION   smLaunchRunIndexNext
            DESCRIPTION
                 "The mib requires that subsequent reads of smLaunchRunIndexNext
                  must return different values. This agent does not increment
                  the value with every read. A read always returns the next
                  available index value.

                  The mib requires that subsequent reads of
                  smLaunchRunIndexNext must return different values. This agent
                  does not increment the value with every read. A read always
                  returns the next available index value."

        VARIATION   smLaunchStart
            DESCRIPTION
                 "In the 4.0 release there is no user access rights checking to
                  verify that the user setting smLaunchStart has read-access to
                  the script. A user command access profile with RADIUS/TACACS+
                  authentication will be associated to the script in a later
                  release.

                  The mib requires that in order for a set to smLaunchStart to
                  succede th number of concurrently executing scripts must be
                  less than the value of smLaunchMaxRunning. This agent does not
                  support execution of more than one script at a time. Instead,
                  a smRunEntry is created with smRunState equal to
                  'initializing' and sequentially queued for later execution.
                  The maximum number of smRunEntry rows is limited to 255
                  regardless of the value of smRunState.

                  The mib specifies that when the smRunEntry is created by
                  setting smLaunchStart, the smRunStartTime should be set to the
                  current time. Because of the one-at-a-time queuing for
                  execution there may be a long time between entering the
                  'initializing' state and transitioning to the 'executing'
                  state, this agent does not set smRunStartTime until smRunState
                  transitions to 'executing'.

                  In the 4.0 release there is no user access rights checking to
                  verify that the user setting smLaunchStart has read-access to
                  the script. A user command access profile with RADIUS/TACACS+
                  authentication will be associated to the script in a later
                  release.

                  The mib requires that in order for a set to smLaunchStart to
                  succede th number of concurrently executing scripts must be
                  less than the value of smLaunchMaxRunning. This agent does not
                  support execution of more than one script at a time. Instead,
                  a smRunEntry is created with smRunState equal to
                  'initializing' and sequentially queued for later execution.
                  The maximum number of smRunEntry rows is limited to 255
                  regardless of the value of smRunState.

                  The mib specifies that when the smRunEntry is created by
                  setting smLaunchStart, the smRunStartTime should be set to the
                  current time. Because of the one-at-a-time queuing for
                  execution there may be a long time between entering the
                  'initializing' state and transitioning to the 'executing'
                  state, this agent does not set smRunStartTime until smRunState
                  transitions to 'executing'."

        VARIATION   smLaunchStorageType
            SYNTAX  INTEGER {
                    -- other                (1)
                    -- volatile             (2)
                       nonVolatile          (3) -- e.g., in NVRAM
                    -- permanent            (4)
                    -- readOnly             (5)
                    }
            DEFVAL  { nonVolatile  }
            DESCRIPTION
                 "This agent supports only 'nonVolatile (3)' storage type. This
                  is interpreted to be the desired storage type for the
                  configuration of the launch entry.

                  When smLaunchStorageType has a value of 'nonVolatile' its
                  configuration is written to the configuration file upon a
                  'save configuration' operation. If the system reboots between
                  the time this row entry is created and before a 'save
                  configuration' operation is made, this row entry will NOT be
                  restored following the reboot.

                  This agent supports only 'nonVolatile (3)' storage type. This
                  is interpreted to be the desired storage type for the
                  configuration of the launch entry.

                  When smLaunchStorageType has a value of 'nonVolatile' its
                  configuration is written to the configuration file upon a
                  'save configuration' operation. If the system reboots between
                  the time this row entry is created and before a 'save
                  configuration' operation is made, this row entry will NOT be
                  restored following the reboot."

        VARIATION   smRunArgument
            SYNTAX  OCTET STRING (SIZE (0..255))
            DESCRIPTION
                 "The maximum size string returned by a read of smRunArgument is
                  255 octets.

                  The maximum size string returned by a read of smRunArgument
                  is 255 octets."

        VARIATION   smRunControl
            SYNTAX  INTEGER {
                       abort                (1),
                    -- suspend              (2)
                    -- resume               (3)
                       nop                  (4)
                    }
            DESCRIPTION
                 "The 'suspend (2)' and 'resume (3)' controls are not supported.
                  An attempt to set either value results in an
                  'inconsistentValue' error.

                  The 'suspend (2)' and 'resume (3)' controls are not
                  supported. An attempt to set either value results in an
                  'inconsistentValue' error."

        VARIATION   smRunEntry
            DESCRIPTION
                 "A maximum of 255 smRunEntry rows are allowed to be created
                  regardless of the value of smRunState.

                  A maximum of 255 smRunEntry rows are allowed to be created
                  regardless of the value of smRunState."

        VARIATION   smRunExpireTime
            DESCRIPTION
                 "Unlike smRunLifeTime, the mib does not specify a value for
                  smRunExpireTime that can be used to indicate this smRunEntry
                  should be kept forever and never aged out. This agent uses the
                  maximum value (2147483647) to specify that this smRunEntry
                  does not age out after its smRunState transitions to
                  'terminated'.

                  If smRunExpireTime is set to its maximum value (2147483647),
                  either by a set operation or by its initialization from the
                  smLaunchExpireTime object, then it does not tick backwards. A
                  terminated script with a maximum smRunExpireTime value thus is
                  never be aged out and removed from the table.

                  Unlike smRunLifeTime, the mib does not specify a value for
                  smRunExpireTime that can be used to indicate this smRunEntry
                  should be kept forever and never aged out. This agent uses the
                  maximum value (2147483647) to specify that this smRunEntry
                  does not age out after its smRunState transitions to
                  'terminated'.

                  If smRunExpireTime is set to its maximum value (2147483647),
                  either by a set operation or by its initialization from the
                  smLaunchExpireTime object, then it does not tick backwards. A
                  terminated script with a maximum smRunExpireTime value thus is
                  never be aged out and removed from the table."

        VARIATION   smRunLifeTime
            DESCRIPTION
                 "It is not clear from the mib if smRunLifeTime starts to tick
                  backwards when smRunState equals 'initializing' or when
                  smRunState equals 'executing'. This agent implementation
                  starts to decrement smRunLifeTime when smRunState transitions
                  to 'executing'.

                  It is not clear from the mib if smRunLifeTime starts to tick
                  backwards when smRunState equals 'initializing' or when
                  smRunState equals 'executing'. This agent implementation
                  starts to decrement smRunLifeTime when smRunState transitions
                  to 'executing'."

        VARIATION   smRunResult
            SYNTAX  OCTET STRING (SIZE (0..255))
            DESCRIPTION
                 "The maximum size string returned by a read of smRunResult is
                  255 octets.

                  The maximum size string returned by a read of smRunResult is
                  255 octets."

        VARIATION   smRunStartTime
            DESCRIPTION
                 "It is not clear from the mib if smRunStartTime is set when
                  smRunState transitions to 'initializing' or not until
                  smRunState transitions to 'executing'. This agent
                  implementation sets smRunStartTime when smRunState transitions
                  to 'executing'.

                  It is not clear from the mib if smRunStartTime is set when
                  smRunState transitions to 'initializing' or not until
                  smRunState transitions to 'executing'. This agent
                  implementation sets smRunStartTime when smRunState transitions
                  to 'executing'."

        VARIATION   smRunState
            SYNTAX  INTEGER {
                       initializing         (1),
                       executing            (2),
                    -- suspending           (3)
                    -- suspended            (4)
                    -- resuming             (5)
                       aborting             (6),
                       terminated           (7)
                    }
            DESCRIPTION
                 "The 'suspending (3)', 'suspended (4)', and 'resuming (5)'
                  states are not supported.

                  The 'suspending (3)', 'suspended (4)', and 'resuming (5)'
                  states are not supported."

        VARIATION   smScriptAdminStatus
            SYNTAX  INTEGER {
                       enabled              (1),
                       disabled             (2)
                    -- editing              (3)
                    }
            DESCRIPTION
                 "The smScriptAdminStatus state 'editing (3)' is not supported
                  because smCodeTable is not supported.

                  The smScriptAdminStatus state 'editing (3)' is not supported
                  because smCodeTable is not supported."

        VARIATION   smScriptDescr
            SYNTAX  SnmpAdminString (SIZE (0..80))
            DESCRIPTION
                 "The maximum size string supported for smScriptDescr is 80
                  octets.

                  The maximum size string supported for smScriptDescr is 80
                  octets."

        VARIATION   smScriptEntry
            DESCRIPTION
                 "A maximum of 255 smScriptEntry rows are allowed to be created.

                  A maximum of 255 smScriptEntry rows are allowed to be
                  created."

        VARIATION   smScriptLanguage
            SYNTAX  Integer32 (1)
            DESCRIPTION
                 "The only script language supported is the TiMOS CLI that has
                  an smLangIndex value equal 1. smScriptLanguage can only be set
                  to the value 1.

                  The only script language supported is the TiMOS CLI that has
                  an smLangIndex value equal 1. smScriptLanguage can only be set
                  to the value 1."

        VARIATION   smScriptOwner
            SYNTAX  SnmpAdminString (SIZE (1..32))
            DESCRIPTION
                 "The minimum length of smScriptOwner is 1 when creating new
                  entries in tables via SNMP SET requests.

                  The minimum length of smScriptOwner is 1 when creating new
                  entries in tables via SNMP SET requests."

        VARIATION   smScriptSource
            DESCRIPTION
                 "The mib requires that when smScriptAdminStatus is set to
                  'enabled', the agent at that point should 'pull' the script
                  from local cflash or remote URL if one is specified. This
                  agent does not 'pull' scripts to its local storage. The URL
                  specified in smScriptSource is passed as an argument to the
                  CLI 'exec' command when the smRunState transitions to
                  'executing'.

                  The mib states that an empty URL implies that the script
                  scource is already in local storage and are located by some
                  implementation specific mapping scheme between the local
                  storage file name and the smScriptName index. This agent does
                  not support this behavior. An empty smScriptSource URL causes
                  an attempt to set a value to smLaunchStart to return an
                  'inconsistentValue' error.

                  The mib requires that when smScriptAdminStatus is set to
                  'enabled', the agent at that point should 'pull' the script
                  from local cflash or remote URL if one is specified. This
                  agent does not 'pull' scripts to its local storage. The URL
                  specified in smScriptSource is passed as an argument to the
                  CLI 'exec' command when the smRunState transitions to
                  'executing'.

                  The mib states that an empty URL implies that the script
                  scource is already in local storage and are located by some
                  implementation specific mapping scheme between the local
                  storage file name and the smScriptName index. This agent does
                  not support this behavior. An empty smScriptSource URL causes
                  an attempt to set a value to smLaunchStart to return an
                  'inconsistentValue' error."

        VARIATION   smScriptStorageType
            DEFVAL  { nonVolatile  }
            DESCRIPTION
                 "This agent supports only 'nonVolatile' storage type. This is
                  interpreted to be the desired storage type for the
                  configuration of the script row entry.

                  When smLaunchStorageType has a value of 'nonVolatile' its
                  configuration is written to the configuration file upon a
                  'save configuration' operation. If the system reboots between
                  the time this row entry is created and before a 'save
                  configuration' operation is made, this row entry will NOT be
                  restored following the reboot.

                  This agent supports only 'nonVolatile' storage type. This is
                  interpreted to be the desired storage type for the
                  configuration of the script row entry.

                  When smLaunchStorageType has a value of 'nonVolatile' its
                  configuration is written to the configuration file upon a
                  'save configuration' operation. If the system reboots between
                  the time this row entry is created and before a 'save
                  configuration' operation is made, this row entry will NOT be
                  restored following the reboot."

    ::= { tmnxSASAgentV9v0  19 }

--
-- SAS DOT1AG_CFM CAPABILITIES
--
tmnxSASDot1agCfmV9v0              AGENT-CAPABILITIES
    PRODUCT-RELEASE "Alcatel-Lucent SAS"
    STATUS          current
    DESCRIPTION
         "Implementation of Dot1ag CFM capabilities for Alcatel-Lucent SAS
          systems release 9.0."

    SUPPORTS        IEEE8021-CFM-MIB
        INCLUDES {
           dot1agCfmMaGroup,
           dot1agCfmMdGroup,
           dot1agCfmMepDbGroup,
           dot1agCfmMepGroup,
           dot1agCfmNotificationsGroup
        }

        VARIATION   dot1agCfmMaCompIdPermission
            SYNTAX  Dot1agCfmIdPermission {
                       sendIdNone           (1)
                    -- sendIdChassis        (2)
                    -- sendIdManage         (3)
                    -- sendIdChassisManage  (4)
                    -- sendIdDefer          (5)
                    }
            DEFVAL  { defMHFnone  }
            DESCRIPTION
                 "dot1agCfmMaCompIdPermission defaults to, and only supports the
                  value 'defMHFnone'.

                  dot1agCfmMaCompIdPermission defaults to, and only supports
                  the value 'defMHFnone'."

        VARIATION   dot1agCfmMaCompMhfCreation
            SYNTAX  Dot1agCfmMhfCreation {
                       defMHFnone           (1),
                    -- defMHFdefault        (2)
                       defMHFexplicit       (3)
                    -- defMHFdefer          (4)
                    }
            DEFVAL  { defMHFnone  }
            DESCRIPTION
                 "dot1agCfmMaCompMhfCreation defaults to 'defMHFnone' if not
                  specified.

                  dot1agCfmMaCompMhfCreation defaults to 'defMHFnone' if not
                  specified."

        VARIATION   dot1agCfmMaComponentId
            DESCRIPTION
                 "dot1agCfmMaComponentId supports a smaller range than specified
                  in the IEEE-8021-CFM-MIB. The 7x50 series supports the range
                  of 1..2147483647.

                  dot1agCfmMaComponentId supports a smaller range than
                  specified in the IEEE-8021-CFM-MIB. The 7x50 series supports
                  the range of 1..2147483647."

        VARIATION   dot1agCfmMaNetCcmInterval
            SYNTAX  INTEGER {
                    -- intervalInvalid      (0)
                    -- interval300Hz        (1)
                    -- interval10ms         (2)
                    -- interval100ms        (3)
                       interval1s           (4),
                       interval10s          (5),
                       interval1min         (6),
                       interval10min        (7)
                    }
            DEFVAL  { interval10s  }
            DESCRIPTION
                 "dot1agCfmMaNetCcmInterval defaults to 'interval10s' if not
                  specified, and does not support sub-second intervals.

                  dot1agCfmMaNetCcmInterval defaults to 'interval10s' if not
                  specified, and does not support sub-second intervals."

        VARIATION   dot1agCfmMaNetFormat
            DEFVAL  { unsignedInt16  }
            DESCRIPTION
                 "dot1agCfmMaNetFormat defaults to 'unsignedInt16' if not
                  specified.

                  dot1agCfmMaNetFormat defaults to 'unsignedInt16' if not
                  specified."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone'.

                  dot1agCfmMdMhfCreation only supports 'defMHFnone'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone'.

                  dot1agCfmMdMhfIdPermission only supports 'sendIdNone'."

        VARIATION   dot1agCfmMepCcmLtmPriority
            DEFVAL  { 7  }
            DESCRIPTION
                 "dot1agCfmMepCcmLtmPriority defaults to 7, if not specified.

                  dot1agCfmMepCcmLtmPriority defaults to 7, if not specified."

        VARIATION   dot1agCfmMepDbChassisId
            ACCESS  not-implemented
            DESCRIPTION
                 "Not supported.

                  Not supported."

        VARIATION   dot1agCfmMepDbChassisIdSubtype
            ACCESS  not-implemented
            DESCRIPTION
                 "Not supported.

                  Not supported."

        VARIATION   dot1agCfmMepDbManAddress
            ACCESS  not-implemented
            DESCRIPTION
                 "Not supported.

                  Not supported."

        VARIATION   dot1agCfmMepDbManAddressDomain
            ACCESS  not-implemented
            DESCRIPTION
                 "Not supported.

                  Not supported."

        VARIATION   dot1agCfmMepErrorCcmLastFailure
            SYNTAX  OCTET STRING (SIZE(0..1522))
            DESCRIPTION
                 "dot1agCfmMepErrorCcmLastFailure supports a size of 0 octets.

                  dot1agCfmMepErrorCcmLastFailure supports a size of 0 octets."

        VARIATION   dot1agCfmMepFngAlarmTime
            ACCESS  read-only
            DESCRIPTION
                 "read-only implementation.

                  read-only implementation."

        VARIATION   dot1agCfmMepFngResetTime
            ACCESS  read-only
            DESCRIPTION
                 "read-only implementation.

                  read-only implementation."

        VARIATION   dot1agCfmMepPrimaryVid
            SYNTAX  Unsigned32
            DESCRIPTION
                 "dot1agCfmMepPrimaryVid supports the entire Unsigned32 range of
                  values. This is to facilitate Q-in-Q encapsulation for SAPs.

                  dot1agCfmMepPrimaryVid supports the entire Unsigned32 range
                  of values. This is to facilitate Q-in-Q encapsulation for
                  SAPs."

        VARIATION   dot1agCfmMepTransmitLbmDestIsMepId
            DEFVAL  { false  }
            DESCRIPTION
                 "dot1agCfmMepTransmitLbmDestIsMepId defaults to, and only
                  supports the value false.

                  dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0).

                  dot1agCfmMepTransmitLbmDestMepId defaults to, and only
                  supports the value zero (0)."

        VARIATION   dot1agCfmMepTransmitLbmMessages
            SYNTAX  Integer32 (0..5)
            DEFVAL  { 0  }
            DESCRIPTION
                 "dot1agCfmMepTransmitLbmMessages supports a range from 0 to 5
                  messages and defaults to 0.

                  dot1agCfmMepTransmitLbmMessages supports a range from 0 to 5
                  messages and defaults to 0."

        VARIATION   dot1agCfmMepTransmitLbmStatus
            ACCESS  read-only
            DESCRIPTION
                 "read-only implementation.

                  read-only implementation."

        VARIATION   dot1agCfmMepTransmitLbmVlanDropEnable
            ACCESS  read-only
            DESCRIPTION
                 "dot1agCfmMepTransmitLbmVlanDropEnable is implemented as
                  read-only and only supports the value of false.

                  dot1agCfmMepTransmitLbmVlanDropEnable is implemented as
                  read-only and only supports the value of false."

        VARIATION   dot1agCfmMepTransmitLtmTargetIsMepId
            DEFVAL  { false  }
            DESCRIPTION
                 "dot1agCfmMepTransmitLtmTargetIsMepId defaults to, and only
                  supports the value false.

                  dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets.

                  dot1agCfmMepXconCcmLastFailure supports a size of 0 octets."

    SUPPORTS        TIMETRA-IEEE8021-CFM-MIB
        INCLUDES {
           tmnxDot1agCfmMepGroupV7v0,
           tmnxDot1agCfmMipGroupV8v0,
           tmnxDot1agCfmMipNotifyGroup,
           tmnxDot1agCfmNotificationGroup,
           tmnxDot1agCfmSapStackGroup,
           tmnxDot1agCfmSdpBindStackGroup,
           tmnxY1731CfmNotificationGroup
        }

        VARIATION   tmnxDot1agCfmMaMepListMacAddress
            ACCESS  not-implemented
            DESCRIPTION
                 "SNMP set and get are disabled.Only snmp walk is working.

                  SNMP set and get are disabled.Only snmp walk is working."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only.

                  tmnxDot1agCfmMepEthTestPattern supports all zero and all one
                  patterns only."

        VARIATION   tmnxDot1agCfmMepSvcId
            ACCESS  not-implemented
            DESCRIPTION
                 "Not supported.

                  Not supported."

    ::= { tmnxSASAgentV9v0  23 }

--
-- SAS DOT1AG_CFM CAPABILITIES
--
tmnxSASDot1agCfmV9v0              AGENT-CAPABILITIES
    PRODUCT-RELEASE "Alcatel-Lucent SAS"
    STATUS          current
    DESCRIPTION
         "Implementation of Dot1ag CFM capabilities for Alcatel-Lucent SAS
          systems release 9.0."

    SUPPORTS        IEEE8021-CFM-MIB
        INCLUDES {
           dot1agCfmMaGroup,
           dot1agCfmMdGroup,
           dot1agCfmMepDbGroup,
           dot1agCfmMepGroup,
           dot1agCfmNotificationsGroup
        }

        VARIATION   dot1agCfmMaCompIdPermission
            SYNTAX  Dot1agCfmIdPermission {
                       sendIdNone           (1)
                    -- sendIdChassis        (2)
                    -- sendIdManage         (3)
                    -- sendIdChassisManage  (4)
                    -- sendIdDefer          (5)
                    }
            DEFVAL  { defMHFnone  }
            DESCRIPTION
                 "dot1agCfmMaCompIdPermission defaults to, and only supports the
                  value 'defMHFnone'.

                  dot1agCfmMaCompIdPermission defaults to, and only supports
                  the value 'defMHFnone'."

        VARIATION   dot1agCfmMaCompMhfCreation
            SYNTAX  Dot1agCfmMhfCreation {
                       defMHFnone           (1),
                    -- defMHFdefault        (2)
                       defMHFexplicit       (3)
                    -- defMHFdefer          (4)
                    }
            DEFVAL  { defMHFnone  }
            DESCRIPTION
                 "dot1agCfmMaCompMhfCreation defaults to 'defMHFnone' if not
                  specified.

                  dot1agCfmMaCompMhfCreation defaults to 'defMHFnone' if not
                  specified."

        VARIATION   dot1agCfmMaComponentId
            DESCRIPTION
                 "dot1agCfmMaComponentId supports a smaller range than specified
                  in the IEEE-8021-CFM-MIB. The 7x50 series supports the range
                  of 1..2147483647.

                  dot1agCfmMaComponentId supports a smaller range than
                  specified in the IEEE-8021-CFM-MIB. The 7x50 series supports
                  the range of 1..2147483647."

        VARIATION   dot1agCfmMaNetCcmInterval
            SYNTAX  INTEGER {
                    -- intervalInvalid      (0)
                    -- interval300Hz        (1)
                    -- interval10ms         (2)
                    -- interval100ms        (3)
                       interval1s           (4),
                       interval10s          (5),
                       interval1min         (6),
                       interval10min        (7)
                    }
            DEFVAL  { interval10s  }
            DESCRIPTION
                 "dot1agCfmMaNetCcmInterval defaults to 'interval10s' if not
                  specified, and does not support sub-second intervals.

                  dot1agCfmMaNetCcmInterval defaults to 'interval10s' if not
                  specified, and does not support sub-second intervals."

        VARIATION   dot1agCfmMaNetFormat
            DEFVAL  { unsignedInt16  }
            DESCRIPTION
                 "dot1agCfmMaNetFormat defaults to 'unsignedInt16' if not
                  specified.

                  dot1agCfmMaNetFormat defaults to 'unsignedInt16' if not
                  specified."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone'.

                  dot1agCfmMdMhfCreation only supports 'defMHFnone'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone'.

                  dot1agCfmMdMhfIdPermission only supports 'sendIdNone'."

        VARIATION   dot1agCfmMepCcmLtmPriority
            DEFVAL  { 7  }
            DESCRIPTION
                 "dot1agCfmMepCcmLtmPriority defaults to 7, if not specified.

                  dot1agCfmMepCcmLtmPriority defaults to 7, if not specified."

        VARIATION   dot1agCfmMepDbChassisId
            ACCESS  not-implemented
            DESCRIPTION
                 "Not supported.

                  Not supported."

        VARIATION   dot1agCfmMepDbChassisIdSubtype
            ACCESS  not-implemented
            DESCRIPTION
                 "Not supported.

                  Not supported."

        VARIATION   dot1agCfmMepDbManAddress
            ACCESS  not-implemented
            DESCRIPTION
                 "Not supported.

                  Not supported."

        VARIATION   dot1agCfmMepDbManAddressDomain
            ACCESS  not-implemented
            DESCRIPTION
                 "Not supported.

                  Not supported."

        VARIATION   dot1agCfmMepErrorCcmLastFailure
            SYNTAX  OCTET STRING (SIZE(0..1522))
            DESCRIPTION
                 "dot1agCfmMepErrorCcmLastFailure supports a size of 0 octets.

                  dot1agCfmMepErrorCcmLastFailure supports a size of 0 octets."

        VARIATION   dot1agCfmMepFngAlarmTime
            ACCESS  read-only
            DESCRIPTION
                 "read-only implementation.

                  read-only implementation."

        VARIATION   dot1agCfmMepFngResetTime
            ACCESS  read-only
            DESCRIPTION
                 "read-only implementation.

                  read-only implementation."

        VARIATION   dot1agCfmMepPrimaryVid
            SYNTAX  Unsigned32
            DESCRIPTION
                 "dot1agCfmMepPrimaryVid supports the entire Unsigned32 range of
                  values. This is to facilitate Q-in-Q encapsulation for SAPs.

                  dot1agCfmMepPrimaryVid supports the entire Unsigned32 range
                  of values. This is to facilitate Q-in-Q encapsulation for
                  SAPs."

        VARIATION   dot1agCfmMepTransmitLbmDestIsMepId
            DEFVAL  { false  }
            DESCRIPTION
                 "dot1agCfmMepTransmitLbmDestIsMepId defaults to, and only
                  supports the value false.

                  dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0).

                  dot1agCfmMepTransmitLbmDestMepId defaults to, and only
                  supports the value zero (0)."

        VARIATION   dot1agCfmMepTransmitLbmMessages
            SYNTAX  Integer32 (0..5)
            DEFVAL  { 0  }
            DESCRIPTION
                 "dot1agCfmMepTransmitLbmMessages supports a range from 0 to 5
                  messages and defaults to 0.

                  dot1agCfmMepTransmitLbmMessages supports a range from 0 to 5
                  messages and defaults to 0."

        VARIATION   dot1agCfmMepTransmitLbmStatus
            ACCESS  read-only
            DESCRIPTION
                 "read-only implementation.

                  read-only implementation."

        VARIATION   dot1agCfmMepTransmitLbmVlanDropEnable
            ACCESS  read-only
            DESCRIPTION
                 "dot1agCfmMepTransmitLbmVlanDropEnable is implemented as
                  read-only and only supports the value of false.

                  dot1agCfmMepTransmitLbmVlanDropEnable is implemented as
                  read-only and only supports the value of false."

        VARIATION   dot1agCfmMepTransmitLtmTargetIsMepId
            DEFVAL  { false  }
            DESCRIPTION
                 "dot1agCfmMepTransmitLtmTargetIsMepId defaults to, and only
                  supports the value false.

                  dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets.

                  dot1agCfmMepXconCcmLastFailure supports a size of 0 octets."

    SUPPORTS        TIMETRA-IEEE8021-CFM-MIB
        INCLUDES {
           tmnxDot1agCfmMepGroupV7v0,
           tmnxDot1agCfmMipGroupV8v0,
           tmnxDot1agCfmMipNotifyGroup,
           tmnxDot1agCfmNotificationGroup,
           tmnxDot1agCfmSapStackGroup,
           tmnxDot1agCfmSdpBindStackGroup,
           tmnxY1731CfmNotificationGroup
        }

        VARIATION   tmnxDot1agCfmMaMepListMacAddress
            ACCESS  not-implemented
            DESCRIPTION
                 "SNMP set and get are disabled.Only snmp walk is working.

                  SNMP set and get are disabled.Only snmp walk is working."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only.

                  tmnxDot1agCfmMepEthTestPattern supports all zero and all one
                  patterns only."

        VARIATION   tmnxDot1agCfmMepSvcId
            ACCESS  not-implemented
            DESCRIPTION
                 "Not supported.

                  Not supported."

    ::= { tmnxSASAgentV9v0  23 }

--
-- SAST DOT1AG_CFM CAPABILITIES
--
tmnxSASTDot1agCfmV9v0             AGENT-CAPABILITIES
    PRODUCT-RELEASE "Alcatel-Lucent SAS"
    STATUS          current
    DESCRIPTION
         "Implementation of Dot1ag CFM capabilities for Alcatel-Lucent SAST
          systems release 9.0."

    SUPPORTS        IEEE8021-CFM-MIB
        INCLUDES {
           dot1agCfmMaGroup,
           dot1agCfmMdGroup,
           dot1agCfmMepDbGroup,
           dot1agCfmMepGroup,
           dot1agCfmNotificationsGroup
        }

        VARIATION   dot1agCfmMaCompIdPermission
            SYNTAX  Dot1agCfmIdPermission {
                       sendIdNone           (1)
                    -- sendIdChassis        (2)
                    -- sendIdManage         (3)
                    -- sendIdChassisManage  (4)
                    -- sendIdDefer          (5)
                    }
            DEFVAL  { defMHFnone  }
            DESCRIPTION
                 "dot1agCfmMaCompIdPermission defaults to, and only supports the
                  value 'defMHFnone'."

        VARIATION   dot1agCfmMaCompMhfCreation
            SYNTAX  Dot1agCfmMhfCreation {
                       defMHFnone           (1),
                    -- defMHFdefault        (2)
                       defMHFexplicit       (3)
                    -- defMHFdefer          (4)
                    }
            DEFVAL  { defMHFnone  }
            DESCRIPTION
                 "dot1agCfmMaCompMhfCreation defaults to 'defMHFnone' if not
                  specified."

        VARIATION   dot1agCfmMaComponentId
            DESCRIPTION
                 "dot1agCfmMaComponentId supports a smaller range than specified
                  in the IEEE-8021-CFM-MIB. The 7x50 series supports the range
                  of 1..2147483647."

        VARIATION   dot1agCfmMaNetCcmInterval
            SYNTAX  INTEGER {
                    -- intervalInvalid      (0)
                    -- interval300Hz        (1)
                    -- interval10ms         (2)
                    -- interval100ms        (3)
                       interval1s           (4),
                       interval10s          (5),
                       interval1min         (6),
                       interval10min        (7)
                    }
            DEFVAL  { interval10s  }
            DESCRIPTION
                 "dot1agCfmMaNetCcmInterval defaults to 'interval10s' if not
                  specified, and does not support sub-second intervals."

        VARIATION   dot1agCfmMaNetFormat
            DEFVAL  { unsignedInt16  }
            DESCRIPTION
                 "dot1agCfmMaNetFormat defaults to 'unsignedInt16' if not
                  specified."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone'."

        VARIATION   dot1agCfmMepCcmLtmPriority
            DEFVAL  { 7  }
            DESCRIPTION
                 "dot1agCfmMepCcmLtmPriority defaults to 7, if not specified."

        VARIATION   dot1agCfmMepDbChassisId
            ACCESS  not-implemented
            DESCRIPTION
                 "Not supported."

        VARIATION   dot1agCfmMepDbChassisIdSubtype
            ACCESS  not-implemented
            DESCRIPTION
                 "Not supported."

        VARIATION   dot1agCfmMepDbManAddress
            ACCESS  not-implemented
            DESCRIPTION
                 "Not supported."

        VARIATION   dot1agCfmMepDbManAddressDomain
            ACCESS  not-implemented
            DESCRIPTION
                 "Not supported."

        VARIATION   dot1agCfmMepDirection
            ACCESS  not-implemented
            DESCRIPTION
                 "Not supported."

        VARIATION   dot1agCfmMepErrorCcmLastFailure
            SYNTAX  OCTET STRING (SIZE(0..1522))
            DESCRIPTION
                 "dot1agCfmMepErrorCcmLastFailure supports a size of 0 octets."

        VARIATION   dot1agCfmMepFngAlarmTime
            ACCESS  read-only
            DESCRIPTION
                 "read-only implementation."

        VARIATION   dot1agCfmMepFngResetTime
            ACCESS  read-only
            DESCRIPTION
                 "read-only implementation."

        VARIATION   dot1agCfmMepPrimaryVid
            SYNTAX  Unsigned32
            DESCRIPTION
                 "dot1agCfmMepPrimaryVid supports the entire Unsigned32 range of
                  values. This is to facilitate Q-in-Q encapsulation for SAPs."

        VARIATION   dot1agCfmMepTransmitLbmDestIsMepId
            DEFVAL  { false  }
            DESCRIPTION
                 "dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0)."

        VARIATION   dot1agCfmMepTransmitLbmMessages
            SYNTAX  Integer32 (0..5)
            DEFVAL  { 0  }
            DESCRIPTION
                 "dot1agCfmMepTransmitLbmMessages supports a range from 0 to 5
                  messages and defaults to 0."

        VARIATION   dot1agCfmMepTransmitLbmStatus
            ACCESS  read-only
            DESCRIPTION
                 "read-only implementation."

        VARIATION   dot1agCfmMepTransmitLbmVlanDropEnable
            ACCESS  read-only
            DESCRIPTION
                 "dot1agCfmMepTransmitLbmVlanDropEnable is implemented as
                  read-only and only supports the value of false."

        VARIATION   dot1agCfmMepTransmitLtmTargetIsMepId
            DEFVAL  { false  }
            DESCRIPTION
                 "dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets."

    SUPPORTS        TIMETRA-IEEE8021-CFM-MIB
        INCLUDES {
           tmnxDot1agCfmMepGroupV7v0,
           tmnxDot1agCfmMipGroupV8v0,
           tmnxDot1agCfmMipNotifyGroup,
           tmnxDot1agCfmNotificationGroup,
           tmnxDot1agCfmSapStackGroup,
           tmnxDot1agCfmSdpBindStackGroup,
           tmnxY1731CfmNotificationGroup
        }

        VARIATION   tmnxDot1agCfmMaMepListMacAddress
            ACCESS  not-implemented
            DESCRIPTION
                 "SNMP set and get are disabled.Only snmp walk is working."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only."

        VARIATION   tmnxDot1agCfmMepSvcId
            ACCESS  not-implemented
            DESCRIPTION
                 "Not supported."

    ::= { tmnxSASTAgentV9v0  23 }

--
-- SASMxp DOT1AG_CFM CAPABILITIES
--
tmnxSASMxpDot1agCfmV9v0           AGENT-CAPABILITIES
    PRODUCT-RELEASE "Alcatel-Lucent SAS"
    STATUS          current
    DESCRIPTION
         "Implementation of Dot1ag CFM capabilities for Alcatel-Lucent SASM xp
          systems release 9.0."

    SUPPORTS        IEEE8021-CFM-MIB
        INCLUDES {
           dot1agCfmMaGroup,
           dot1agCfmMdGroup,
           dot1agCfmMepDbGroup,
           dot1agCfmMepGroup,
           dot1agCfmNotificationsGroup
        }

        VARIATION   dot1agCfmMaCompIdPermission
            SYNTAX  Dot1agCfmIdPermission {
                       sendIdNone           (1)
                    -- sendIdChassis        (2)
                    -- sendIdManage         (3)
                    -- sendIdChassisManage  (4)
                    -- sendIdDefer          (5)
                    }
            DEFVAL  { defMHFnone  }
            DESCRIPTION
                 "dot1agCfmMaCompIdPermission defaults to, and only supports the
                  value 'defMHFnone'."

        VARIATION   dot1agCfmMaCompMhfCreation
            SYNTAX  Dot1agCfmMhfCreation {
                       defMHFnone           (1),
                    -- defMHFdefault        (2)
                       defMHFexplicit       (3)
                    -- defMHFdefer          (4)
                    }
            DEFVAL  { defMHFnone  }
            DESCRIPTION
                 "dot1agCfmMaCompMhfCreation defaults to 'defMHFnone' if not
                  specified."

        VARIATION   dot1agCfmMaComponentId
            DESCRIPTION
                 "dot1agCfmMaComponentId supports a smaller range than specified
                  in the IEEE-8021-CFM-MIB. The 7x50 series supports the range
                  of 1..2147483647."

        VARIATION   dot1agCfmMaNetCcmInterval
            SYNTAX  INTEGER {
                    -- intervalInvalid      (0)
                    -- interval300Hz        (1)
                    -- interval10ms         (2)
                    -- interval100ms        (3)
                       interval1s           (4),
                       interval10s          (5),
                       interval1min         (6),
                       interval10min        (7)
                    }
            DEFVAL  { interval10s  }
            DESCRIPTION
                 "dot1agCfmMaNetCcmInterval defaults to 'interval10s' if not
                  specified, and does not support sub-second intervals."

        VARIATION   dot1agCfmMaNetFormat
            DEFVAL  { unsignedInt16  }
            DESCRIPTION
                 "dot1agCfmMaNetFormat defaults to 'unsignedInt16' if not
                  specified."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone'."

        VARIATION   dot1agCfmMepCcmLtmPriority
            DEFVAL  { 7  }
            DESCRIPTION
                 "dot1agCfmMepCcmLtmPriority defaults to 7, if not specified."

        VARIATION   dot1agCfmMepDbChassisId
            ACCESS  not-implemented
            DESCRIPTION
                 "Not supported."

        VARIATION   dot1agCfmMepDbChassisIdSubtype
            ACCESS  not-implemented
            DESCRIPTION
                 "Not supported."

        VARIATION   dot1agCfmMepDbManAddress
            ACCESS  not-implemented
            DESCRIPTION
                 "Not supported."

        VARIATION   dot1agCfmMepDbManAddressDomain
            ACCESS  not-implemented
            DESCRIPTION
                 "Not supported."

        VARIATION   dot1agCfmMepDirection
            ACCESS  not-implemented
            DESCRIPTION
                 "Not supported."

        VARIATION   dot1agCfmMepErrorCcmLastFailure
            SYNTAX  OCTET STRING (SIZE(0..1522))
            DESCRIPTION
                 "dot1agCfmMepErrorCcmLastFailure supports a size of 0 octets."

        VARIATION   dot1agCfmMepFngAlarmTime
            ACCESS  read-only
            DESCRIPTION
                 "read-only implementation."

        VARIATION   dot1agCfmMepFngResetTime
            ACCESS  read-only
            DESCRIPTION
                 "read-only implementation."

        VARIATION   dot1agCfmMepPrimaryVid
            SYNTAX  Unsigned32
            DESCRIPTION
                 "dot1agCfmMepPrimaryVid supports the entire Unsigned32 range of
                  values. This is to facilitate Q-in-Q encapsulation for SAPs."

        VARIATION   dot1agCfmMepTransmitLbmDestIsMepId
            DEFVAL  { false  }
            DESCRIPTION
                 "dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0)."

        VARIATION   dot1agCfmMepTransmitLbmMessages
            SYNTAX  Integer32 (0..5)
            DEFVAL  { 0  }
            DESCRIPTION
                 "dot1agCfmMepTransmitLbmMessages supports a range from 0 to 5
                  messages and defaults to 0."

        VARIATION   dot1agCfmMepTransmitLbmStatus
            ACCESS  read-only
            DESCRIPTION
                 "read-only implementation."

        VARIATION   dot1agCfmMepTransmitLbmVlanDropEnable
            ACCESS  read-only
            DESCRIPTION
                 "dot1agCfmMepTransmitLbmVlanDropEnable is implemented as
                  read-only and only supports the value of false."

        VARIATION   dot1agCfmMepTransmitLtmTargetIsMepId
            DEFVAL  { false  }
            DESCRIPTION
                 "dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets."

    SUPPORTS        TIMETRA-IEEE8021-CFM-MIB
        INCLUDES {
           tmnxDot1agCfmMepGroupV7v0,
           tmnxDot1agCfmMipGroupV8v0,
           tmnxDot1agCfmMipNotifyGroup,
           tmnxDot1agCfmNotificationGroup,
           tmnxDot1agCfmSapStackGroup,
           tmnxDot1agCfmSdpBindStackGroup,
           tmnxY1731CfmNotificationGroup
        }

        VARIATION   tmnxDot1agCfmMaMepListMacAddress
            ACCESS  not-implemented
            DESCRIPTION
                 "SNMP set and get are disabled.Only snmp walk is working."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only."

        VARIATION   tmnxDot1agCfmMepSvcId
            ACCESS  not-implemented
            DESCRIPTION
                 "Not supported."

    ::= { tmnxSASMxpAgentV9v0  23 }

--
-- SASSx DOT1AG_CFM CAPABILITIES
--
tmnxSASSxDot1agCfmV9v0            AGENT-CAPABILITIES
    PRODUCT-RELEASE "Alcatel-Lucent SAS"
    STATUS          current
    DESCRIPTION
         "Implementation of Dot1ag CFM capabilities for Alcatel-Lucent SASS x
          systems release 9.0."

    SUPPORTS        IEEE8021-CFM-MIB
        INCLUDES {
           dot1agCfmMaGroup,
           dot1agCfmMdGroup,
           dot1agCfmMepDbGroup,
           dot1agCfmMepGroup,
           dot1agCfmNotificationsGroup
        }

        VARIATION   dot1agCfmMaCompIdPermission
            SYNTAX  Dot1agCfmIdPermission {
                       sendIdNone           (1)
                    -- sendIdChassis        (2)
                    -- sendIdManage         (3)
                    -- sendIdChassisManage  (4)
                    -- sendIdDefer          (5)
                    }
            DEFVAL  { defMHFnone  }
            DESCRIPTION
                 "dot1agCfmMaCompIdPermission defaults to, and only supports the
                  value 'defMHFnone'."

        VARIATION   dot1agCfmMaCompMhfCreation
            SYNTAX  Dot1agCfmMhfCreation {
                       defMHFnone           (1),
                    -- defMHFdefault        (2)
                       defMHFexplicit       (3)
                    -- defMHFdefer          (4)
                    }
            DEFVAL  { defMHFnone  }
            DESCRIPTION
                 "dot1agCfmMaCompMhfCreation defaults to 'defMHFnone' if not
                  specified."

        VARIATION   dot1agCfmMaComponentId
            DESCRIPTION
                 "dot1agCfmMaComponentId supports a smaller range than specified
                  in the IEEE-8021-CFM-MIB. The 7x50 series supports the range
                  of 1..2147483647."

        VARIATION   dot1agCfmMaNetCcmInterval
            SYNTAX  INTEGER {
                    -- intervalInvalid      (0)
                    -- interval300Hz        (1)
                    -- interval10ms         (2)
                    -- interval100ms        (3)
                       interval1s           (4),
                       interval10s          (5),
                       interval1min         (6),
                       interval10min        (7)
                    }
            DEFVAL  { interval10s  }
            DESCRIPTION
                 "dot1agCfmMaNetCcmInterval defaults to 'interval10s' if not
                  specified, and does not support sub-second intervals."

        VARIATION   dot1agCfmMaNetFormat
            DEFVAL  { unsignedInt16  }
            DESCRIPTION
                 "dot1agCfmMaNetFormat defaults to 'unsignedInt16' if not
                  specified."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone'."

        VARIATION   dot1agCfmMepCcmLtmPriority
            DEFVAL  { 7  }
            DESCRIPTION
                 "dot1agCfmMepCcmLtmPriority defaults to 7, if not specified."

        VARIATION   dot1agCfmMepDbChassisId
            ACCESS  not-implemented
            DESCRIPTION
                 "Not supported."

        VARIATION   dot1agCfmMepDbChassisIdSubtype
            ACCESS  not-implemented
            DESCRIPTION
                 "Not supported."

        VARIATION   dot1agCfmMepDbManAddress
            ACCESS  not-implemented
            DESCRIPTION
                 "Not supported."

        VARIATION   dot1agCfmMepDbManAddressDomain
            ACCESS  not-implemented
            DESCRIPTION
                 "Not supported."

        VARIATION   dot1agCfmMepDirection
            ACCESS  not-implemented
            DESCRIPTION
                 "Not supported."

        VARIATION   dot1agCfmMepErrorCcmLastFailure
            SYNTAX  OCTET STRING (SIZE(0..1522))
            DESCRIPTION
                 "dot1agCfmMepErrorCcmLastFailure supports a size of 0 octets."

        VARIATION   dot1agCfmMepFngAlarmTime
            ACCESS  read-only
            DESCRIPTION
                 "read-only implementation."

        VARIATION   dot1agCfmMepFngResetTime
            ACCESS  read-only
            DESCRIPTION
                 "read-only implementation."

        VARIATION   dot1agCfmMepPrimaryVid
            SYNTAX  Unsigned32
            DESCRIPTION
                 "dot1agCfmMepPrimaryVid supports the entire Unsigned32 range of
                  values. This is to facilitate Q-in-Q encapsulation for SAPs."

        VARIATION   dot1agCfmMepTransmitLbmDestIsMepId
            DEFVAL  { false  }
            DESCRIPTION
                 "dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0)."

        VARIATION   dot1agCfmMepTransmitLbmMessages
            SYNTAX  Integer32 (0..5)
            DEFVAL  { 0  }
            DESCRIPTION
                 "dot1agCfmMepTransmitLbmMessages supports a range from 0 to 5
                  messages and defaults to 0."

        VARIATION   dot1agCfmMepTransmitLbmStatus
            ACCESS  read-only
            DESCRIPTION
                 "read-only implementation."

        VARIATION   dot1agCfmMepTransmitLbmVlanDropEnable
            ACCESS  read-only
            DESCRIPTION
                 "dot1agCfmMepTransmitLbmVlanDropEnable is implemented as
                  read-only and only supports the value of false."

        VARIATION   dot1agCfmMepTransmitLtmTargetIsMepId
            DEFVAL  { false  }
            DESCRIPTION
                 "dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets."

    SUPPORTS        TIMETRA-IEEE8021-CFM-MIB
        INCLUDES {
           tmnxDot1agCfmMepGroupV7v0,
           tmnxDot1agCfmMipGroupV8v0,
           tmnxDot1agCfmMipNotifyGroup,
           tmnxDot1agCfmNotificationGroup,
           tmnxDot1agCfmSapStackGroup,
           tmnxDot1agCfmSdpBindStackGroup,
           tmnxY1731CfmNotificationGroup
        }

        VARIATION   tmnxDot1agCfmMaMepListMacAddress
            ACCESS  not-implemented
            DESCRIPTION
                 "SNMP set and get are disabled.Only snmp walk is working."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only."

        VARIATION   tmnxDot1agCfmMepSvcId
            ACCESS  not-implemented
            DESCRIPTION
                 "Not supported."

    ::= { tmnxSASSxAgentV9v0  23 }

--
-- SASK DOT1AG_CFM CAPABILITIES
--
tmnxSASKDot1agCfmV9v0             AGENT-CAPABILITIES
    PRODUCT-RELEASE "Alcatel-Lucent SAS"
    STATUS          current
    DESCRIPTION
         "Implementation of Dot1ag CFM capabilities for Alcatel-Lucent SASK
          systems release 9.0."

    SUPPORTS        IEEE8021-CFM-MIB
        INCLUDES {
           dot1agCfmMaGroup,
           dot1agCfmMdGroup,
           dot1agCfmMepDbGroup,
           dot1agCfmMepGroup,
           dot1agCfmNotificationsGroup
        }

        VARIATION   dot1agCfmMaCompIdPermission
            SYNTAX  Dot1agCfmIdPermission {
                       sendIdNone           (1)
                    -- sendIdChassis        (2)
                    -- sendIdManage         (3)
                    -- sendIdChassisManage  (4)
                    -- sendIdDefer          (5)
                    }
            DEFVAL  { defMHFnone  }
            DESCRIPTION
                 "dot1agCfmMaCompIdPermission defaults to, and only supports the
                  value 'defMHFnone'."

        VARIATION   dot1agCfmMaCompMhfCreation
            SYNTAX  Dot1agCfmMhfCreation {
                       defMHFnone           (1),
                    -- defMHFdefault        (2)
                       defMHFexplicit       (3)
                    -- defMHFdefer          (4)
                    }
            DEFVAL  { defMHFnone  }
            DESCRIPTION
                 "dot1agCfmMaCompMhfCreation defaults to 'defMHFnone' if not
                  specified."

        VARIATION   dot1agCfmMaComponentId
            DESCRIPTION
                 "dot1agCfmMaComponentId supports a smaller range than specified
                  in the IEEE-8021-CFM-MIB. The 7x50 series supports the range
                  of 1..2147483647."

        VARIATION   dot1agCfmMaNetCcmInterval
            SYNTAX  INTEGER {
                    -- intervalInvalid      (0)
                    -- interval300Hz        (1)
                    -- interval10ms         (2)
                    -- interval100ms        (3)
                       interval1s           (4),
                       interval10s          (5),
                       interval1min         (6),
                       interval10min        (7)
                    }
            DEFVAL  { interval10s  }
            DESCRIPTION
                 "dot1agCfmMaNetCcmInterval defaults to 'interval10s' if not
                  specified, and does not support sub-second intervals."

        VARIATION   dot1agCfmMaNetFormat
            DEFVAL  { unsignedInt16  }
            DESCRIPTION
                 "dot1agCfmMaNetFormat defaults to 'unsignedInt16' if not
                  specified."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone'."

        VARIATION   dot1agCfmMepCcmLtmPriority
            DEFVAL  { 7  }
            DESCRIPTION
                 "dot1agCfmMepCcmLtmPriority defaults to 7, if not specified."

        VARIATION   dot1agCfmMepDbChassisId
            ACCESS  not-implemented
            DESCRIPTION
                 "Not supported."

        VARIATION   dot1agCfmMepDbChassisIdSubtype
            ACCESS  not-implemented
            DESCRIPTION
                 "Not supported."

        VARIATION   dot1agCfmMepDbManAddress
            ACCESS  not-implemented
            DESCRIPTION
                 "Not supported."

        VARIATION   dot1agCfmMepDbManAddressDomain
            ACCESS  not-implemented
            DESCRIPTION
                 "Not supported."

        VARIATION   dot1agCfmMepDirection
            ACCESS  not-implemented
            DESCRIPTION
                 "Not supported."

        VARIATION   dot1agCfmMepErrorCcmLastFailure
            SYNTAX  OCTET STRING (SIZE(0..1522))
            DESCRIPTION
                 "dot1agCfmMepErrorCcmLastFailure supports a size of 0 octets."

        VARIATION   dot1agCfmMepFngAlarmTime
            ACCESS  read-only
            DESCRIPTION
                 "read-only implementation."

        VARIATION   dot1agCfmMepFngResetTime
            ACCESS  read-only
            DESCRIPTION
                 "read-only implementation."

        VARIATION   dot1agCfmMepPrimaryVid
            SYNTAX  Unsigned32
            DESCRIPTION
                 "dot1agCfmMepPrimaryVid supports the entire Unsigned32 range of
                  values. This is to facilitate Q-in-Q encapsulation for SAPs."

        VARIATION   dot1agCfmMepTransmitLbmDestIsMepId
            DEFVAL  { false  }
            DESCRIPTION
                 "dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0)."

        VARIATION   dot1agCfmMepTransmitLbmMessages
            SYNTAX  Integer32 (0..5)
            DEFVAL  { 0  }
            DESCRIPTION
                 "dot1agCfmMepTransmitLbmMessages supports a range from 0 to 5
                  messages and defaults to 0."

        VARIATION   dot1agCfmMepTransmitLbmStatus
            ACCESS  read-only
            DESCRIPTION
                 "read-only implementation."

        VARIATION   dot1agCfmMepTransmitLbmVlanDropEnable
            ACCESS  read-only
            DESCRIPTION
                 "dot1agCfmMepTransmitLbmVlanDropEnable is implemented as
                  read-only and only supports the value of false."

        VARIATION   dot1agCfmMepTransmitLtmTargetIsMepId
            DEFVAL  { false  }
            DESCRIPTION
                 "dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets."

    SUPPORTS        TIMETRA-IEEE8021-CFM-MIB
        INCLUDES {
           tmnxDot1agCfmMepGroupV7v0,
           tmnxDot1agCfmMipGroupV8v0,
           tmnxDot1agCfmMipNotifyGroup,
           tmnxDot1agCfmNotificationGroup,
           tmnxDot1agCfmSapStackGroup,
           tmnxDot1agCfmSdpBindStackGroup,
           tmnxY1731CfmNotificationGroup
        }

        VARIATION   tmnxDot1agCfmMaMepListMacAddress
            ACCESS  not-implemented
            DESCRIPTION
                 "SNMP set and get are disabled.Only snmp walk is working."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only."

        VARIATION   tmnxDot1agCfmMepSvcId
            ACCESS  not-implemented
            DESCRIPTION
                 "Not supported."

    ::= { tmnxSASKAgentV9v0  23 }

--
-- SAS DOT3_OAM CAPABILITIES
--
tmnxSASDot3OamV9v0                AGENT-CAPABILITIES
    PRODUCT-RELEASE "Alcatel-Lucent SAS"
    STATUS          current
    DESCRIPTION
         "Implementation of Ethernet OAM (802.3ah) capabilities for
          Alcatel-Lucent SAS systems release 9.0."

    SUPPORTS        DOT3-OAM-MIB
        INCLUDES {
           dot3OamControlGroup,
           dot3OamEventLogGroup,
           dot3OamLoopbackGroup,
           dot3OamNotificationGroup,
           dot3OamPeerGroup,
           dot3OamStatsBaseGroup
        }

        VARIATION   dot3OamEventLogRunningTotal
            ACCESS  not-implemented
            DESCRIPTION
                 "Not supported.

                  Not supported."

        VARIATION   dot3OamEventLogThresholdHi
            ACCESS  not-implemented
            DESCRIPTION
                 "Not supported.

                  Not supported."

        VARIATION   dot3OamEventLogThresholdLo
            ACCESS  not-implemented
            DESCRIPTION
                 "Not supported.

                  Not supported."

        VARIATION   dot3OamEventLogValue
            ACCESS  not-implemented
            DESCRIPTION
                 "Not supported.

                  Not supported."

        VARIATION   dot3OamEventLogWindowHi
            ACCESS  not-implemented
            DESCRIPTION
                 "Not supported.

                  Not supported."

        VARIATION   dot3OamEventLogWindowLo
            ACCESS  not-implemented
            DESCRIPTION
                 "Not supported.

                  Not supported."

        VARIATION   dot3OamThresholdEvent
            ACCESS  not-implemented
            DESCRIPTION
                 "Not supported.

                  Not supported."

    SUPPORTS        TIMETRA-DOT3-OAM-MIB
        INCLUDES {
           tmnxDot3OamEventConfigEntry,
           tmnxDot3OamLoopbackGroup,
           tmnxDot3OamNotificationV6v0Group,
           tmnxDot3OamV6v0Group,
           tmnxDot3OamV6v1Group
        }

        VARIATION   tmnxDot3OamErrFrmEnabled
            ACCESS  not-implemented
            DESCRIPTION
                 "Not supported.

                  Not supported."

        VARIATION   tmnxDot3OamErrFrmPrdEnabled
            ACCESS  not-implemented
            DESCRIPTION
                 "Not supported.

                  Not supported."

        VARIATION   tmnxDot3OamErrFrmPrdSdThreshold
            ACCESS  not-implemented
            DESCRIPTION
                 "Not supported.

                  Not supported."

        VARIATION   tmnxDot3OamErrFrmSdThreshold
            ACCESS  not-implemented
            DESCRIPTION
                 "Not supported.

                  Not supported."

        VARIATION   tmnxDot3OamErrFrmSecEnabled
            ACCESS  not-implemented
            DESCRIPTION
                 "Not supported.

                  Not supported."

        VARIATION   tmnxDot3OamErrFrmSecSdThreshold
            ACCESS  not-implemented
            DESCRIPTION
                 "Not supported.

                  Not supported."

        VARIATION   tmnxDot3OamErrSymPrdEnabled
            ACCESS  not-implemented
            DESCRIPTION
                 "Not supported.

                  Not supported."

        VARIATION   tmnxDot3OamErrSymPrdSdThreshold
            ACCESS  not-implemented
            DESCRIPTION
                 "Not supported.

                  Not supported."

        VARIATION   tmnxDot3OamErrSymPrdWindowTime
            ACCESS  not-implemented
            DESCRIPTION
                 "Not supported.

                  Not supported."

        VARIATION   tmnxDot3OamLinkMonEnabled
            ACCESS  not-implemented
            DESCRIPTION
                 "Not supported.

                  Not supported."

        VARIATION   tmnxDot3OamLocalSfActEventBurst
            ACCESS  not-implemented
            DESCRIPTION
                 "Not supported.

                  Not supported."

        VARIATION   tmnxDot3OamLocalSfActPortAction
            ACCESS  not-implemented
            DESCRIPTION
                 "Not supported.

                  Not supported."

        VARIATION   tmnxDot3OamPrRdiRxCriticalEvent
            ACCESS  not-implemented
            DESCRIPTION
                 "Not supported.

                  Not supported."

        VARIATION   tmnxDot3OamPrRdiRxDyingGasp
            ACCESS  not-implemented
            DESCRIPTION
                 "Not supported.

                  Not supported."

        VARIATION   tmnxDot3OamPrRdiRxEventNotif
            ACCESS  not-implemented
            DESCRIPTION
                 "Not supported.

                  Not supported."

        VARIATION   tmnxDot3OamPrRdiRxLinkFault
            ACCESS  not-implemented
            DESCRIPTION
                 "Not supported.

                  Not supported."

    ::= { tmnxSASAgentV9v0  22 }

--
-- SAS DOT3_OAM CAPABILITIES
--
tmnxSASDot3OamV9v0                AGENT-CAPABILITIES
    PRODUCT-RELEASE "Alcatel-Lucent SAS"
    STATUS          current
    DESCRIPTION
         "Implementation of Ethernet OAM (802.3ah) capabilities for
          Alcatel-Lucent SAS systems release 9.0."

    SUPPORTS        DOT3-OAM-MIB
        INCLUDES {
           dot3OamControlGroup,
           dot3OamEventLogGroup,
           dot3OamLoopbackGroup,
           dot3OamNotificationGroup,
           dot3OamPeerGroup,
           dot3OamStatsBaseGroup
        }

        VARIATION   dot3OamEventLogRunningTotal
            ACCESS  not-implemented
            DESCRIPTION
                 "Not supported.

                  Not supported."

        VARIATION   dot3OamEventLogThresholdHi
            ACCESS  not-implemented
            DESCRIPTION
                 "Not supported.

                  Not supported."

        VARIATION   dot3OamEventLogThresholdLo
            ACCESS  not-implemented
            DESCRIPTION
                 "Not supported.

                  Not supported."

        VARIATION   dot3OamEventLogValue
            ACCESS  not-implemented
            DESCRIPTION
                 "Not supported.

                  Not supported."

        VARIATION   dot3OamEventLogWindowHi
            ACCESS  not-implemented
            DESCRIPTION
                 "Not supported.

                  Not supported."

        VARIATION   dot3OamEventLogWindowLo
            ACCESS  not-implemented
            DESCRIPTION
                 "Not supported.

                  Not supported."

        VARIATION   dot3OamThresholdEvent
            ACCESS  not-implemented
            DESCRIPTION
                 "Not supported.

                  Not supported."

    SUPPORTS        TIMETRA-DOT3-OAM-MIB
        INCLUDES {
           tmnxDot3OamEventConfigEntry,
           tmnxDot3OamLoopbackGroup,
           tmnxDot3OamNotificationV6v0Group,
           tmnxDot3OamV6v0Group,
           tmnxDot3OamV6v1Group
        }

        VARIATION   tmnxDot3OamErrFrmEnabled
            ACCESS  not-implemented
            DESCRIPTION
                 "Not supported.

                  Not supported."

        VARIATION   tmnxDot3OamErrFrmPrdEnabled
            ACCESS  not-implemented
            DESCRIPTION
                 "Not supported.

                  Not supported."

        VARIATION   tmnxDot3OamErrFrmPrdSdThreshold
            ACCESS  not-implemented
            DESCRIPTION
                 "Not supported.

                  Not supported."

        VARIATION   tmnxDot3OamErrFrmSdThreshold
            ACCESS  not-implemented
            DESCRIPTION
                 "Not supported.

                  Not supported."

        VARIATION   tmnxDot3OamErrFrmSecEnabled
            ACCESS  not-implemented
            DESCRIPTION
                 "Not supported.

                  Not supported."

        VARIATION   tmnxDot3OamErrFrmSecSdThreshold
            ACCESS  not-implemented
            DESCRIPTION
                 "Not supported.

                  Not supported."

        VARIATION   tmnxDot3OamErrSymPrdEnabled
            ACCESS  not-implemented
            DESCRIPTION
                 "Not supported.

                  Not supported."

        VARIATION   tmnxDot3OamErrSymPrdSdThreshold
            ACCESS  not-implemented
            DESCRIPTION
                 "Not supported.

                  Not supported."

        VARIATION   tmnxDot3OamErrSymPrdWindowTime
            ACCESS  not-implemented
            DESCRIPTION
                 "Not supported.

                  Not supported."

        VARIATION   tmnxDot3OamLinkMonEnabled
            ACCESS  not-implemented
            DESCRIPTION
                 "Not supported.

                  Not supported."

        VARIATION   tmnxDot3OamLocalSfActEventBurst
            ACCESS  not-implemented
            DESCRIPTION
                 "Not supported.

                  Not supported."

        VARIATION   tmnxDot3OamLocalSfActPortAction
            ACCESS  not-implemented
            DESCRIPTION
                 "Not supported.

                  Not supported."

        VARIATION   tmnxDot3OamPrRdiRxCriticalEvent
            ACCESS  not-implemented
            DESCRIPTION
                 "Not supported.

                  Not supported."

        VARIATION   tmnxDot3OamPrRdiRxDyingGasp
            ACCESS  not-implemented
            DESCRIPTION
                 "Not supported.

                  Not supported."

        VARIATION   tmnxDot3OamPrRdiRxEventNotif
            ACCESS  not-implemented
            DESCRIPTION
                 "Not supported.

                  Not supported."

        VARIATION   tmnxDot3OamPrRdiRxLinkFault
            ACCESS  not-implemented
            DESCRIPTION
                 "Not supported.

                  Not supported."

    ::= { tmnxSASAgentV9v0  22 }

--
-- SASR DOT3_OAM CAPABILITIES
--
tmnxSASRDot3OamV9v0               AGENT-CAPABILITIES
    PRODUCT-RELEASE "Alcatel-Lucent SAS"
    STATUS          current
    DESCRIPTION
         "Implementation of Ethernet OAM (802.3ah) capabilities for
          Alcatel-Lucent SASR systems release 9.0."

    SUPPORTS        DOT3-OAM-MIB
        INCLUDES {
           dot3OamControlGroup,
           dot3OamEventLogGroup,
           dot3OamLoopbackGroup,
           dot3OamNotificationGroup,
           dot3OamPeerGroup,
           dot3OamStatsBaseGroup
        }

        VARIATION   dot3OamEventLogEventTotal
            ACCESS  not-implemented
            DESCRIPTION
                 "Not supported."

        VARIATION   dot3OamEventLogLocation
            ACCESS  not-implemented
            DESCRIPTION
                 "Not supported."

        VARIATION   dot3OamEventLogOui
            ACCESS  not-implemented
            DESCRIPTION
                 "Not supported."

        VARIATION   dot3OamEventLogRunningTotal
            ACCESS  not-implemented
            DESCRIPTION
                 "Not supported."

        VARIATION   dot3OamEventLogThresholdHi
            ACCESS  not-implemented
            DESCRIPTION
                 "Not supported."

        VARIATION   dot3OamEventLogThresholdLo
            ACCESS  not-implemented
            DESCRIPTION
                 "Not supported."

        VARIATION   dot3OamEventLogTimestamp
            ACCESS  not-implemented
            DESCRIPTION
                 "Not supported."

        VARIATION   dot3OamEventLogType
            ACCESS  not-implemented
            DESCRIPTION
                 "Not supported."

        VARIATION   dot3OamEventLogValue
            ACCESS  not-implemented
            DESCRIPTION
                 "Not supported."

        VARIATION   dot3OamEventLogWindowHi
            ACCESS  not-implemented
            DESCRIPTION
                 "Not supported."

        VARIATION   dot3OamEventLogWindowLo
            ACCESS  not-implemented
            DESCRIPTION
                 "Not supported."

        VARIATION   dot3OamThresholdEvent
            ACCESS  not-implemented
            DESCRIPTION
                 "Not supported."

    SUPPORTS        TIMETRA-DOT3-OAM-MIB
        INCLUDES {
           tmnxDot3OamEventConfigEntry,
           tmnxDot3OamLoopbackGroup,
           tmnxDot3OamNotificationV6v0Group,
           tmnxDot3OamV6v0Group,
           tmnxDot3OamV6v1Group
        }

        VARIATION   tmnxDot3OamErrFrmEnabled
            ACCESS  not-implemented
            DESCRIPTION
                 "Not supported."

        VARIATION   tmnxDot3OamErrFrmPrdEnabled
            ACCESS  not-implemented
            DESCRIPTION
                 "Not supported."

        VARIATION   tmnxDot3OamErrFrmPrdSdThreshold
            ACCESS  not-implemented
            DESCRIPTION
                 "Not supported."

        VARIATION   tmnxDot3OamErrFrmSdThreshold
            ACCESS  not-implemented
            DESCRIPTION
                 "Not supported."

        VARIATION   tmnxDot3OamErrFrmSecEnabled
            ACCESS  not-implemented
            DESCRIPTION
                 "Not supported."

        VARIATION   tmnxDot3OamErrFrmSecSdThreshold
            ACCESS  not-implemented
            DESCRIPTION
                 "Not supported."

        VARIATION   tmnxDot3OamErrSymPrdEnabled
            ACCESS  not-implemented
            DESCRIPTION
                 "Not supported."

        VARIATION   tmnxDot3OamErrSymPrdSdThreshold
            ACCESS  not-implemented
            DESCRIPTION
                 "Not supported."

        VARIATION   tmnxDot3OamErrSymPrdWindowTime
            ACCESS  not-implemented
            DESCRIPTION
                 "Not supported."

        VARIATION   tmnxDot3OamLinkMonEnabled
            ACCESS  not-implemented
            DESCRIPTION
                 "Not supported."

        VARIATION   tmnxDot3OamLocalSfActEventBurst
            ACCESS  not-implemented
            DESCRIPTION
                 "Not supported."

        VARIATION   tmnxDot3OamLocalSfActPortAction
            ACCESS  not-implemented
            DESCRIPTION
                 "Not supported."

        VARIATION   tmnxDot3OamPrRdiRxCriticalEvent
            ACCESS  not-implemented
            DESCRIPTION
                 "Not supported."

        VARIATION   tmnxDot3OamPrRdiRxDyingGasp
            ACCESS  not-implemented
            DESCRIPTION
                 "Not supported."

        VARIATION   tmnxDot3OamPrRdiRxEventNotif
            ACCESS  not-implemented
            DESCRIPTION
                 "Not supported."

        VARIATION   tmnxDot3OamPrRdiRxLinkFault
            ACCESS  not-implemented
            DESCRIPTION
                 "Not supported."

    ::= { tmnxSASRAgentV9v0  22 }

--
-- SASX DOT3_OAM CAPABILITIES
--
tmnxSASXDot3OamV9v0               AGENT-CAPABILITIES
    PRODUCT-RELEASE "Alcatel-Lucent SAS"
    STATUS          current
    DESCRIPTION
         "Implementation of Ethernet OAM (802.3ah) capabilities for
          Alcatel-Lucent SASX systems release 9.0."

    SUPPORTS        DOT3-OAM-MIB
        INCLUDES {
           dot3OamControlGroup,
           dot3OamEventLogGroup,
           dot3OamLoopbackGroup,
           dot3OamNotificationGroup,
           dot3OamPeerGroup,
           dot3OamStatsBaseGroup
        }

        VARIATION   dot3OamEventLogEventTotal
            ACCESS  not-implemented
            DESCRIPTION
                 "Not supported."

        VARIATION   dot3OamEventLogLocation
            ACCESS  not-implemented
            DESCRIPTION
                 "Not supported."

        VARIATION   dot3OamEventLogOui
            ACCESS  not-implemented
            DESCRIPTION
                 "Not supported."

        VARIATION   dot3OamEventLogRunningTotal
            ACCESS  not-implemented
            DESCRIPTION
                 "Not supported."

        VARIATION   dot3OamEventLogThresholdHi
            ACCESS  not-implemented
            DESCRIPTION
                 "Not supported."

        VARIATION   dot3OamEventLogThresholdLo
            ACCESS  not-implemented
            DESCRIPTION
                 "Not supported."

        VARIATION   dot3OamEventLogTimestamp
            ACCESS  not-implemented
            DESCRIPTION
                 "Not supported."

        VARIATION   dot3OamEventLogType
            ACCESS  not-implemented
            DESCRIPTION
                 "Not supported."

        VARIATION   dot3OamEventLogValue
            ACCESS  not-implemented
            DESCRIPTION
                 "Not supported."

        VARIATION   dot3OamEventLogWindowHi
            ACCESS  not-implemented
            DESCRIPTION
                 "Not supported."

        VARIATION   dot3OamEventLogWindowLo
            ACCESS  not-implemented
            DESCRIPTION
                 "Not supported."

        VARIATION   dot3OamThresholdEvent
            ACCESS  not-implemented
            DESCRIPTION
                 "Not supported."

    SUPPORTS        TIMETRA-DOT3-OAM-MIB
        INCLUDES {
           tmnxDot3OamEventConfigEntry,
           tmnxDot3OamLoopbackGroup,
           tmnxDot3OamNotificationV6v0Group,
           tmnxDot3OamV6v0Group,
           tmnxDot3OamV6v1Group
        }

        VARIATION   tmnxDot3OamErrFrmEnabled
            ACCESS  not-implemented
            DESCRIPTION
                 "Not supported."

        VARIATION   tmnxDot3OamErrFrmPrdEnabled
            ACCESS  not-implemented
            DESCRIPTION
                 "Not supported."

        VARIATION   tmnxDot3OamErrFrmPrdSdThreshold
            ACCESS  not-implemented
            DESCRIPTION
                 "Not supported."

        VARIATION   tmnxDot3OamErrFrmSdThreshold
            ACCESS  not-implemented
            DESCRIPTION
                 "Not supported."

        VARIATION   tmnxDot3OamErrFrmSecEnabled
            ACCESS  not-implemented
            DESCRIPTION
                 "Not supported."

        VARIATION   tmnxDot3OamErrFrmSecSdThreshold
            ACCESS  not-implemented
            DESCRIPTION
                 "Not supported."

        VARIATION   tmnxDot3OamErrSymPrdEnabled
            ACCESS  not-implemented
            DESCRIPTION
                 "Not supported."

        VARIATION   tmnxDot3OamErrSymPrdSdThreshold
            ACCESS  not-implemented
            DESCRIPTION
                 "Not supported."

        VARIATION   tmnxDot3OamErrSymPrdWindowTime
            ACCESS  not-implemented
            DESCRIPTION
                 "Not supported."

        VARIATION   tmnxDot3OamLinkMonEnabled
            ACCESS  not-implemented
            DESCRIPTION
                 "Not supported."

        VARIATION   tmnxDot3OamLocalSfActEventBurst
            ACCESS  not-implemented
            DESCRIPTION
                 "Not supported."

        VARIATION   tmnxDot3OamLocalSfActPortAction
            ACCESS  not-implemented
            DESCRIPTION
                 "Not supported."

        VARIATION   tmnxDot3OamPrRdiRxCriticalEvent
            ACCESS  not-implemented
            DESCRIPTION
                 "Not supported."

        VARIATION   tmnxDot3OamPrRdiRxDyingGasp
            ACCESS  not-implemented
            DESCRIPTION
                 "Not supported."

        VARIATION   tmnxDot3OamPrRdiRxEventNotif
            ACCESS  not-implemented
            DESCRIPTION
                 "Not supported."

        VARIATION   tmnxDot3OamPrRdiRxLinkFault
            ACCESS  not-implemented
            DESCRIPTION
                 "Not supported."

    ::= { tmnxSASXAgentV9v0  22 }

--
-- SASM DOT3_OAM CAPABILITIES
--
tmnxSASMDot3OamV9v0               AGENT-CAPABILITIES
    PRODUCT-RELEASE "Alcatel-Lucent SAS"
    STATUS          current
    DESCRIPTION
         "Implementation of Ethernet OAM (802.3ah) capabilities for
          Alcatel-Lucent SASM systems release 9.0."

    SUPPORTS        DOT3-OAM-MIB
        INCLUDES {
           dot3OamControlGroup,
           dot3OamEventLogGroup,
           dot3OamLoopbackGroup,
           dot3OamNotificationGroup,
           dot3OamPeerGroup,
           dot3OamStatsBaseGroup
        }

        VARIATION   dot3OamEventLogEventTotal
            ACCESS  not-implemented
            DESCRIPTION
                 "Not supported."

        VARIATION   dot3OamEventLogLocation
            ACCESS  not-implemented
            DESCRIPTION
                 "Not supported."

        VARIATION   dot3OamEventLogOui
            ACCESS  not-implemented
            DESCRIPTION
                 "Not supported."

        VARIATION   dot3OamEventLogRunningTotal
            ACCESS  not-implemented
            DESCRIPTION
                 "Not supported."

        VARIATION   dot3OamEventLogThresholdHi
            ACCESS  not-implemented
            DESCRIPTION
                 "Not supported."

        VARIATION   dot3OamEventLogThresholdLo
            ACCESS  not-implemented
            DESCRIPTION
                 "Not supported."

        VARIATION   dot3OamEventLogTimestamp
            ACCESS  not-implemented
            DESCRIPTION
                 "Not supported."

        VARIATION   dot3OamEventLogType
            ACCESS  not-implemented
            DESCRIPTION
                 "Not supported."

        VARIATION   dot3OamEventLogValue
            ACCESS  not-implemented
            DESCRIPTION
                 "Not supported."

        VARIATION   dot3OamEventLogWindowHi
            ACCESS  not-implemented
            DESCRIPTION
                 "Not supported."

        VARIATION   dot3OamEventLogWindowLo
            ACCESS  not-implemented
            DESCRIPTION
                 "Not supported."

        VARIATION   dot3OamThresholdEvent
            ACCESS  not-implemented
            DESCRIPTION
                 "Not supported."

    SUPPORTS        TIMETRA-DOT3-OAM-MIB
        INCLUDES {
           tmnxDot3OamEventConfigEntry,
           tmnxDot3OamLoopbackGroup,
           tmnxDot3OamNotificationV6v0Group,
           tmnxDot3OamV6v0Group,
           tmnxDot3OamV6v1Group
        }

        VARIATION   tmnxDot3OamErrFrmEnabled
            ACCESS  not-implemented
            DESCRIPTION
                 "Not supported."

        VARIATION   tmnxDot3OamErrFrmPrdEnabled
            ACCESS  not-implemented
            DESCRIPTION
                 "Not supported."

        VARIATION   tmnxDot3OamErrFrmPrdSdThreshold
            ACCESS  not-implemented
            DESCRIPTION
                 "Not supported."

        VARIATION   tmnxDot3OamErrFrmSdThreshold
            ACCESS  not-implemented
            DESCRIPTION
                 "Not supported."

        VARIATION   tmnxDot3OamErrFrmSecEnabled
            ACCESS  not-implemented
            DESCRIPTION
                 "Not supported."

        VARIATION   tmnxDot3OamErrFrmSecSdThreshold
            ACCESS  not-implemented
            DESCRIPTION
                 "Not supported."

        VARIATION   tmnxDot3OamErrSymPrdEnabled
            ACCESS  not-implemented
            DESCRIPTION
                 "Not supported."

        VARIATION   tmnxDot3OamErrSymPrdSdThreshold
            ACCESS  not-implemented
            DESCRIPTION
                 "Not supported."

        VARIATION   tmnxDot3OamErrSymPrdWindowTime
            ACCESS  not-implemented
            DESCRIPTION
                 "Not supported."

        VARIATION   tmnxDot3OamLinkMonEnabled
            ACCESS  not-implemented
            DESCRIPTION
                 "Not supported."

        VARIATION   tmnxDot3OamLocalSfActEventBurst
            ACCESS  not-implemented
            DESCRIPTION
                 "Not supported."

        VARIATION   tmnxDot3OamLocalSfActPortAction
            ACCESS  not-implemented
            DESCRIPTION
                 "Not supported."

        VARIATION   tmnxDot3OamPrRdiRxCriticalEvent
            ACCESS  not-implemented
            DESCRIPTION
                 "Not supported."

        VARIATION   tmnxDot3OamPrRdiRxDyingGasp
            ACCESS  not-implemented
            DESCRIPTION
                 "Not supported."

        VARIATION   tmnxDot3OamPrRdiRxEventNotif
            ACCESS  not-implemented
            DESCRIPTION
                 "Not supported."

        VARIATION   tmnxDot3OamPrRdiRxLinkFault
            ACCESS  not-implemented
            DESCRIPTION
                 "Not supported."

    ::= { tmnxSASMAgentV9v0  22 }

--
-- SASR DS0 CAPABILITIES
--
tmnxSASRDs0V9v0                   AGENT-CAPABILITIES
    PRODUCT-RELEASE "Alcatel-Lucent SAS"
    STATUS          current
    DESCRIPTION
         "Implementation of DS0 Interface Types capabilities for Alcatel-Lucent
          SASR systems release 9.0"

    SUPPORTS        DS0-MIB
        INCLUDES {
           ds0ConfigGroup
        }

        VARIATION   dsx0CircuitIdentifier
            ACCESS  not-implemented
            DESCRIPTION
                 "Not supported."

        VARIATION   dsx0Ds0BundleMappedIfIndex
            ACCESS  not-implemented
            DESCRIPTION
                 "Not supported."

        VARIATION   dsx0IdleCode
            ACCESS  not-implemented
            DESCRIPTION
                 "Not supported."

        VARIATION   dsx0ReceivedCode
            ACCESS  not-implemented
            DESCRIPTION
                 "Not supported."

        VARIATION   dsx0RobbedBitSignalling
            ACCESS  not-implemented
            DESCRIPTION
                 "Not supported."

        VARIATION   dsx0SeizedCode
            ACCESS  not-implemented
            DESCRIPTION
                 "Not supported."

        VARIATION   dsx0TransmitCodesEnable
            ACCESS  not-implemented
            DESCRIPTION
                 "Not supported."

    ::= { tmnxSASRAgentV9v0  26 }

--
-- SASX DS0 CAPABILITIES
--
tmnxSASXDs0V9v0                   AGENT-CAPABILITIES
    PRODUCT-RELEASE "Alcatel-Lucent SAS"
    STATUS          current
    DESCRIPTION
         "Implementation of DS0 Interface Types capabilities for Alcatel-Lucent
          SASX systems release 9.0"

    SUPPORTS        DS0-MIB
        INCLUDES {
           ds0ConfigGroup
        }

        VARIATION   dsx0CircuitIdentifier
            ACCESS  not-implemented
            DESCRIPTION
                 "Not supported."

        VARIATION   dsx0Ds0BundleMappedIfIndex
            ACCESS  not-implemented
            DESCRIPTION
                 "Not supported."

        VARIATION   dsx0IdleCode
            ACCESS  not-implemented
            DESCRIPTION
                 "Not supported."

        VARIATION   dsx0ReceivedCode
            ACCESS  not-implemented
            DESCRIPTION
                 "Not supported."

        VARIATION   dsx0RobbedBitSignalling
            ACCESS  not-implemented
            DESCRIPTION
                 "Not supported."

        VARIATION   dsx0SeizedCode
            ACCESS  not-implemented
            DESCRIPTION
                 "Not supported."

        VARIATION   dsx0TransmitCodesEnable
            ACCESS  not-implemented
            DESCRIPTION
                 "Not supported."

    ::= { tmnxSASXAgentV9v0  26 }

--
-- SASM DS0 CAPABILITIES
--
tmnxSASMDs0V9v0                   AGENT-CAPABILITIES
    PRODUCT-RELEASE "Alcatel-Lucent SAS"
    STATUS          current
    DESCRIPTION
         "Implementation of DS0 Interface Types capabilities for Alcatel-Lucent
          SASM systems release 9.0"

    SUPPORTS        DS0-MIB
        INCLUDES {
           ds0ConfigGroup
        }

        VARIATION   dsx0CircuitIdentifier
            ACCESS  not-implemented
            DESCRIPTION
                 "Not supported."

        VARIATION   dsx0Ds0BundleMappedIfIndex
            ACCESS  not-implemented
            DESCRIPTION
                 "Not supported."

        VARIATION   dsx0IdleCode
            ACCESS  not-implemented
            DESCRIPTION
                 "Not supported."

        VARIATION   dsx0ReceivedCode
            ACCESS  not-implemented
            DESCRIPTION
                 "Not supported."

        VARIATION   dsx0RobbedBitSignalling
            ACCESS  not-implemented
            DESCRIPTION
                 "Not supported."

        VARIATION   dsx0SeizedCode
            ACCESS  not-implemented
            DESCRIPTION
                 "Not supported."

        VARIATION   dsx0TransmitCodesEnable
            ACCESS  not-implemented
            DESCRIPTION
                 "Not supported."

    ::= { tmnxSASMAgentV9v0  26 }

--
-- SASR DS1 CAPABILITIES
--
tmnxSASRDs1V9v0                   AGENT-CAPABILITIES
    PRODUCT-RELEASE "Alcatel-Lucent SAS"
    STATUS          current
    DESCRIPTION
         "Implementation of DS1, E1, DS2 and E2 Interface Types capabilities for
          Alcatel-Lucent SASR systems release 9.0"

    SUPPORTS        DS1-MIB
        INCLUDES {
           ds1ChanMappingGroup,
           ds1NearEndConfigGroup,
           ds1NearEndOptionalConfigGroup,
           ds1NearEndOptionalTrapGroup,
           ds1NearEndStatisticsGroup,
           ds1TransStatsGroup
-- EXCLUDE dsx1FracTable
-- EXCLUDE dsx1IfIndex
-- EXCLUDE dsx1LineBuildOut
-- EXCLUDE dsx1LineMode
        }

    ::= { tmnxSASRAgentV9v0  27 }

--
-- SASM DS1 CAPABILITIES
--
tmnxSASMDs1V9v0                   AGENT-CAPABILITIES
    PRODUCT-RELEASE "Alcatel-Lucent SAS"
    STATUS          current
    DESCRIPTION
         "Implementation of DS1, E1, DS2 and E2 Interface Types capabilities for
          Alcatel-Lucent SASM systems release 9.0"

    SUPPORTS        DS1-MIB
        INCLUDES {
           ds1ChanMappingGroup,
           ds1NearEndConfigGroup,
           ds1NearEndOptionalConfigGroup,
           ds1NearEndOptionalTrapGroup,
           ds1NearEndStatisticsGroup,
           ds1TransStatsGroup
-- EXCLUDE dsx1FracTable
-- EXCLUDE dsx1IfIndex
-- EXCLUDE dsx1LineBuildOut
-- EXCLUDE dsx1LineMode
        }

    ::= { tmnxSASMAgentV9v0  27 }

--
-- SAS ETHER_LIKE CAPABILITIES
--
tmnxSASEtherLikeV9v0              AGENT-CAPABILITIES
    PRODUCT-RELEASE "Alcatel-Lucent SAS"
    STATUS          current
    DESCRIPTION
         "Implementation of Ethernet-like network interfaces capabilities for
          Alcatel-Lucent SAS systems release 9.0"

    SUPPORTS        EtherLike-MIB
        INCLUDES {
-- EXCLUDE dot3CollTable
-- EXCLUDE dot3ControlTable
-- EXCLUDE dot3Errors
-- EXCLUDE dot3HCStatsTable
-- EXCLUDE dot3PauseTable
-- EXCLUDE dot3StatsRateControlAbility
-- EXCLUDE dot3StatsRateControlStatus
-- EXCLUDE dot3Tests
           etherCollisionTableGroup,
           etherDuplexGroup,
           etherStatsBaseGroup2,
           etherStatsHalfDuplexGroup,
           etherStatsHighSpeedGroup,
           etherStatsLowSpeedGroup
        }

        VARIATION   dot3ControlInUnknownOpcodes
            ACCESS  not-implemented
            DESCRIPTION
                 "dot3ControlInUnknownOpcodes is not implemented on
                  Alcatel-Lucent SAS in release 9.0.

                  dot3ControlInUnknownOpcodes is not implemented on
                  Alcatel-Lucent SAS in release 9.0."

        VARIATION   dot3HCControlInUnknownOpcodes
            ACCESS  not-implemented
            DESCRIPTION
                 "dot3HCControlInUnknownOpcodes is not implemented on
                  Alcatel-Lucent SAS in release 9.0.

                  dot3HCControlInUnknownOpcodes is not implemented on
                  Alcatel-Lucent SAS in release 9.0."

        VARIATION   dot3PauseAdminMode
            ACCESS  not-implemented
            DESCRIPTION
                 "dot3PauseAdminMode is not implemented on Alcatel-Lucent SAS in
                  release 9.0.

                  dot3PauseAdminMode is not implemented on Alcatel-Lucent SAS
                  in release 9.0."

        VARIATION   dot3PauseOperMode
            ACCESS  not-implemented
            DESCRIPTION
                 "dot3PauseOperMode is not implemented on Alcatel-Lucent SAS in
                  release 9.0.

                  dot3PauseOperMode is not implemented on Alcatel-Lucent SAS in
                  release 9.0."

    ::= { tmnxSASAgentV9v0   3 }

--
-- SAS ETHER_LIKE CAPABILITIES
--
tmnxSASEtherLikeV9v0              AGENT-CAPABILITIES
    PRODUCT-RELEASE "Alcatel-Lucent SAS"
    STATUS          current
    DESCRIPTION
         "Implementation of Ethernet-like network interfaces capabilities for
          Alcatel-Lucent SAS systems release 9.0"

    SUPPORTS        EtherLike-MIB
        INCLUDES {
-- EXCLUDE dot3CollTable
-- EXCLUDE dot3ControlTable
-- EXCLUDE dot3Errors
-- EXCLUDE dot3HCStatsTable
-- EXCLUDE dot3PauseTable
-- EXCLUDE dot3StatsRateControlAbility
-- EXCLUDE dot3StatsRateControlStatus
-- EXCLUDE dot3Tests
           etherCollisionTableGroup,
           etherDuplexGroup,
           etherStatsBaseGroup2,
           etherStatsHalfDuplexGroup,
           etherStatsHighSpeedGroup,
           etherStatsLowSpeedGroup
        }

        VARIATION   dot3ControlInUnknownOpcodes
            ACCESS  not-implemented
            DESCRIPTION
                 "dot3ControlInUnknownOpcodes is not implemented on
                  Alcatel-Lucent SAS in release 9.0.

                  dot3ControlInUnknownOpcodes is not implemented on
                  Alcatel-Lucent SAS in release 9.0."

        VARIATION   dot3HCControlInUnknownOpcodes
            ACCESS  not-implemented
            DESCRIPTION
                 "dot3HCControlInUnknownOpcodes is not implemented on
                  Alcatel-Lucent SAS in release 9.0.

                  dot3HCControlInUnknownOpcodes is not implemented on
                  Alcatel-Lucent SAS in release 9.0."

        VARIATION   dot3PauseAdminMode
            ACCESS  not-implemented
            DESCRIPTION
                 "dot3PauseAdminMode is not implemented on Alcatel-Lucent SAS in
                  release 9.0.

                  dot3PauseAdminMode is not implemented on Alcatel-Lucent SAS
                  in release 9.0."

        VARIATION   dot3PauseOperMode
            ACCESS  not-implemented
            DESCRIPTION
                 "dot3PauseOperMode is not implemented on Alcatel-Lucent SAS in
                  release 9.0.

                  dot3PauseOperMode is not implemented on Alcatel-Lucent SAS in
                  release 9.0."

    ::= { tmnxSASAgentV9v0   3 }

--
-- SAS IEEE8021_PAE CAPABILITIES
--
tmnxSASIeee8021PaeV9v0            AGENT-CAPABILITIES
    PRODUCT-RELEASE "Alcatel-Lucent SAS"
    STATUS          current
    DESCRIPTION
         "Implementation of IEEE 8021 PAE protocol capabilities for
          Alcatel-Lucent SAS systems release 9.0."

    SUPPORTS        ALCATEL-IEEE8021-PAE-MIB
        INCLUDES {
           alxDot1xAuthConfigGroup,
           alxDot1xRadiusPlcyGroup
        }

    SUPPORTS        IEEE8021-PAE-MIB
        INCLUDES {
           dot1xPaeAuthConfigGroup,
           dot1xPaeAuthDiagGroup,
           dot1xPaeAuthSessionStatsGroup,
           dot1xPaeAuthStatsGroup,
-- EXCLUDE dot1xPaeSuppConfigGroup,
-- EXCLUDE dot1xPaeSuppStatsGroup
           dot1xPaeSystemGroup
        }

        VARIATION   dot1xAuthAdminControlledDirections
            ACCESS  read-only
            DESCRIPTION
                 "read-only support.

                  read-only support."

        VARIATION   dot1xAuthKeyTxEnabled
            SYNTAX  TruthValue
            ACCESS  read-only
            DESCRIPTION
                 "read-only support. The value returned is always false.

                  read-only support. The value returned is always false."

    ::= { tmnxSASAgentV9v0   1 }

--
-- SAS IEEE8021_PAE CAPABILITIES
--
tmnxSASIeee8021PaeV9v0            AGENT-CAPABILITIES
    PRODUCT-RELEASE "Alcatel-Lucent SAS"
    STATUS          current
    DESCRIPTION
         "Implementation of IEEE 8021 PAE protocol capabilities for
          Alcatel-Lucent SAS systems release 9.0."

    SUPPORTS        ALCATEL-IEEE8021-PAE-MIB
        INCLUDES {
           alxDot1xAuthConfigGroup,
           alxDot1xRadiusPlcyGroup
        }

    SUPPORTS        IEEE8021-PAE-MIB
        INCLUDES {
           dot1xPaeAuthConfigGroup,
           dot1xPaeAuthDiagGroup,
           dot1xPaeAuthSessionStatsGroup,
           dot1xPaeAuthStatsGroup,
-- EXCLUDE dot1xPaeSuppConfigGroup,
-- EXCLUDE dot1xPaeSuppStatsGroup
           dot1xPaeSystemGroup
        }

        VARIATION   dot1xAuthAdminControlledDirections
            ACCESS  read-only
            DESCRIPTION
                 "read-only support.

                  read-only support."

        VARIATION   dot1xAuthKeyTxEnabled
            SYNTAX  TruthValue
            ACCESS  read-only
            DESCRIPTION
                 "read-only support. The value returned is always false.

                  read-only support. The value returned is always false."

    ::= { tmnxSASAgentV9v0   1 }

--
-- SASR IGMP CAPABILITIES
--
tmnxSASRIgmpV9v0                  AGENT-CAPABILITIES
    PRODUCT-RELEASE "Alcatel-Lucent SAS"
    STATUS          current
    DESCRIPTION
         "Implementation of IGMP protocol capabilities for Alcatel-Lucent SASR
          systems release 9.0."

    SUPPORTS        TIMETRA-IGMP-MIB
        INCLUDES {
           tmnxIgmpGlobalGroup,
           tmnxIgmpIfV10v0Group,
           tmnxIgmpIfV5v0Group,
           tmnxIgmpIfV6v1Group,
           tmnxIgmpIfV7v0Group,
           tmnxIgmpIfV8v0Group,
           tmnxIgmpIfV9v0Group,
           tmnxIgmpNotificationV10v0Group
        }

        VARIATION   vRtrIgmpGrpIfRowStatus
            ACCESS  not-implemented
            DESCRIPTION
                 "Not supported."

        VARIATION   vRtrIgmpIfMcacAvailMandBw
            ACCESS  not-implemented
            DESCRIPTION
                 "Not supported."

        VARIATION   vRtrIgmpIfMcacAvailOpnlBw
            ACCESS  not-implemented
            DESCRIPTION
                 "Not supported."

        VARIATION   vRtrIgmpIfMcacConstAdminState
            ACCESS  not-implemented
            DESCRIPTION
                 "Not supported."

        VARIATION   vRtrIgmpIfMcacPolicyName
            ACCESS  not-implemented
            DESCRIPTION
                 "Not supported."

        VARIATION   vRtrIgmpIfMcacPreRsvdMandBW
            ACCESS  not-implemented
            DESCRIPTION
                 "Not supported."

        VARIATION   vRtrIgmpIfMcacUnconstrainedBW
            ACCESS  not-implemented
            DESCRIPTION
                 "Not supported."

        VARIATION   vRtrIgmpIfMcacValuesInTransit
            ACCESS  not-implemented
            DESCRIPTION
                 "Not supported."

        VARIATION   vRtrIgmpIfMcacinUseMandBw
            ACCESS  not-implemented
            DESCRIPTION
                 "Not supported."

        VARIATION   vRtrIgmpIfMcacinUseOpnlBw
            ACCESS  not-implemented
            DESCRIPTION
                 "Not supported."

    ::= { tmnxSASRAgentV9v0  34 }

--
-- SASX IGMP CAPABILITIES
--
tmnxSASXIgmpV9v0                  AGENT-CAPABILITIES
    PRODUCT-RELEASE "Alcatel-Lucent SAS"
    STATUS          current
    DESCRIPTION
         "Implementation of IGMP protocol capabilities for Alcatel-Lucent SASX
          systems release 9.0."

    SUPPORTS        TIMETRA-IGMP-MIB
        INCLUDES {
           tmnxIgmpGlobalGroup,
           tmnxIgmpIfV10v0Group,
           tmnxIgmpIfV5v0Group,
           tmnxIgmpIfV6v1Group,
           tmnxIgmpIfV7v0Group,
           tmnxIgmpIfV8v0Group,
           tmnxIgmpIfV9v0Group,
           tmnxIgmpNotificationV10v0Group
        }

        VARIATION   vRtrIgmpGrpIfRowStatus
            ACCESS  not-implemented
            DESCRIPTION
                 "Not supported."

        VARIATION   vRtrIgmpIfMcacAvailMandBw
            ACCESS  not-implemented
            DESCRIPTION
                 "Not supported."

        VARIATION   vRtrIgmpIfMcacAvailOpnlBw
            ACCESS  not-implemented
            DESCRIPTION
                 "Not supported."

        VARIATION   vRtrIgmpIfMcacConstAdminState
            ACCESS  not-implemented
            DESCRIPTION
                 "Not supported."

        VARIATION   vRtrIgmpIfMcacPolicyName
            ACCESS  not-implemented
            DESCRIPTION
                 "Not supported."

        VARIATION   vRtrIgmpIfMcacPreRsvdMandBW
            ACCESS  not-implemented
            DESCRIPTION
                 "Not supported."

        VARIATION   vRtrIgmpIfMcacUnconstrainedBW
            ACCESS  not-implemented
            DESCRIPTION
                 "Not supported."

        VARIATION   vRtrIgmpIfMcacValuesInTransit
            ACCESS  not-implemented
            DESCRIPTION
                 "Not supported."

        VARIATION   vRtrIgmpIfMcacinUseMandBw
            ACCESS  not-implemented
            DESCRIPTION
                 "Not supported."

        VARIATION   vRtrIgmpIfMcacinUseOpnlBw
            ACCESS  not-implemented
            DESCRIPTION
                 "Not supported."

    ::= { tmnxSASXAgentV9v0  34 }

--
-- SASM IGMP CAPABILITIES
--
tmnxSASMIgmpV9v0                  AGENT-CAPABILITIES
    PRODUCT-RELEASE "Alcatel-Lucent SAS"
    STATUS          current
    DESCRIPTION
         "Implementation of IGMP protocol capabilities for Alcatel-Lucent SASM
          systems release 9.0."

    SUPPORTS        TIMETRA-IGMP-MIB
        INCLUDES {
           tmnxIgmpGlobalGroup,
           tmnxIgmpIfV10v0Group,
           tmnxIgmpIfV5v0Group,
           tmnxIgmpIfV6v1Group,
           tmnxIgmpIfV7v0Group,
           tmnxIgmpIfV8v0Group,
           tmnxIgmpIfV9v0Group,
           tmnxIgmpNotificationV10v0Group
        }

        VARIATION   vRtrIgmpGrpIfRowStatus
            ACCESS  not-implemented
            DESCRIPTION
                 "Not supported."

        VARIATION   vRtrIgmpIfMcacAvailMandBw
            ACCESS  not-implemented
            DESCRIPTION
                 "Not supported."

        VARIATION   vRtrIgmpIfMcacAvailOpnlBw
            ACCESS  not-implemented
            DESCRIPTION
                 "Not supported."

        VARIATION   vRtrIgmpIfMcacConstAdminState
            ACCESS  not-implemented
            DESCRIPTION
                 "Not supported."

        VARIATION   vRtrIgmpIfMcacPolicyName
            ACCESS  not-implemented
            DESCRIPTION
                 "Not supported."

        VARIATION   vRtrIgmpIfMcacPreRsvdMandBW
            ACCESS  not-implemented
            DESCRIPTION
                 "Not supported."

        VARIATION   vRtrIgmpIfMcacUnconstrainedBW
            ACCESS  not-implemented
            DESCRIPTION
                 "Not supported."

        VARIATION   vRtrIgmpIfMcacValuesInTransit
            ACCESS  not-implemented
            DESCRIPTION
                 "Not supported."

        VARIATION   vRtrIgmpIfMcacinUseMandBw
            ACCESS  not-implemented
            DESCRIPTION
                 "Not supported."

        VARIATION   vRtrIgmpIfMcacinUseOpnlBw
            ACCESS  not-implemented
            DESCRIPTION
                 "Not supported."

    ::= { tmnxSASMAgentV9v0  34 }

--
-- SAS IGMP_SNOOPING CAPABILITIES
--
tmnxSASIgmpSnoopingV9v0           AGENT-CAPABILITIES
    PRODUCT-RELEASE "Alcatel-Lucent SAS"
    STATUS          current
    DESCRIPTION
         "Implementation of IGMP Snooping capabilities for Alcatel-Lucent SAS
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMcacAvailMandBw
            ACCESS  not-implemented
            DESCRIPTION
                 "Not supported.

                  Not supported."

        VARIATION   sapIgmpSnpgCfgMcacAvailOpnlBw
            ACCESS  not-implemented
            DESCRIPTION
                 "Not supported.

                  Not supported."

        VARIATION   sapIgmpSnpgCfgMcacConstAdmSt
            ACCESS  not-implemented
            DESCRIPTION
                 "Not supported.

                  Not supported."

        VARIATION   sapIgmpSnpgCfgMcacLagLastChangeT
            ACCESS  not-implemented
            DESCRIPTION
                 "Not supported.

                  Not supported."

        VARIATION   sapIgmpSnpgCfgMcacLagLevel
            ACCESS  not-implemented
            DESCRIPTION
                 "Not supported.

                  Not supported."

        VARIATION   sapIgmpSnpgCfgMcacLagRowStat
            ACCESS  not-implemented
            DESCRIPTION
                 "Not supported.

                  Not supported."

        VARIATION   sapIgmpSnpgCfgMcacLevelBW
            ACCESS  not-implemented
            DESCRIPTION
                 "Not supported.

                  Not supported."

        VARIATION   sapIgmpSnpgCfgMcacLevelLastChngT
            ACCESS  not-implemented
            DESCRIPTION
                 "Not supported.

                  Not supported."

        VARIATION   sapIgmpSnpgCfgMcacLevelRowStat
            ACCESS  not-implemented
            DESCRIPTION
                 "Not supported.

                  Not supported."

        VARIATION   sapIgmpSnpgCfgMcacPolicyName
            ACCESS  not-implemented
            DESCRIPTION
                 "Not supported.

                  Not supported."

        VARIATION   sapIgmpSnpgCfgMcacPrRsvMndBW
            ACCESS  not-implemented
            DESCRIPTION
                 "Not supported.

                  Not supported."

        VARIATION   sapIgmpSnpgCfgMcacUnconstBW
            ACCESS  not-implemented
            DESCRIPTION
                 "Not supported.

                  Not supported."

        VARIATION   sapIgmpSnpgCfgMcacValInTrans
            ACCESS  not-implemented
            DESCRIPTION
                 "Not supported.

                  Not supported."

        VARIATION   sapIgmpSnpgCfgMcacinUseMandBw
            ACCESS  not-implemented
            DESCRIPTION
                 "Not supported.

                  Not supported."

        VARIATION   sapIgmpSnpgCfgMcacinUseOpnlBw
            ACCESS  not-implemented
            DESCRIPTION
                 "Not supported.

                  Not supported."

        VARIATION   sapIgmpSnpgMcacPolicyDrops
            ACCESS  not-implemented
            DESCRIPTION
                 "Not supported.

                  Not supported."

        VARIATION   sapIgmpSnpgMcsFailures
            ACCESS  not-implemented
            DESCRIPTION
                 "Not supported.

                  Not supported."

    ::= { tmnxSASAgentV9v0   2 }

--
-- SAS IGMP_SNOOPING CAPABILITIES
--
tmnxSASIgmpSnoopingV9v0           AGENT-CAPABILITIES
    PRODUCT-RELEASE "Alcatel-Lucent SAS"
    STATUS          current
    DESCRIPTION
         "Implementation of IGMP Snooping capabilities for Alcatel-Lucent SAS
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMcacAvailMandBw
            ACCESS  not-implemented
            DESCRIPTION
                 "Not supported.

                  Not supported."

        VARIATION   sapIgmpSnpgCfgMcacAvailOpnlBw
            ACCESS  not-implemented
            DESCRIPTION
                 "Not supported.

                  Not supported."

        VARIATION   sapIgmpSnpgCfgMcacConstAdmSt
            ACCESS  not-implemented
            DESCRIPTION
                 "Not supported.

                  Not supported."

        VARIATION   sapIgmpSnpgCfgMcacLagLastChangeT
            ACCESS  not-implemented
            DESCRIPTION
                 "Not supported.

                  Not supported."

        VARIATION   sapIgmpSnpgCfgMcacLagLevel
            ACCESS  not-implemented
            DESCRIPTION
                 "Not supported.

                  Not supported."

        VARIATION   sapIgmpSnpgCfgMcacLagRowStat
            ACCESS  not-implemented
            DESCRIPTION
                 "Not supported.

                  Not supported."

        VARIATION   sapIgmpSnpgCfgMcacLevelBW
            ACCESS  not-implemented
            DESCRIPTION
                 "Not supported.

                  Not supported."

        VARIATION   sapIgmpSnpgCfgMcacLevelLastChngT
            ACCESS  not-implemented
            DESCRIPTION
                 "Not supported.

                  Not supported."

        VARIATION   sapIgmpSnpgCfgMcacLevelRowStat
            ACCESS  not-implemented
            DESCRIPTION
                 "Not supported.

                  Not supported."

        VARIATION   sapIgmpSnpgCfgMcacPolicyName
            ACCESS  not-implemented
            DESCRIPTION
                 "Not supported.

                  Not supported."

        VARIATION   sapIgmpSnpgCfgMcacPrRsvMndBW
            ACCESS  not-implemented
            DESCRIPTION
                 "Not supported.

                  Not supported."

        VARIATION   sapIgmpSnpgCfgMcacUnconstBW
            ACCESS  not-implemented
            DESCRIPTION
                 "Not supported.

                  Not supported."

        VARIATION   sapIgmpSnpgCfgMcacValInTrans
            ACCESS  not-implemented
            DESCRIPTION
                 "Not supported.

                  Not supported."

        VARIATION   sapIgmpSnpgCfgMcacinUseMandBw
            ACCESS  not-implemented
            DESCRIPTION
                 "Not supported.

                  Not supported."

        VARIATION   sapIgmpSnpgCfgMcacinUseOpnlBw
            ACCESS  not-implemented
            DESCRIPTION
                 "Not supported.

                  Not supported."

        VARIATION   sapIgmpSnpgMcacPolicyDrops
            ACCESS  not-implemented
            DESCRIPTION
                 "Not supported.

                  Not supported."

        VARIATION   sapIgmpSnpgMcsFailures
            ACCESS  not-implemented
            DESCRIPTION
                 "Not supported.

                  Not supported."

    ::= { tmnxSASAgentV9v0   2 }

--
-- SASR IGMP_SNOOPING CAPABILITIES
--
tmnxSASRIgmpSnoopingV9v0          AGENT-CAPABILITIES
    PRODUCT-RELEASE "Alcatel-Lucent SAS"
    STATUS          current
    DESCRIPTION
         "Implementation of IGMP Snooping capabilities for Alcatel-Lucent SASR
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMcacAvailMandBw
            ACCESS  not-implemented
            DESCRIPTION
                 "Not supported."

        VARIATION   sapIgmpSnpgCfgMcacAvailOpnlBw
            ACCESS  not-implemented
            DESCRIPTION
                 "Not supported."

        VARIATION   sapIgmpSnpgCfgMcacConstAdmSt
            ACCESS  not-implemented
            DESCRIPTION
                 "Not supported."

        VARIATION   sapIgmpSnpgCfgMcacLagLastChangeT
            ACCESS  not-implemented
            DESCRIPTION
                 "Not supported."

        VARIATION   sapIgmpSnpgCfgMcacLagLevel
            ACCESS  not-implemented
            DESCRIPTION
                 "Not supported."

        VARIATION   sapIgmpSnpgCfgMcacLagRowStat
            ACCESS  not-implemented
            DESCRIPTION
                 "Not supported."

        VARIATION   sapIgmpSnpgCfgMcacLevelBW
            ACCESS  not-implemented
            DESCRIPTION
                 "Not supported."

        VARIATION   sapIgmpSnpgCfgMcacLevelLastChngT
            ACCESS  not-implemented
            DESCRIPTION
                 "Not supported."

        VARIATION   sapIgmpSnpgCfgMcacLevelRowStat
            ACCESS  not-implemented
            DESCRIPTION
                 "Not supported."

        VARIATION   sapIgmpSnpgCfgMcacPolicyName
            ACCESS  not-implemented
            DESCRIPTION
                 "Not supported."

        VARIATION   sapIgmpSnpgCfgMcacPrRsvMndBW
            ACCESS  not-implemented
            DESCRIPTION
                 "Not supported."

        VARIATION   sapIgmpSnpgCfgMcacUnconstBW
            ACCESS  not-implemented
            DESCRIPTION
                 "Not supported."

        VARIATION   sapIgmpSnpgCfgMcacValInTrans
            ACCESS  not-implemented
            DESCRIPTION
                 "Not supported."

        VARIATION   sapIgmpSnpgCfgMcacinUseMandBw
            ACCESS  not-implemented
            DESCRIPTION
                 "Not supported."

        VARIATION   sapIgmpSnpgCfgMcacinUseOpnlBw
            ACCESS  not-implemented
            DESCRIPTION
                 "Not supported."

        VARIATION   sapIgmpSnpgFwdSrcSpecQueries
            ACCESS  not-implemented
            DESCRIPTION
                 "Not supported."

        VARIATION   sapIgmpSnpgMcacPolicyDrops
            ACCESS  not-implemented
            DESCRIPTION
                 "Not supported."

        VARIATION   sapIgmpSnpgMcsFailures
            ACCESS  not-implemented
            DESCRIPTION
                 "Not supported."

        VARIATION   sapIgmpSnpgRxRsvdScopePkts
            ACCESS  not-implemented
            DESCRIPTION
                 "Not supported."

        VARIATION   sdpBndIgmpSnpgCfgMcacAvailMndBw
            ACCESS  not-implemented
            DESCRIPTION
                 "Not supported."

        VARIATION   sdpBndIgmpSnpgCfgMcacAvailOplBw
            ACCESS  not-implemented
            DESCRIPTION
                 "Not supported."

        VARIATION   sdpBndIgmpSnpgCfgMcacPolicyName
            ACCESS  not-implemented
            DESCRIPTION
                 "Not supported."

        VARIATION   sdpBndIgmpSnpgCfgMcacPrRsvMndBW
            ACCESS  not-implemented
            DESCRIPTION
                 "Not supported."

        VARIATION   sdpBndIgmpSnpgCfgMcacUnconstBW
            ACCESS  not-implemented
            DESCRIPTION
                 "Not supported."

        VARIATION   sdpBndIgmpSnpgCfgMcacValInTrans
            ACCESS  not-implemented
            DESCRIPTION
                 "Not supported."

        VARIATION   sdpBndIgmpSnpgCfgMcacinUseMndBw
            ACCESS  not-implemented
            DESCRIPTION
                 "Not supported."

        VARIATION   sdpBndIgmpSnpgCfgMcacinUseOplBw
            ACCESS  not-implemented
            DESCRIPTION
                 "Not supported."

        VARIATION   sdpBndIgmpSnpgFwdSrcSpecQueries
            ACCESS  not-implemented
            DESCRIPTION
                 "Not supported."

        VARIATION   sdpBndIgmpSnpgFwdV3Reports
            ACCESS  not-implemented
            DESCRIPTION
                 "Not supported."

        VARIATION   sdpBndIgmpSnpgGrpFilterMode
            ACCESS  not-implemented
            DESCRIPTION
                 "Not supported."

        VARIATION   sdpBndIgmpSnpgMcacPolicyDrops
            ACCESS  not-implemented
            DESCRIPTION
                 "Not supported."

        VARIATION   sdpBndIgmpSnpgRxRsvdScopePkts
            ACCESS  not-implemented
            DESCRIPTION
                 "Not supported."

        VARIATION   sdpBndIgmpSnpgRxSrcSpecQueries
            ACCESS  not-implemented
            DESCRIPTION
                 "Not supported."

        VARIATION   sdpBndIgmpSnpgRxV3Reports
            ACCESS  not-implemented
            DESCRIPTION
                 "Not supported."

        VARIATION   sdpBndIgmpSnpgTxSrcSpecQueries
            ACCESS  not-implemented
            DESCRIPTION
                 "Not supported."

        VARIATION   sdpBndIgmpSnpgTxV3Reports
            ACCESS  not-implemented
            DESCRIPTION
                 "Not supported."

    ::= { tmnxSASRAgentV9v0   2 }

--
-- SASX IGMP_SNOOPING CAPABILITIES
--
tmnxSASXIgmpSnoopingV9v0          AGENT-CAPABILITIES
    PRODUCT-RELEASE "Alcatel-Lucent SAS"
    STATUS          current
    DESCRIPTION
         "Implementation of IGMP Snooping capabilities for Alcatel-Lucent SASX
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMaxNbrGrps
            SYNTAX  Integer32 (0..1024)
            DESCRIPTION
                 "sapIgmpSnpgCfgMaxNbrGrps upto 1024 is supported on SASX."

        VARIATION   sapIgmpSnpgCfgMcacAvailMandBw
            ACCESS  not-implemented
            DESCRIPTION
                 "Not supported."

        VARIATION   sapIgmpSnpgCfgMcacAvailOpnlBw
            ACCESS  not-implemented
            DESCRIPTION
                 "Not supported."

        VARIATION   sapIgmpSnpgCfgMcacConstAdmSt
            ACCESS  not-implemented
            DESCRIPTION
                 "Not supported."

        VARIATION   sapIgmpSnpgCfgMcacLagLastChangeT
            ACCESS  not-implemented
            DESCRIPTION
                 "Not supported."

        VARIATION   sapIgmpSnpgCfgMcacLagLevel
            ACCESS  not-implemented
            DESCRIPTION
                 "Not supported."

        VARIATION   sapIgmpSnpgCfgMcacLagRowStat
            ACCESS  not-implemented
            DESCRIPTION
                 "Not supported."

        VARIATION   sapIgmpSnpgCfgMcacLevelBW
            ACCESS  not-implemented
            DESCRIPTION
                 "Not supported."

        VARIATION   sapIgmpSnpgCfgMcacLevelLastChngT
            ACCESS  not-implemented
            DESCRIPTION
                 "Not supported."

        VARIATION   sapIgmpSnpgCfgMcacLevelRowStat
            ACCESS  not-implemented
            DESCRIPTION
                 "Not supported."

        VARIATION   sapIgmpSnpgCfgMcacPolicyName
            ACCESS  not-implemented
            DESCRIPTION
                 "Not supported."

        VARIATION   sapIgmpSnpgCfgMcacPrRsvMndBW
            ACCESS  not-implemented
            DESCRIPTION
                 "Not supported."

        VARIATION   sapIgmpSnpgCfgMcacUnconstBW
            ACCESS  not-implemented
            DESCRIPTION
                 "Not supported."

        VARIATION   sapIgmpSnpgCfgMcacValInTrans
            ACCESS  not-implemented
            DESCRIPTION
                 "Not supported."

        VARIATION   sapIgmpSnpgCfgMcacinUseMandBw
            ACCESS  not-implemented
            DESCRIPTION
                 "Not supported."

        VARIATION   sapIgmpSnpgCfgMcacinUseOpnlBw
            ACCESS  not-implemented
            DESCRIPTION
                 "Not supported."

        VARIATION   sapIgmpSnpgFwdSrcSpecQueries
            ACCESS  not-implemented
            DESCRIPTION
                 "Not supported."

        VARIATION   sapIgmpSnpgFwdV3Reports
            ACCESS  not-implemented
            DESCRIPTION
                 "Not supported."

        VARIATION   sapIgmpSnpgGrpFilterMode
            ACCESS  not-implemented
            DESCRIPTION
                 "Not supported."

        VARIATION   sapIgmpSnpgMcacPolicyDrops
            ACCESS  not-implemented
            DESCRIPTION
                 "Not supported."

        VARIATION   sapIgmpSnpgMcsFailures
            ACCESS  not-implemented
            DESCRIPTION
                 "Not supported."

        VARIATION   sapIgmpSnpgRxRsvdScopePkts
            ACCESS  not-implemented
            DESCRIPTION
                 "Not supported."

        VARIATION   sapIgmpSnpgRxSrcSpecQueries
            ACCESS  not-implemented
            DESCRIPTION
                 "Not supported."

        VARIATION   sapIgmpSnpgRxV3Reports
            ACCESS  not-implemented
            DESCRIPTION
                 "Not supported."

        VARIATION   sapIgmpSnpgTxSrcSpecQueries
            ACCESS  not-implemented
            DESCRIPTION
                 "Not supported."

        VARIATION   sapIgmpSnpgTxV3Reports
            ACCESS  not-implemented
            DESCRIPTION
                 "Not supported."

        VARIATION   sdpBndIgmpSnpgCfgFastLeave
            ACCESS  not-implemented
            DESCRIPTION
                 "Not supported."

        VARIATION   sdpBndIgmpSnpgCfgImportPlcy
            ACCESS  not-implemented
            DESCRIPTION
                 "Not supported."

        VARIATION   sdpBndIgmpSnpgCfgMcacAvailMndBw
            ACCESS  not-implemented
            DESCRIPTION
                 "Not supported."

        VARIATION   sdpBndIgmpSnpgCfgMcacAvailOplBw
            ACCESS  not-implemented
            DESCRIPTION
                 "Not supported."

        VARIATION   sdpBndIgmpSnpgCfgMcacPolicyName
            ACCESS  not-implemented
            DESCRIPTION
                 "Not supported."

        VARIATION   sdpBndIgmpSnpgCfgMcacPrRsvMndBW
            ACCESS  not-implemented
            DESCRIPTION
                 "Not supported."

        VARIATION   sdpBndIgmpSnpgCfgMcacUnconstBW
            ACCESS  not-implemented
            DESCRIPTION
                 "Not supported."

        VARIATION   sdpBndIgmpSnpgCfgMcacValInTrans
            ACCESS  not-implemented
            DESCRIPTION
                 "Not supported."

        VARIATION   sdpBndIgmpSnpgCfgMcacinUseMndBw
            ACCESS  not-implemented
            DESCRIPTION
                 "Not supported."

        VARIATION   sdpBndIgmpSnpgCfgMcacinUseOplBw
            ACCESS  not-implemented
            DESCRIPTION
                 "Not supported."

        VARIATION   sdpBndIgmpSnpgFwdSrcSpecQueries
            ACCESS  not-implemented
            DESCRIPTION
                 "Not supported."

        VARIATION   sdpBndIgmpSnpgFwdV3Reports
            ACCESS  not-implemented
            DESCRIPTION
                 "Not supported."

        VARIATION   sdpBndIgmpSnpgGrpFilterMode
            ACCESS  not-implemented
            DESCRIPTION
                 "Not supported."

        VARIATION   sdpBndIgmpSnpgMcacPolicyDrops
            ACCESS  not-implemented
            DESCRIPTION
                 "Not supported."

        VARIATION   sdpBndIgmpSnpgRxRsvdScopePkts
            ACCESS  not-implemented
            DESCRIPTION
                 "Not supported."

        VARIATION   sdpBndIgmpSnpgRxSrcSpecQueries
            ACCESS  not-implemented
            DESCRIPTION
                 "Not supported."

        VARIATION   sdpBndIgmpSnpgRxV3Reports
            ACCESS  not-implemented
            DESCRIPTION
                 "Not supported."

        VARIATION   sdpBndIgmpSnpgTxSrcSpecQueries
            ACCESS  not-implemented
            DESCRIPTION
                 "Not supported."

        VARIATION   sdpBndIgmpSnpgTxV3Reports
            ACCESS  not-implemented
            DESCRIPTION
                 "Not supported."

    ::= { tmnxSASXAgentV9v0   2 }

--
-- SAST IGMP_SNOOPING CAPABILITIES
--
tmnxSASTIgmpSnoopingV9v0          AGENT-CAPABILITIES
    PRODUCT-RELEASE "Alcatel-Lucent SAS"
    STATUS          current
    DESCRIPTION
         "Implementation of IGMP Snooping capabilities for Alcatel-Lucent SAST
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMaxNbrGrps
            SYNTAX  Integer32 (0..1024)
            DESCRIPTION
                 "sapIgmpSnpgCfgMaxNbrGrps upto 1024 is supported on SASX."

        VARIATION   sapIgmpSnpgCfgMaxNbrSrcs
            SYNTAX  Integer32 (0..1024)
            DESCRIPTION
                 "sapIgmpSnpgCfgMaxNbrSrcs upto 1024 is supported on SAST."

        VARIATION   sapIgmpSnpgCfgMcacAvailMandBw
            ACCESS  not-implemented
            DESCRIPTION
                 "Not supported."

        VARIATION   sapIgmpSnpgCfgMcacAvailOpnlBw
            ACCESS  not-implemented
            DESCRIPTION
                 "Not supported."

        VARIATION   sapIgmpSnpgCfgMcacConstAdmSt
            ACCESS  not-implemented
            DESCRIPTION
                 "Not supported."

        VARIATION   sapIgmpSnpgCfgMcacLagLastChangeT
            ACCESS  not-implemented
            DESCRIPTION
                 "Not supported."

        VARIATION   sapIgmpSnpgCfgMcacLagLevel
            ACCESS  not-implemented
            DESCRIPTION
                 "Not supported."

        VARIATION   sapIgmpSnpgCfgMcacLagRowStat
            ACCESS  not-implemented
            DESCRIPTION
                 "Not supported."

        VARIATION   sapIgmpSnpgCfgMcacLevelBW
            ACCESS  not-implemented
            DESCRIPTION
                 "Not supported."

        VARIATION   sapIgmpSnpgCfgMcacLevelLastChngT
            ACCESS  not-implemented
            DESCRIPTION
                 "Not supported."

        VARIATION   sapIgmpSnpgCfgMcacLevelRowStat
            ACCESS  not-implemented
            DESCRIPTION
                 "Not supported."

        VARIATION   sapIgmpSnpgCfgMcacPolicyName
            ACCESS  not-implemented
            DESCRIPTION
                 "Not supported."

        VARIATION   sapIgmpSnpgCfgMcacPrRsvMndBW
            ACCESS  not-implemented
            DESCRIPTION
                 "Not supported."

        VARIATION   sapIgmpSnpgCfgMcacUnconstBW
            ACCESS  not-implemented
            DESCRIPTION
                 "Not supported."

        VARIATION   sapIgmpSnpgCfgMcacValInTrans
            ACCESS  not-implemented
            DESCRIPTION
                 "Not supported."

        VARIATION   sapIgmpSnpgCfgMcacinUseMandBw
            ACCESS  not-implemented
            DESCRIPTION
                 "Not supported."

        VARIATION   sapIgmpSnpgCfgMcacinUseOpnlBw
            ACCESS  not-implemented
            DESCRIPTION
                 "Not supported."

        VARIATION   sapIgmpSnpgMcacPolicyDrops
            ACCESS  not-implemented
            DESCRIPTION
                 "Not supported."

        VARIATION   sapIgmpSnpgMcsFailures
            ACCESS  not-implemented
            DESCRIPTION
                 "Not supported."

    ::= { tmnxSASTAgentV9v0   2 }

--
-- SASM IGMP_SNOOPING CAPABILITIES
--
tmnxSASMIgmpSnoopingV9v0          AGENT-CAPABILITIES
    PRODUCT-RELEASE "Alcatel-Lucent SAS"
    STATUS          current
    DESCRIPTION
         "Implementation of IGMP Snooping capabilities for Alcatel-Lucent SASM
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMcacAvailMandBw
            ACCESS  not-implemented
            DESCRIPTION
                 "Not supported."

        VARIATION   sapIgmpSnpgCfgMcacAvailOpnlBw
            ACCESS  not-implemented
            DESCRIPTION
                 "Not supported."

        VARIATION   sapIgmpSnpgCfgMcacConstAdmSt
            ACCESS  not-implemented
            DESCRIPTION
                 "Not supported."

        VARIATION   sapIgmpSnpgCfgMcacLagLastChangeT
            ACCESS  not-implemented
            DESCRIPTION
                 "Not supported."

        VARIATION   sapIgmpSnpgCfgMcacLagLevel
            ACCESS  not-implemented
            DESCRIPTION
                 "Not supported."

        VARIATION   sapIgmpSnpgCfgMcacLagRowStat
            ACCESS  not-implemented
            DESCRIPTION
                 "Not supported."

        VARIATION   sapIgmpSnpgCfgMcacLevelBW
            ACCESS  not-implemented
            DESCRIPTION
                 "Not supported."

        VARIATION   sapIgmpSnpgCfgMcacLevelLastChngT
            ACCESS  not-implemented
            DESCRIPTION
                 "Not supported."

        VARIATION   sapIgmpSnpgCfgMcacLevelRowStat
            ACCESS  not-implemented
            DESCRIPTION
                 "Not supported."

        VARIATION   sapIgmpSnpgCfgMcacPolicyName
            ACCESS  not-implemented
            DESCRIPTION
                 "Not supported."

        VARIATION   sapIgmpSnpgCfgMcacPrRsvMndBW
            ACCESS  not-implemented
            DESCRIPTION
                 "Not supported."

        VARIATION   sapIgmpSnpgCfgMcacUnconstBW
            ACCESS  not-implemented
            DESCRIPTION
                 "Not supported."

        VARIATION   sapIgmpSnpgCfgMcacValInTrans
            ACCESS  not-implemented
            DESCRIPTION
                 "Not supported."

        VARIATION   sapIgmpSnpgCfgMcacinUseMandBw
            ACCESS  not-implemented
            DESCRIPTION
                 "Not supported."

        VARIATION   sapIgmpSnpgCfgMcacinUseOpnlBw
            ACCESS  not-implemented
            DESCRIPTION
                 "Not supported."

        VARIATION   sapIgmpSnpgFwdSrcSpecQueries
            ACCESS  not-implemented
            DESCRIPTION
                 "Not supported."

        VARIATION   sapIgmpSnpgMcacPolicyDrops
            ACCESS  not-implemented
            DESCRIPTION
                 "Not supported."

        VARIATION   sapIgmpSnpgMcsFailures
            ACCESS  not-implemented
            DESCRIPTION
                 "Not supported."

        VARIATION   sapIgmpSnpgRxRsvdScopePkts
            ACCESS  not-implemented
            DESCRIPTION
                 "Not supported."

        VARIATION   sdpBndIgmpSnpgCfgMcacAvailMndBw
            ACCESS  not-implemented
            DESCRIPTION
                 "Not supported."

        VARIATION   sdpBndIgmpSnpgCfgMcacAvailOplBw
            ACCESS  not-implemented
            DESCRIPTION
                 "Not supported."

        VARIATION   sdpBndIgmpSnpgCfgMcacPolicyName
            ACCESS  not-implemented
            DESCRIPTION
                 "Not supported."

        VARIATION   sdpBndIgmpSnpgCfgMcacPrRsvMndBW
            ACCESS  not-implemented
            DESCRIPTION
                 "Not supported."

        VARIATION   sdpBndIgmpSnpgCfgMcacUnconstBW
            ACCESS  not-implemented
            DESCRIPTION
                 "Not supported."

        VARIATION   sdpBndIgmpSnpgCfgMcacValInTrans
            ACCESS  not-implemented
            DESCRIPTION
                 "Not supported."

        VARIATION   sdpBndIgmpSnpgCfgMcacinUseMndBw
            ACCESS  not-implemented
            DESCRIPTION
                 "Not supported."

        VARIATION   sdpBndIgmpSnpgCfgMcacinUseOplBw
            ACCESS  not-implemented
            DESCRIPTION
                 "Not supported."

        VARIATION   sdpBndIgmpSnpgFwdSrcSpecQueries
            ACCESS  not-implemented
            DESCRIPTION
                 "Not supported."

        VARIATION   sdpBndIgmpSnpgFwdV3Reports
            ACCESS  not-implemented
            DESCRIPTION
                 "Not supported."

        VARIATION   sdpBndIgmpSnpgGrpFilterMode
            ACCESS  not-implemented
            DESCRIPTION
                 "Not supported."

        VARIATION   sdpBndIgmpSnpgMcacPolicyDrops
            ACCESS  not-implemented
            DESCRIPTION
                 "Not supported."

        VARIATION   sdpBndIgmpSnpgRxRsvdScopePkts
            ACCESS  not-implemented
            DESCRIPTION
                 "Not supported."

        VARIATION   sdpBndIgmpSnpgRxSrcSpecQueries
            ACCESS  not-implemented
            DESCRIPTION
                 "Not supported."

        VARIATION   sdpBndIgmpSnpgRxV3Reports
            ACCESS  not-implemented
            DESCRIPTION
                 "Not supported."

        VARIATION   sdpBndIgmpSnpgTxSrcSpecQueries
            ACCESS  not-implemented
            DESCRIPTION
                 "Not supported."

        VARIATION   sdpBndIgmpSnpgTxV3Reports
            ACCESS  not-implemented
            DESCRIPTION
                 "Not supported."

    ::= { tmnxSASMAgentV9v0   2 }

--
-- SASMxp IGMP_SNOOPING CAPABILITIES
--
tmnxSASMxpIgmpSnoopingV9v0        AGENT-CAPABILITIES
    PRODUCT-RELEASE "Alcatel-Lucent SAS"
    STATUS          current
    DESCRIPTION
         "Implementation of IGMP Snooping capabilities for Alcatel-Lucent SASM
          xp systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMaxNbrGrps
            SYNTAX  Integer32 (0..1024)
            DESCRIPTION
                 "sapIgmpSnpgCfgMaxNbrGrps upto 1024 is supported on SASX."

        VARIATION   sapIgmpSnpgCfgMaxNbrSrcs
            SYNTAX  Integer32 (0..1024)
            DESCRIPTION
                 "sapIgmpSnpgCfgMaxNbrSrcs upto 1024 is supported on SAST."

        VARIATION   sapIgmpSnpgCfgMcacAvailMandBw
            ACCESS  not-implemented
            DESCRIPTION
                 "Not supported."

        VARIATION   sapIgmpSnpgCfgMcacAvailOpnlBw
            ACCESS  not-implemented
            DESCRIPTION
                 "Not supported."

        VARIATION   sapIgmpSnpgCfgMcacConstAdmSt
            ACCESS  not-implemented
            DESCRIPTION
                 "Not supported."

        VARIATION   sapIgmpSnpgCfgMcacLagLastChangeT
            ACCESS  not-implemented
            DESCRIPTION
                 "Not supported."

        VARIATION   sapIgmpSnpgCfgMcacLagLevel
            ACCESS  not-implemented
            DESCRIPTION
                 "Not supported."

        VARIATION   sapIgmpSnpgCfgMcacLagRowStat
            ACCESS  not-implemented
            DESCRIPTION
                 "Not supported."

        VARIATION   sapIgmpSnpgCfgMcacLevelBW
            ACCESS  not-implemented
            DESCRIPTION
                 "Not supported."

        VARIATION   sapIgmpSnpgCfgMcacLevelLastChngT
            ACCESS  not-implemented
            DESCRIPTION
                 "Not supported."

        VARIATION   sapIgmpSnpgCfgMcacLevelRowStat
            ACCESS  not-implemented
            DESCRIPTION
                 "Not supported."

        VARIATION   sapIgmpSnpgCfgMcacPolicyName
            ACCESS  not-implemented
            DESCRIPTION
                 "Not supported."

        VARIATION   sapIgmpSnpgCfgMcacPrRsvMndBW
            ACCESS  not-implemented
            DESCRIPTION
                 "Not supported."

        VARIATION   sapIgmpSnpgCfgMcacUnconstBW
            ACCESS  not-implemented
            DESCRIPTION
                 "Not supported."

        VARIATION   sapIgmpSnpgCfgMcacValInTrans
            ACCESS  not-implemented
            DESCRIPTION
                 "Not supported."

        VARIATION   sapIgmpSnpgCfgMcacinUseMandBw
            ACCESS  not-implemented
            DESCRIPTION
                 "Not supported."

        VARIATION   sapIgmpSnpgCfgMcacinUseOpnlBw
            ACCESS  not-implemented
            DESCRIPTION
                 "Not supported."

        VARIATION   sapIgmpSnpgFwdSrcSpecQueries
            ACCESS  not-implemented
            DESCRIPTION
                 "Not supported."

        VARIATION   sapIgmpSnpgMcacPolicyDrops
            ACCESS  not-implemented
            DESCRIPTION
                 "Not supported."

        VARIATION   sapIgmpSnpgMcsFailures
            ACCESS  not-implemented
            DESCRIPTION
                 "Not supported."

        VARIATION   sapIgmpSnpgRxRsvdScopePkts
            ACCESS  not-implemented
            DESCRIPTION
                 "Not supported."

        VARIATION   sdpBndIgmpSnpgCfgMcacAvailMndBw
            ACCESS  not-implemented
            DESCRIPTION
                 "Not supported."

        VARIATION   sdpBndIgmpSnpgCfgMcacAvailOplBw
            ACCESS  not-implemented
            DESCRIPTION
                 "Not supported."

        VARIATION   sdpBndIgmpSnpgCfgMcacPolicyName
            ACCESS  not-implemented
            DESCRIPTION
                 "Not supported."

        VARIATION   sdpBndIgmpSnpgCfgMcacPrRsvMndBW
            ACCESS  not-implemented
            DESCRIPTION
                 "Not supported."

        VARIATION   sdpBndIgmpSnpgCfgMcacUnconstBW
            ACCESS  not-implemented
            DESCRIPTION
                 "Not supported."

        VARIATION   sdpBndIgmpSnpgCfgMcacValInTrans
            ACCESS  not-implemented
            DESCRIPTION
                 "Not supported."

        VARIATION   sdpBndIgmpSnpgCfgMcacinUseMndBw
            ACCESS  not-implemented
            DESCRIPTION
                 "Not supported."

        VARIATION   sdpBndIgmpSnpgCfgMcacinUseOplBw
            ACCESS  not-implemented
            DESCRIPTION
                 "Not supported."

        VARIATION   sdpBndIgmpSnpgFwdSrcSpecQueries
            ACCESS  not-implemented
            DESCRIPTION
                 "Not supported."

        VARIATION   sdpBndIgmpSnpgFwdV3Reports
            ACCESS  not-implemented
            DESCRIPTION
                 "Not supported."

        VARIATION   sdpBndIgmpSnpgGrpFilterMode
            ACCESS  not-implemented
            DESCRIPTION
                 "Not supported."

        VARIATION   sdpBndIgmpSnpgMcacPolicyDrops
            ACCESS  not-implemented
            DESCRIPTION
                 "Not supported."

        VARIATION   sdpBndIgmpSnpgRxRsvdScopePkts
            ACCESS  not-implemented
            DESCRIPTION
                 "Not supported."

        VARIATION   sdpBndIgmpSnpgRxSrcSpecQueries
            ACCESS  not-implemented
            DESCRIPTION
                 "Not supported."

        VARIATION   sdpBndIgmpSnpgRxV3Reports
            ACCESS  not-implemented
            DESCRIPTION
                 "Not supported."

        VARIATION   sdpBndIgmpSnpgTxSrcSpecQueries
            ACCESS  not-implemented
            DESCRIPTION
                 "Not supported."

        VARIATION   sdpBndIgmpSnpgTxV3Reports
            ACCESS  not-implemented
            DESCRIPTION
                 "Not supported."

    ::= { tmnxSASMxpAgentV9v0   2 }

--
-- SASSx IGMP_SNOOPING CAPABILITIES
--
tmnxSASSxIgmpSnoopingV9v0         AGENT-CAPABILITIES
    PRODUCT-RELEASE "Alcatel-Lucent SAS"
    STATUS          current
    DESCRIPTION
         "Implementation of IGMP Snooping capabilities for Alcatel-Lucent SASS x
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
           alxSapMvrV3v0Group,
           alxSdpBindIgmpSnpgConfV5v0Group,
           alxSdpBindIgmpSnpgNotV5v0Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMaxNbrGrps
            SYNTAX  Integer32 (0..1024)
            DESCRIPTION
                 "sapIgmpSnpgCfgMaxNbrGrps upto 1024 is supported on SASX."

        VARIATION   sapIgmpSnpgCfgMaxNbrSrcs
            SYNTAX  Integer32 (0..1024)
            DESCRIPTION
                 "sapIgmpSnpgCfgMaxNbrSrcs upto 1024 is supported on SAST."

        VARIATION   sapIgmpSnpgCfgMcacAvailMandBw
            ACCESS  not-implemented
            DESCRIPTION
                 "Not supported."

        VARIATION   sapIgmpSnpgCfgMcacAvailOpnlBw
            ACCESS  not-implemented
            DESCRIPTION
                 "Not supported."

        VARIATION   sapIgmpSnpgCfgMcacConstAdmSt
            ACCESS  not-implemented
            DESCRIPTION
                 "Not supported."

        VARIATION   sapIgmpSnpgCfgMcacLagLastChangeT
            ACCESS  not-implemented
            DESCRIPTION
                 "Not supported."

        VARIATION   sapIgmpSnpgCfgMcacLagLevel
            ACCESS  not-implemented
            DESCRIPTION
                 "Not supported."

        VARIATION   sapIgmpSnpgCfgMcacLagRowStat
            ACCESS  not-implemented
            DESCRIPTION
                 "Not supported."

        VARIATION   sapIgmpSnpgCfgMcacLevelBW
            ACCESS  not-implemented
            DESCRIPTION
                 "Not supported."

        VARIATION   sapIgmpSnpgCfgMcacLevelLastChngT
            ACCESS  not-implemented
            DESCRIPTION
                 "Not supported."

        VARIATION   sapIgmpSnpgCfgMcacLevelRowStat
            ACCESS  not-implemented
            DESCRIPTION
                 "Not supported."

        VARIATION   sapIgmpSnpgCfgMcacPolicyName
            ACCESS  not-implemented
            DESCRIPTION
                 "Not supported."

        VARIATION   sapIgmpSnpgCfgMcacPrRsvMndBW
            ACCESS  not-implemented
            DESCRIPTION
                 "Not supported."

        VARIATION   sapIgmpSnpgCfgMcacUnconstBW
            ACCESS  not-implemented
            DESCRIPTION
                 "Not supported."

        VARIATION   sapIgmpSnpgCfgMcacValInTrans
            ACCESS  not-implemented
            DESCRIPTION
                 "Not supported."

        VARIATION   sapIgmpSnpgCfgMcacinUseMandBw
            ACCESS  not-implemented
            DESCRIPTION
                 "Not supported."

        VARIATION   sapIgmpSnpgCfgMcacinUseOpnlBw
            ACCESS  not-implemented
            DESCRIPTION
                 "Not supported."

        VARIATION   sapIgmpSnpgMcacPolicyDrops
            ACCESS  not-implemented
            DESCRIPTION
                 "Not supported."

        VARIATION   sapIgmpSnpgMcsFailures
            ACCESS  not-implemented
            DESCRIPTION
                 "Not supported."

    ::= { tmnxSASSxAgentV9v0   2 }

--
-- SASK IGMP_SNOOPING CAPABILITIES
--
tmnxSASKIgmpSnoopingV9v0          AGENT-CAPABILITIES
    PRODUCT-RELEASE "Alcatel-Lucent SAS"
    STATUS          current
    DESCRIPTION
         "Implementation of IGMP Snooping capabilities for Alcatel-Lucent SASK
          systems release 9.0."

    SUPPORTS        ALCATEL-IGMP-SNOOPING-MIB
        INCLUDES {
           alxSapIgmpSnpgConfigV5v0Group,
           alxSapIgmpSnpgGroupV3v0,
           alxSapIgmpSnpgNotV5v0Group,
           alxSapIgmpSnpgStaticV3v0Group,
           alxSapIgmpSnpgStatsV6v0Group,
           alxSapIgmpSnpgTimeStampGroup,
-- EXCLUDE alxSapMvrV3v0Group
-- EXCLUDE alxSdpBindIgmpSnpgConfV5v0Group
-- EXCLUDE alxSdpBindIgmpSnpgNotV5v0Group
-- EXCLUDE alxSdpBindIgmpSnpgStatV3v0Group
-- EXCLUDE alxSdpBindIgmpSnpgStatsV6v0Grp
-- EXCLUDE alxSdpBindIgmpSnpgTimeStampGroup
-- EXCLUDE alxSdpBindIgmpSnpgV3v0Group
           alxTlsIgmpSnpgConfigV6v0Group,
           alxTlsIgmpSnpgMRouterV3v0Group,
           alxTlsIgmpSnpgProxyV3v0Group,
           alxTlsIgmpSnpgQuerierV3v0Group,
           alxTlsIgmpSnpgTimeStampGroup
-- EXCLUDE alxTlsMvrConfigV3v0Group,
        }

        VARIATION   sapIgmpSnpgCfgMaxNbrGrps
            SYNTAX  Integer32 (0..1024)
            DESCRIPTION
                 "sapIgmpSnpgCfgMaxNbrGrps upto 1024 is supported on SASX."

        VARIATION   sapIgmpSnpgCfgMaxNbrSrcs
            SYNTAX  Integer32 (0..1024)
            DESCRIPTION
                 "sapIgmpSnpgCfgMaxNbrSrcs upto 1024 is supported on SAST."

        VARIATION   sapIgmpSnpgCfgMcacAvailMandBw
            ACCESS  not-implemented
            DESCRIPTION
                 "Not supported."

        VARIATION   sapIgmpSnpgCfgMcacAvailOpnlBw
            ACCESS  not-implemented
            DESCRIPTION
                 "Not supported."

        VARIATION   sapIgmpSnpgCfgMcacConstAdmSt
            ACCESS  not-implemented
            DESCRIPTION
                 "Not supported."

        VARIATION   sapIgmpSnpgCfgMcacLagLastChangeT
            ACCESS  not-implemented
            DESCRIPTION
                 "Not supported."

        VARIATION   sapIgmpSnpgCfgMcacLagLevel
            ACCESS  not-implemented
            DESCRIPTION
                 "Not supported."

        VARIATION   sapIgmpSnpgCfgMcacLagRowStat
            ACCESS  not-implemented
            DESCRIPTION
                 "Not supported."

        VARIATION   sapIgmpSnpgCfgMcacLevelBW
            ACCESS  not-implemented
            DESCRIPTION
                 "Not supported."

        VARIATION   sapIgmpSnpgCfgMcacLevelLastChngT
            ACCESS  not-implemented
            DESCRIPTION
                 "Not supported."

        VARIATION   sapIgmpSnpgCfgMcacLevelRowStat
            ACCESS  not-implemented
            DESCRIPTION
                 "Not supported."

        VARIATION   sapIgmpSnpgCfgMcacPolicyName
            ACCESS  not-implemented
            DESCRIPTION
                 "Not supported."

        VARIATION   sapIgmpSnpgCfgMcacPrRsvMndBW
            ACCESS  not-implemented
            DESCRIPTION
                 "Not supported."

        VARIATION   sapIgmpSnpgCfgMcacUnconstBW
            ACCESS  not-implemented
            DESCRIPTION
                 "Not supported."

        VARIATION   sapIgmpSnpgCfgMcacValInTrans
            ACCESS  not-implemented
            DESCRIPTION
                 "Not supported."

        VARIATION   sapIgmpSnpgCfgMcacinUseMandBw
            ACCESS  not-implemented
            DESCRIPTION
                 "Not supported."

        VARIATION   sapIgmpSnpgCfgMcacinUseOpnlBw
            ACCESS  not-implemented
            DESCRIPTION
                 "Not supported."

        VARIATION   sapIgmpSnpgMcacPolicyDrops
            ACCESS  not-implemented
            DESCRIPTION
                 "Not supported."

        VARIATION   sapIgmpSnpgMcsFailures
            ACCESS  not-implemented
            DESCRIPTION
                 "Not supported."

        VARIATION   tlsIgmpSnpgMRouterSdpId
            ACCESS  not-implemented
            DESCRIPTION
                 "Not supported."

        VARIATION   tlsIgmpSnpgMRouterVcId
            ACCESS  not-implemented
            DESCRIPTION
                 "Not supported."

        VARIATION   tlsIgmpSnpgQuerierSdpId
            ACCESS  not-implemented
            DESCRIPTION
                 "Not supported."

        VARIATION   tlsIgmpSnpgQuerierVcId
            ACCESS  not-implemented
            DESCRIPTION
                 "Not supported."

    ::= { tmnxSASKAgentV9v0   2 }

--
-- SAS INTERFACE CAPABILITIES
--
tmnxSASInterfaceV9v0              AGENT-CAPABILITIES
    PRODUCT-RELEASE "Alcatel-Lucent SAS"
    STATUS          current
    DESCRIPTION
         "Implementation of Interface capabilities for Alcatel-Lucent SAS
          systems release 9.0."

    SUPPORTS        IF-INVERTED-STACK-MIB
        INCLUDES {
           ifInvStackGroup
        }

    SUPPORTS        IF-MIB
        INCLUDES {
           ifCounterDiscontinuityGroup,
           ifGeneralInformationGroup,
           ifHCPacketGroup,
           ifPacketGroup,
           ifStackGroup2,
           ifVHCPacketGroup,
           linkUpDownNotificationsGroup
        }

        VARIATION   ifAdminStatus
            SYNTAX  INTEGER {
                       up                   (1), -- ready to pass packets
                       down                 (2)
                    }
            DESCRIPTION
                 "Write access using value 'testing (3)' is not supported.

                  Write access using value 'testing (3)' is not supported."

        VARIATION   ifAlias
            ACCESS  read-only
            DESCRIPTION
                 "read-only implementation.

                  read-only implementation."

        VARIATION   ifLinkUpDownTrapEnable
            ACCESS  read-only
            DESCRIPTION
                 "read-only implementation.

                  read-only implementation."

        VARIATION   ifPromiscuousMode
            ACCESS  read-only
            DESCRIPTION
                 "read-only implementation.

                  read-only implementation."

        VARIATION   ifStackStatus
            ACCESS  read-only
            DESCRIPTION
                 "read-only implementation.

                  read-only implementation."

        VARIATION   linkDown
            DESCRIPTION
                 "The linkDown notification has ifDescr appended to the variable
                  list.

                  The linkDown notification has ifDescr appended to the
                  variable list."

        VARIATION   linkUp
            DESCRIPTION
                 "The linkUp trap has ifDescr appended to the variable list.

                  The linkUp trap has ifDescr appended to the variable list."

    ::= { tmnxSASAgentV9v0   6 }

--
-- SAS INTERFACE CAPABILITIES
--
tmnxSASInterfaceV9v0              AGENT-CAPABILITIES
    PRODUCT-RELEASE "Alcatel-Lucent SAS"
    STATUS          current
    DESCRIPTION
         "Implementation of Interface capabilities for Alcatel-Lucent SAS
          systems release 9.0."

    SUPPORTS        IF-INVERTED-STACK-MIB
        INCLUDES {
           ifInvStackGroup
        }

    SUPPORTS        IF-MIB
        INCLUDES {
           ifCounterDiscontinuityGroup,
           ifGeneralInformationGroup,
           ifHCPacketGroup,
           ifPacketGroup,
           ifStackGroup2,
           ifVHCPacketGroup,
           linkUpDownNotificationsGroup
        }

        VARIATION   ifAdminStatus
            SYNTAX  INTEGER {
                       up                   (1), -- ready to pass packets
                       down                 (2)
                    }
            DESCRIPTION
                 "Write access using value 'testing (3)' is not supported.

                  Write access using value 'testing (3)' is not supported."

        VARIATION   ifAlias
            ACCESS  read-only
            DESCRIPTION
                 "read-only implementation.

                  read-only implementation."

        VARIATION   ifLinkUpDownTrapEnable
            ACCESS  read-only
            DESCRIPTION
                 "read-only implementation.

                  read-only implementation."

        VARIATION   ifPromiscuousMode
            ACCESS  read-only
            DESCRIPTION
                 "read-only implementation.

                  read-only implementation."

        VARIATION   ifStackStatus
            ACCESS  read-only
            DESCRIPTION
                 "read-only implementation.

                  read-only implementation."

        VARIATION   linkDown
            DESCRIPTION
                 "The linkDown notification has ifDescr appended to the variable
                  list.

                  The linkDown notification has ifDescr appended to the
                  variable list."

        VARIATION   linkUp
            DESCRIPTION
                 "The linkUp trap has ifDescr appended to the variable list.

                  The linkUp trap has ifDescr appended to the variable list."

    ::= { tmnxSASAgentV9v0   6 }

--
-- SAS IP CAPABILITIES
--
tmnxSASIpV9v0                     AGENT-CAPABILITIES
    PRODUCT-RELEASE "Alcatel-Lucent SAS"
    STATUS          current
    DESCRIPTION
         "Implementation of Internet Protocol, IP, capabilities for
          Alcatel-Lucent SAS systems release 9.0."

    SUPPORTS        IP-FORWARD-MIB
        INCLUDES {
-- EXCLUDE inetCidrRouteDiscards
-- EXCLUDE inetCidrRouteNumber
           inetForwardCidrRouteGroup,
           ipForwardCidrRouteGroup
-- EXCLUDE ipForwardNumber
-- EXCLUDE ipForwardTable
        }

        VARIATION   inetCidrRouteDestType
            DESCRIPTION
                 "inetCidrRouteDestType can only be ipv4 on SAS-X 7210.

                  inetCidrRouteDestType can only be ipv4 on SAS-X 7210."

        VARIATION   inetCidrRouteDiscards
            ACCESS  not-implemented
            DESCRIPTION
                 "Not supported.

                  Not supported."

        VARIATION   inetCidrRouteIfIndex
            ACCESS  read-only
            DESCRIPTION
                 "read-only implementation.

                  read-only implementation."

        VARIATION   inetCidrRouteMetric1
            ACCESS  read-only
            DESCRIPTION
                 "read-only implementation.

                  read-only implementation."

        VARIATION   inetCidrRouteMetric2
            ACCESS  read-only
            DESCRIPTION
                 "read-only implementation.

                  read-only implementation."

        VARIATION   inetCidrRouteMetric3
            ACCESS  read-only
            DESCRIPTION
                 "read-only implementation.

                  read-only implementation."

        VARIATION   inetCidrRouteMetric4
            ACCESS  read-only
            DESCRIPTION
                 "read-only implementation.

                  read-only implementation."

        VARIATION   inetCidrRouteMetric5
            ACCESS  read-only
            DESCRIPTION
                 "read-only implementation.

                  read-only implementation."

        VARIATION   inetCidrRouteNextHopAS
            ACCESS  read-only
            DESCRIPTION
                 "read-only implementation.

                  read-only implementation."

        VARIATION   inetCidrRouteNextHopType
            DESCRIPTION
                 "inetCidrRouteNextHopType can only be ipv4 on SAS-X 7210.

                  inetCidrRouteNextHopType can only be ipv4 on SAS-X 7210."

        VARIATION   inetCidrRouteNumber
            ACCESS  not-implemented
            DESCRIPTION
                 "Not supported.

                  Not supported."

        VARIATION   inetCidrRouteStatus
            ACCESS  read-only
            DESCRIPTION
                 "read-only implementation.

                  read-only implementation."

        VARIATION   inetCidrRouteType
            ACCESS  read-only
            DESCRIPTION
                 "read-only implementation.

                  read-only implementation."

        VARIATION   ipCidrRouteIfIndex
            ACCESS  read-only
            DESCRIPTION
                 "read-only implementation.

                  read-only implementation."

        VARIATION   ipCidrRouteInfo
            ACCESS  read-only
            DESCRIPTION
                 "read-only implementation.

                  read-only implementation."

        VARIATION   ipCidrRouteMetric1
            ACCESS  read-only
            DESCRIPTION
                 "read-only implementation.

                  read-only implementation."

        VARIATION   ipCidrRouteMetric2
            ACCESS  read-only
            DESCRIPTION
                 "read-only implementation.

                  read-only implementation."

        VARIATION   ipCidrRouteMetric3
            ACCESS  read-only
            DESCRIPTION
                 "read-only implementation.

                  read-only implementation."

        VARIATION   ipCidrRouteMetric4
            ACCESS  read-only
            DESCRIPTION
                 "read-only implementation.

                  read-only implementation."

        VARIATION   ipCidrRouteMetric5
            ACCESS  read-only
            DESCRIPTION
                 "read-only implementation.

                  read-only implementation."

        VARIATION   ipCidrRouteNextHopAS
            ACCESS  read-only
            DESCRIPTION
                 "read-only implementation.

                  read-only implementation."

        VARIATION   ipCidrRouteStatus
            ACCESS  read-only
            DESCRIPTION
                 "read-only implementation.

                  read-only implementation."

        VARIATION   ipCidrRouteType
            ACCESS  read-only
            DESCRIPTION
                 "read-only implementation.

                  read-only implementation."

    SUPPORTS        IP-MIB
        INCLUDES {
           icmpGroup,
-- EXCLUDE icmpMsgStatsTable
-- EXCLUDE icmpStatsTable
-- EXCLUDE ipAddressGroup
-- EXCLUDE ipAddressPrefixGroup
-- EXCLUDE ipAddressSpinLock
-- EXCLUDE ipDefaultRouterTable
           ipGroup,
-- EXCLUDE ipLastChangeGroup
           ipNetToPhysicalGroup,
-- EXCLUDE ipTrafficStats
-- EXCLUDE ipv4InterfaceTable
-- EXCLUDE ipv6GeneralGroup2
-- EXCLUDE ipv6InterfaceTable
           ipv6RouterAdvertGroup
-- EXCLUDE ipv6RouterAdvertSpinLock
-- EXCLUDE ipv6ScopeZoneIndexTable
        }

        VARIATION   ipDefaultTTL
            ACCESS  read-only
            DESCRIPTION
                 "ipDefaultTTL is read-only on SAS-X 7210. It always returns the
                  value '64'.

                  ipDefaultTTL is read-only on SAS-X 7210. It always returns
                  the value '64'."

        VARIATION   ipForwarding
            ACCESS  read-only
            DESCRIPTION
                 "ipForwarding is read-only on SAS-X 7210. It always returns the
                  value 'forwarding (1)'.

                  ipForwarding is read-only on SAS-X 7210. It always returns
                  the value 'forwarding (1)'."

        VARIATION   ipNetToMediaType
            SYNTAX  INTEGER {
                       other                (1), -- none of the following
                       invalid              (2), -- an invalidated mapping
                       dynamic              (3),
                       static               (4),
                       managed              (5) -- added for 7x50
                    }
            DESCRIPTION
                 "The value 'managed (5)' is used to indicate that the ARP entry
                  has been added by:

                  - a static host; or - by a DHCP lease state if
                  TIMETRA-VRTR-MIB::vRtrIfArpPopulate is set to enabled.

                  An attempt to explicitly set the value of ipNetToMediaType to
                  'managed' results in an 'inconsistentValue' error.

                  The value 'managed (5)' is used to indicate that the ARP
                  entry has been added by:

                  - a static host; or - by a DHCP lease state if
                  TIMETRA-VRTR-MIB::vRtrIfArpPopulate is set to enabled.

                  An attempt to explicitly set the value of ipNetToMediaType to
                  'managed' results in an 'inconsistentValue' error."

        VARIATION   ipNetToPhysicalType
            SYNTAX  INTEGER {
                       other                (1), -- none of the following
                       invalid              (2), -- an invalidated mapping
                       dynamic              (3),
                       static               (4),
                       local                (5), -- local interface
                       managed              (100) -- added for 7x50
                    }
            DESCRIPTION
                 "The value 'managed (100)' is used to indicate that the ARP
                  entry has been added by:

                  - a static host; or - by a DHCP lease state if
                  TIMETRA-VRTR-MIB::vRtrIfArpPopulate is set to enabled.

                  An attempt to explicitly set the value of ipNetToPhysicalType
                  to 'managed' results in an 'inconsistentValue' error.

                  The value 'managed (100)' is used to indicate that the ARP
                  entry has been added by:

                  - a static host; or - by a DHCP lease state if
                  TIMETRA-VRTR-MIB::vRtrIfArpPopulate is set to enabled.

                  An attempt to explicitly set the value of ipNetToPhysicalType
                  to 'managed' results in an 'inconsistentValue' error."

        VARIATION   ipv6RouterAdvertSpinLock
            ACCESS  not-implemented
            DESCRIPTION
                 "Not supported.

                  Not supported."

    SUPPORTS        TCP-MIB
        INCLUDES {
           tcpBaseGroup,
           tcpConnectionGroup,
-- EXCLUDE tcpHCGroup
           tcpListenerGroup
        }

        VARIATION   tcpConnectionState
            ACCESS  read-only
            DESCRIPTION
                 "read-only implementation.

                  read-only implementation."

    SUPPORTS        UDP-MIB
        INCLUDES {
           udpEndpointGroup,
           udpGroup
-- EXCLUDE udpHCGroup
        }

    ::= { tmnxSASAgentV9v0   7 }

--
-- SAS IP CAPABILITIES
--
tmnxSASIpV9v0                     AGENT-CAPABILITIES
    PRODUCT-RELEASE "Alcatel-Lucent SAS"
    STATUS          current
    DESCRIPTION
         "Implementation of Internet Protocol, IP, capabilities for
          Alcatel-Lucent SAS systems release 9.0."

    SUPPORTS        IP-FORWARD-MIB
        INCLUDES {
-- EXCLUDE inetCidrRouteDiscards
-- EXCLUDE inetCidrRouteNumber
           inetForwardCidrRouteGroup,
           ipForwardCidrRouteGroup
-- EXCLUDE ipForwardNumber
-- EXCLUDE ipForwardTable
        }

        VARIATION   inetCidrRouteDestType
            DESCRIPTION
                 "inetCidrRouteDestType can only be ipv4 on SAS-X 7210.

                  inetCidrRouteDestType can only be ipv4 on SAS-X 7210."

        VARIATION   inetCidrRouteDiscards
            ACCESS  not-implemented
            DESCRIPTION
                 "Not supported.

                  Not supported."

        VARIATION   inetCidrRouteIfIndex
            ACCESS  read-only
            DESCRIPTION
                 "read-only implementation.

                  read-only implementation."

        VARIATION   inetCidrRouteMetric1
            ACCESS  read-only
            DESCRIPTION
                 "read-only implementation.

                  read-only implementation."

        VARIATION   inetCidrRouteMetric2
            ACCESS  read-only
            DESCRIPTION
                 "read-only implementation.

                  read-only implementation."

        VARIATION   inetCidrRouteMetric3
            ACCESS  read-only
            DESCRIPTION
                 "read-only implementation.

                  read-only implementation."

        VARIATION   inetCidrRouteMetric4
            ACCESS  read-only
            DESCRIPTION
                 "read-only implementation.

                  read-only implementation."

        VARIATION   inetCidrRouteMetric5
            ACCESS  read-only
            DESCRIPTION
                 "read-only implementation.

                  read-only implementation."

        VARIATION   inetCidrRouteNextHopAS
            ACCESS  read-only
            DESCRIPTION
                 "read-only implementation.

                  read-only implementation."

        VARIATION   inetCidrRouteNextHopType
            DESCRIPTION
                 "inetCidrRouteNextHopType can only be ipv4 on SAS-X 7210.

                  inetCidrRouteNextHopType can only be ipv4 on SAS-X 7210."

        VARIATION   inetCidrRouteNumber
            ACCESS  not-implemented
            DESCRIPTION
                 "Not supported.

                  Not supported."

        VARIATION   inetCidrRouteStatus
            ACCESS  read-only
            DESCRIPTION
                 "read-only implementation.

                  read-only implementation."

        VARIATION   inetCidrRouteType
            ACCESS  read-only
            DESCRIPTION
                 "read-only implementation.

                  read-only implementation."

        VARIATION   ipCidrRouteIfIndex
            ACCESS  read-only
            DESCRIPTION
                 "read-only implementation.

                  read-only implementation."

        VARIATION   ipCidrRouteInfo
            ACCESS  read-only
            DESCRIPTION
                 "read-only implementation.

                  read-only implementation."

        VARIATION   ipCidrRouteMetric1
            ACCESS  read-only
            DESCRIPTION
                 "read-only implementation.

                  read-only implementation."

        VARIATION   ipCidrRouteMetric2
            ACCESS  read-only
            DESCRIPTION
                 "read-only implementation.

                  read-only implementation."

        VARIATION   ipCidrRouteMetric3
            ACCESS  read-only
            DESCRIPTION
                 "read-only implementation.

                  read-only implementation."

        VARIATION   ipCidrRouteMetric4
            ACCESS  read-only
            DESCRIPTION
                 "read-only implementation.

                  read-only implementation."

        VARIATION   ipCidrRouteMetric5
            ACCESS  read-only
            DESCRIPTION
                 "read-only implementation.

                  read-only implementation."

        VARIATION   ipCidrRouteNextHopAS
            ACCESS  read-only
            DESCRIPTION
                 "read-only implementation.

                  read-only implementation."

        VARIATION   ipCidrRouteStatus
            ACCESS  read-only
            DESCRIPTION
                 "read-only implementation.

                  read-only implementation."

        VARIATION   ipCidrRouteType
            ACCESS  read-only
            DESCRIPTION
                 "read-only implementation.

                  read-only implementation."

    SUPPORTS        IP-MIB
        INCLUDES {
           icmpGroup,
-- EXCLUDE icmpMsgStatsTable
-- EXCLUDE icmpStatsTable
-- EXCLUDE ipAddressGroup
-- EXCLUDE ipAddressPrefixGroup
-- EXCLUDE ipAddressSpinLock
-- EXCLUDE ipDefaultRouterTable
           ipGroup,
-- EXCLUDE ipLastChangeGroup
           ipNetToPhysicalGroup,
-- EXCLUDE ipTrafficStats
-- EXCLUDE ipv4InterfaceTable
-- EXCLUDE ipv6GeneralGroup2
-- EXCLUDE ipv6InterfaceTable
           ipv6RouterAdvertGroup
-- EXCLUDE ipv6RouterAdvertSpinLock
-- EXCLUDE ipv6ScopeZoneIndexTable
        }

        VARIATION   ipDefaultTTL
            ACCESS  read-only
            DESCRIPTION
                 "ipDefaultTTL is read-only on SAS-X 7210. It always returns the
                  value '64'.

                  ipDefaultTTL is read-only on SAS-X 7210. It always returns
                  the value '64'."

        VARIATION   ipForwarding
            ACCESS  read-only
            DESCRIPTION
                 "ipForwarding is read-only on SAS-X 7210. It always returns the
                  value 'forwarding (1)'.

                  ipForwarding is read-only on SAS-X 7210. It always returns
                  the value 'forwarding (1)'."

        VARIATION   ipNetToMediaType
            SYNTAX  INTEGER {
                       other                (1), -- none of the following
                       invalid              (2), -- an invalidated mapping
                       dynamic              (3),
                       static               (4),
                       managed              (5) -- added for 7x50
                    }
            DESCRIPTION
                 "The value 'managed (5)' is used to indicate that the ARP entry
                  has been added by:

                  - a static host; or - by a DHCP lease state if
                  TIMETRA-VRTR-MIB::vRtrIfArpPopulate is set to enabled.

                  An attempt to explicitly set the value of ipNetToMediaType to
                  'managed' results in an 'inconsistentValue' error.

                  The value 'managed (5)' is used to indicate that the ARP
                  entry has been added by:

                  - a static host; or - by a DHCP lease state if
                  TIMETRA-VRTR-MIB::vRtrIfArpPopulate is set to enabled.

                  An attempt to explicitly set the value of ipNetToMediaType to
                  'managed' results in an 'inconsistentValue' error."

        VARIATION   ipNetToPhysicalType
            SYNTAX  INTEGER {
                       other                (1), -- none of the following
                       invalid              (2), -- an invalidated mapping
                       dynamic              (3),
                       static               (4),
                       local                (5), -- local interface
                       managed              (100) -- added for 7x50
                    }
            DESCRIPTION
                 "The value 'managed (100)' is used to indicate that the ARP
                  entry has been added by:

                  - a static host; or - by a DHCP lease state if
                  TIMETRA-VRTR-MIB::vRtrIfArpPopulate is set to enabled.

                  An attempt to explicitly set the value of ipNetToPhysicalType
                  to 'managed' results in an 'inconsistentValue' error.

                  The value 'managed (100)' is used to indicate that the ARP
                  entry has been added by:

                  - a static host; or - by a DHCP lease state if
                  TIMETRA-VRTR-MIB::vRtrIfArpPopulate is set to enabled.

                  An attempt to explicitly set the value of ipNetToPhysicalType
                  to 'managed' results in an 'inconsistentValue' error."

        VARIATION   ipv6RouterAdvertSpinLock
            ACCESS  not-implemented
            DESCRIPTION
                 "Not supported.

                  Not supported."

    SUPPORTS        TCP-MIB
        INCLUDES {
           tcpBaseGroup,
           tcpConnectionGroup,
-- EXCLUDE tcpHCGroup
           tcpListenerGroup
        }

        VARIATION   tcpConnectionState
            ACCESS  read-only
            DESCRIPTION
                 "read-only implementation.

                  read-only implementation."

    SUPPORTS        UDP-MIB
        INCLUDES {
           udpEndpointGroup,
           udpGroup
-- EXCLUDE udpHCGroup
        }

    ::= { tmnxSASAgentV9v0   7 }

--
-- SASR ISIS CAPABILITIES
--
tmnxSASRIsisV9v0                  AGENT-CAPABILITIES
    PRODUCT-RELEASE "Alcatel-Lucent SAS"
    STATUS          current
    DESCRIPTION
         "Implementation of ISIS protocol capabilities for Alcatel-Lucent SASR
          systems release 9.0."

    SUPPORTS        ISIS-MIB
        INCLUDES {
           isisCircuitGroup,
           isisISAdjGroup,
           isisSystemGroup
        }

        VARIATION   isisCircEntry
            CREATION-REQUIRES {
                       vRtrIsisIfRowStatus
                    }
            DESCRIPTION
                 "Row entries in the isisCircTable are created by setting
                  TIMETRA-ISIS-MIB::vRtrIsisIfRowStatus."

        VARIATION   isisCircExistState
            SYNTAX  INTEGER {
                       active               (1)
                    }
            ACCESS  read-only
            DESCRIPTION
                 "RowStatus object. read-only implementation."

        VARIATION   isisCircIfIndex
            ACCESS  read-only
            DESCRIPTION
                 "read-only implementation."

        VARIATION   isisCircIfSubIndex
            ACCESS  read-only
            DESCRIPTION
                 "read-only implementation."

        VARIATION   isisCircLevelCSNPInterval
            ACCESS  read-only
            DESCRIPTION
                 "read-only implementation."

        VARIATION   isisCircLevelDRHelloTimer
            ACCESS  read-only
            DESCRIPTION
                 "read-only implementation."

        VARIATION   isisCircLevelDefaultMetric
            SYNTAX  DefaultMetric (0..63)
            ACCESS  read-only
            DESCRIPTION
                 "read-only implementation. isisCircLevelDefaultMetric can have
                  a value of 0 for loopback and system interfaces."

        VARIATION   isisCircLevelHelloMultiplier
            DEFVAL  { 3  }
            DESCRIPTION
                 "The default hello multiplier value is 3 instead of 10 since
                  the value of 10 results in a long holding time."

        VARIATION   isisCircLevelHelloTimer
            ACCESS  read-only
            DESCRIPTION
                 "read-only implementation."

        VARIATION   isisCircLevelISPriority
            ACCESS  read-only
            DESCRIPTION
                 "read-only implementation."

        VARIATION   isisCircLevelLSPThrottle
            ACCESS  read-only
            DESCRIPTION
                 "read-only implementation."

        VARIATION   isisCircLevelMinLSPRetransInt
            ACCESS  read-only
            DESCRIPTION
                 "read-only implementation."

        VARIATION   isisCircLevelPartSNPInterval
            ACCESS  read-only
            DESCRIPTION
                 "read-only implementation."

        VARIATION   isisSummAddrAdminState
            ACCESS  not-implemented
            DESCRIPTION
                 "Not supported."

        VARIATION   isisSummAddrDefaultMetric
            ACCESS  not-implemented
            DESCRIPTION
                 "Not supported."

        VARIATION   isisSummAddrExistState
            ACCESS  not-implemented
            DESCRIPTION
                 "Not supported."

        VARIATION   isisSysEntry
            CREATION-REQUIRES {
                       vRtrIsIsStatus
                    }
            DESCRIPTION
                 "Row entries in the isisSysTable are created by setting
                  TIMETRA-VRTR-MIB::vRtrIsIsStatus to true."

        VARIATION   isisSysExistState
            SYNTAX  INTEGER {
                       active               (1)
                    }
            ACCESS  read-only
            DESCRIPTION
                 "RowStatus object. read-only implementation."

        VARIATION   isisSysID
            ACCESS  read-only
            DESCRIPTION
                 "read-only implementation."

        VARIATION   isisSysL2toL1Leaking
            ACCESS  read-only
            DESCRIPTION
                 "read-only implementation."

        VARIATION   isisSysLSPIgnoreErrors
            ACCESS  read-only
            DESCRIPTION
                 "read-only implementation."

        VARIATION   isisSysLogAdjacencyChanges
            ACCESS  read-only
            DESCRIPTION
                 "read-only implementation."

        VARIATION   isisSysMaxAreaAddresses
            ACCESS  read-only
            DESCRIPTION
                 "read-only implementation."

        VARIATION   isisSysMaxPathSplits
            ACCESS  read-only
            DESCRIPTION
                 "read-only implementation."

        VARIATION   isisSysMinL1LSPGenInt
            ACCESS  read-only
            DESCRIPTION
                 "read-only implementation."

        VARIATION   isisSysMinL2LSPGenInt
            ACCESS  read-only
            DESCRIPTION
                 "read-only implementation."

        VARIATION   isisSysOrigL1LSPBuffSize
            ACCESS  not-implemented
            DESCRIPTION
                 "No longer supported. It has been replaced by
                  TIMETRA-ISIS-MIB::vRtrIsisSysOrigL1LSPBuffSize."

        VARIATION   isisSysOrigL2LSPBuffSize
            ACCESS  not-implemented
            DESCRIPTION
                 "No longer supported. It has been replaced by
                  TIMETRA-ISIS-MIB::vRtrIsisSysOrigL2LSPBuffSize."

        VARIATION   isisSysPollESHelloRate
            ACCESS  read-only
            DESCRIPTION
                 "read-only implementation."

        VARIATION   isisSysProtSuppExistState
            ACCESS  read-only
            DESCRIPTION
                 "read-only implementation."

    ::= { tmnxSASRAgentV9v0   8 }

--
-- SASX ISIS CAPABILITIES
--
tmnxSASXIsisV9v0                  AGENT-CAPABILITIES
    PRODUCT-RELEASE "Alcatel-Lucent SAS"
    STATUS          current
    DESCRIPTION
         "Implementation of ISIS protocol capabilities for Alcatel-Lucent SASX
          systems release 9.0."

    SUPPORTS        ISIS-MIB
        INCLUDES {
           isisCircuitGroup,
           isisISAdjGroup,
           isisSystemGroup
        }

        VARIATION   isisCircEntry
            CREATION-REQUIRES {
                       vRtrIsisIfRowStatus
                    }
            DESCRIPTION
                 "Row entries in the isisCircTable are created by setting
                  TIMETRA-ISIS-MIB::vRtrIsisIfRowStatus."

        VARIATION   isisCircExistState
            SYNTAX  INTEGER {
                       active               (1)
                    }
            ACCESS  read-only
            DESCRIPTION
                 "RowStatus object. read-only implementation."

        VARIATION   isisCircIfIndex
            ACCESS  read-only
            DESCRIPTION
                 "read-only implementation."

        VARIATION   isisCircIfSubIndex
            ACCESS  read-only
            DESCRIPTION
                 "read-only implementation."

        VARIATION   isisCircLevelCSNPInterval
            ACCESS  read-only
            DESCRIPTION
                 "read-only implementation."

        VARIATION   isisCircLevelDRHelloTimer
            ACCESS  read-only
            DESCRIPTION
                 "read-only implementation."

        VARIATION   isisCircLevelDefaultMetric
            SYNTAX  DefaultMetric (0..63)
            ACCESS  read-only
            DESCRIPTION
                 "read-only implementation. isisCircLevelDefaultMetric can have
                  a value of 0 for loopback and system interfaces."

        VARIATION   isisCircLevelHelloMultiplier
            DEFVAL  { 3  }
            DESCRIPTION
                 "The default hello multiplier value is 3 instead of 10 since
                  the value of 10 results in a long holding time."

        VARIATION   isisCircLevelHelloTimer
            ACCESS  read-only
            DESCRIPTION
                 "read-only implementation."

        VARIATION   isisCircLevelISPriority
            ACCESS  read-only
            DESCRIPTION
                 "read-only implementation."

        VARIATION   isisCircLevelLSPThrottle
            ACCESS  read-only
            DESCRIPTION
                 "read-only implementation."

        VARIATION   isisCircLevelMinLSPRetransInt
            ACCESS  read-only
            DESCRIPTION
                 "read-only implementation."

        VARIATION   isisCircLevelPartSNPInterval
            ACCESS  read-only
            DESCRIPTION
                 "read-only implementation."

        VARIATION   isisSummAddrAdminState
            ACCESS  not-implemented
            DESCRIPTION
                 "Not supported."

        VARIATION   isisSummAddrDefaultMetric
            ACCESS  not-implemented
            DESCRIPTION
                 "Not supported."

        VARIATION   isisSummAddrExistState
            ACCESS  not-implemented
            DESCRIPTION
                 "Not supported."

        VARIATION   isisSysEntry
            CREATION-REQUIRES {
                       vRtrIsIsStatus
                    }
            DESCRIPTION
                 "Row entries in the isisSysTable are created by setting
                  TIMETRA-VRTR-MIB::vRtrIsIsStatus to true."

        VARIATION   isisSysExistState
            SYNTAX  INTEGER {
                       active               (1)
                    }
            ACCESS  read-only
            DESCRIPTION
                 "RowStatus object. read-only implementation."

        VARIATION   isisSysID
            ACCESS  read-only
            DESCRIPTION
                 "read-only implementation."

        VARIATION   isisSysL2toL1Leaking
            ACCESS  read-only
            DESCRIPTION
                 "read-only implementation."

        VARIATION   isisSysLSPIgnoreErrors
            ACCESS  read-only
            DESCRIPTION
                 "read-only implementation."

        VARIATION   isisSysLogAdjacencyChanges
            ACCESS  read-only
            DESCRIPTION
                 "read-only implementation."

        VARIATION   isisSysMaxAreaAddresses
            ACCESS  read-only
            DESCRIPTION
                 "read-only implementation."

        VARIATION   isisSysMaxPathSplits
            ACCESS  read-only
            DESCRIPTION
                 "read-only implementation."

        VARIATION   isisSysMinL1LSPGenInt
            ACCESS  read-only
            DESCRIPTION
                 "read-only implementation."

        VARIATION   isisSysMinL2LSPGenInt
            ACCESS  read-only
            DESCRIPTION
                 "read-only implementation."

        VARIATION   isisSysOrigL1LSPBuffSize
            ACCESS  not-implemented
            DESCRIPTION
                 "No longer supported. It has been replaced by
                  TIMETRA-ISIS-MIB::vRtrIsisSysOrigL1LSPBuffSize."

        VARIATION   isisSysOrigL2LSPBuffSize
            ACCESS  not-implemented
            DESCRIPTION
                 "No longer supported. It has been replaced by
                  TIMETRA-ISIS-MIB::vRtrIsisSysOrigL2LSPBuffSize."

        VARIATION   isisSysPollESHelloRate
            ACCESS  read-only
            DESCRIPTION
                 "read-only implementation."

        VARIATION   isisSysProtSuppExistState
            ACCESS  read-only
            DESCRIPTION
                 "read-only implementation."

    ::= { tmnxSASXAgentV9v0   8 }

--
-- SASM ISIS CAPABILITIES
--
tmnxSASMIsisV9v0                  AGENT-CAPABILITIES
    PRODUCT-RELEASE "Alcatel-Lucent SAS"
    STATUS          current
    DESCRIPTION
         "Implementation of ISIS protocol capabilities for Alcatel-Lucent SASM
          systems release 9.0."

    SUPPORTS        ISIS-MIB
        INCLUDES {
           isisCircuitGroup,
           isisISAdjGroup,
           isisSystemGroup
        }

        VARIATION   isisCircEntry
            CREATION-REQUIRES {
                       vRtrIsisIfRowStatus
                    }
            DESCRIPTION
                 "Row entries in the isisCircTable are created by setting
                  TIMETRA-ISIS-MIB::vRtrIsisIfRowStatus."

        VARIATION   isisCircExistState
            SYNTAX  INTEGER {
                       active               (1)
                    }
            ACCESS  read-only
            DESCRIPTION
                 "RowStatus object. read-only implementation."

        VARIATION   isisCircIfIndex
            ACCESS  read-only
            DESCRIPTION
                 "read-only implementation."

        VARIATION   isisCircIfSubIndex
            ACCESS  read-only
            DESCRIPTION
                 "read-only implementation."

        VARIATION   isisCircLevelCSNPInterval
            ACCESS  read-only
            DESCRIPTION
                 "read-only implementation."

        VARIATION   isisCircLevelDRHelloTimer
            ACCESS  read-only
            DESCRIPTION
                 "read-only implementation."

        VARIATION   isisCircLevelDefaultMetric
            SYNTAX  DefaultMetric (0..63)
            ACCESS  read-only
            DESCRIPTION
                 "read-only implementation. isisCircLevelDefaultMetric can have
                  a value of 0 for loopback and system interfaces."

        VARIATION   isisCircLevelHelloMultiplier
            DEFVAL  { 3  }
            DESCRIPTION
                 "The default hello multiplier value is 3 instead of 10 since
                  the value of 10 results in a long holding time."

        VARIATION   isisCircLevelHelloTimer
            ACCESS  read-only
            DESCRIPTION
                 "read-only implementation."

        VARIATION   isisCircLevelISPriority
            ACCESS  read-only
            DESCRIPTION
                 "read-only implementation."

        VARIATION   isisCircLevelLSPThrottle
            ACCESS  read-only
            DESCRIPTION
                 "read-only implementation."

        VARIATION   isisCircLevelMinLSPRetransInt
            ACCESS  read-only
            DESCRIPTION
                 "read-only implementation."

        VARIATION   isisCircLevelPartSNPInterval
            ACCESS  read-only
            DESCRIPTION
                 "read-only implementation."

        VARIATION   isisSummAddrAdminState
            ACCESS  not-implemented
            DESCRIPTION
                 "Not supported."

        VARIATION   isisSummAddrDefaultMetric
            ACCESS  not-implemented
            DESCRIPTION
                 "Not supported."

        VARIATION   isisSummAddrExistState
            ACCESS  not-implemented
            DESCRIPTION
                 "Not supported."

        VARIATION   isisSysEntry
            CREATION-REQUIRES {
                       vRtrIsIsStatus
                    }
            DESCRIPTION
                 "Row entries in the isisSysTable are created by setting
                  TIMETRA-VRTR-MIB::vRtrIsIsStatus to true."

        VARIATION   isisSysExistState
            SYNTAX  INTEGER {
                       active               (1)
                    }
            ACCESS  read-only
            DESCRIPTION
                 "RowStatus object. read-only implementation."

        VARIATION   isisSysID
            ACCESS  read-only
            DESCRIPTION
                 "read-only implementation."

        VARIATION   isisSysL2toL1Leaking
            ACCESS  read-only
            DESCRIPTION
                 "read-only implementation."

        VARIATION   isisSysLSPIgnoreErrors
            ACCESS  read-only
            DESCRIPTION
                 "read-only implementation."

        VARIATION   isisSysLogAdjacencyChanges
            ACCESS  read-only
            DESCRIPTION
                 "read-only implementation."

        VARIATION   isisSysMaxAreaAddresses
            ACCESS  read-only
            DESCRIPTION
                 "read-only implementation."

        VARIATION   isisSysMaxPathSplits
            ACCESS  read-only
            DESCRIPTION
                 "read-only implementation."

        VARIATION   isisSysMinL1LSPGenInt
            ACCESS  read-only
            DESCRIPTION
                 "read-only implementation."

        VARIATION   isisSysMinL2LSPGenInt
            ACCESS  read-only
            DESCRIPTION
                 "read-only implementation."

        VARIATION   isisSysOrigL1LSPBuffSize
            ACCESS  not-implemented
            DESCRIPTION
                 "No longer supported. It has been replaced by
                  TIMETRA-ISIS-MIB::vRtrIsisSysOrigL1LSPBuffSize."

        VARIATION   isisSysOrigL2LSPBuffSize
            ACCESS  not-implemented
            DESCRIPTION
                 "No longer supported. It has been replaced by
                  TIMETRA-ISIS-MIB::vRtrIsisSysOrigL2LSPBuffSize."

        VARIATION   isisSysPollESHelloRate
            ACCESS  read-only
            DESCRIPTION
                 "read-only implementation."

        VARIATION   isisSysProtSuppExistState
            ACCESS  read-only
            DESCRIPTION
                 "read-only implementation."

    ::= { tmnxSASMAgentV9v0   8 }

--
-- SASMxp ISIS CAPABILITIES
--
tmnxSASMxpIsisV9v0                AGENT-CAPABILITIES
    PRODUCT-RELEASE "Alcatel-Lucent SAS"
    STATUS          current
    DESCRIPTION
         "Implementation of ISIS protocol capabilities for Alcatel-Lucent SASM
          xp systems release 9.0."

    SUPPORTS        ISIS-MIB
        INCLUDES {
           isisCircuitGroup,
           isisISAdjGroup,
           isisSystemGroup
        }

        VARIATION   isisCircEntry
            CREATION-REQUIRES {
                       vRtrIsisIfRowStatus
                    }
            DESCRIPTION
                 "Row entries in the isisCircTable are created by setting
                  TIMETRA-ISIS-MIB::vRtrIsisIfRowStatus."

        VARIATION   isisCircExistState
            SYNTAX  INTEGER {
                       active               (1)
                    }
            ACCESS  read-only
            DESCRIPTION
                 "RowStatus object. read-only implementation."

        VARIATION   isisCircIfIndex
            ACCESS  read-only
            DESCRIPTION
                 "read-only implementation."

        VARIATION   isisCircIfSubIndex
            ACCESS  read-only
            DESCRIPTION
                 "read-only implementation."

        VARIATION   isisCircLevelCSNPInterval
            ACCESS  read-only
            DESCRIPTION
                 "read-only implementation."

        VARIATION   isisCircLevelDRHelloTimer
            ACCESS  read-only
            DESCRIPTION
                 "read-only implementation."

        VARIATION   isisCircLevelDefaultMetric
            SYNTAX  DefaultMetric (0..63)
            ACCESS  read-only
            DESCRIPTION
                 "read-only implementation. isisCircLevelDefaultMetric can have
                  a value of 0 for loopback and system interfaces."

        VARIATION   isisCircLevelHelloMultiplier
            DEFVAL  { 3  }
            DESCRIPTION
                 "The default hello multiplier value is 3 instead of 10 since
                  the value of 10 results in a long holding time."

        VARIATION   isisCircLevelHelloTimer
            ACCESS  read-only
            DESCRIPTION
                 "read-only implementation."

        VARIATION   isisCircLevelISPriority
            ACCESS  read-only
            DESCRIPTION
                 "read-only implementation."

        VARIATION   isisCircLevelLSPThrottle
            ACCESS  read-only
            DESCRIPTION
                 "read-only implementation."

        VARIATION   isisCircLevelMinLSPRetransInt
            ACCESS  read-only
            DESCRIPTION
                 "read-only implementation."

        VARIATION   isisCircLevelPartSNPInterval
            ACCESS  read-only
            DESCRIPTION
                 "read-only implementation."

        VARIATION   isisSummAddrAdminState
            ACCESS  not-implemented
            DESCRIPTION
                 "Not supported."

        VARIATION   isisSummAddrDefaultMetric
            ACCESS  not-implemented
            DESCRIPTION
                 "Not supported."

        VARIATION   isisSummAddrExistState
            ACCESS  not-implemented
            DESCRIPTION
                 "Not supported."

        VARIATION   isisSysEntry
            CREATION-REQUIRES {
                       vRtrIsIsStatus
                    }
            DESCRIPTION
                 "Row entries in the isisSysTable are created by setting
                  TIMETRA-VRTR-MIB::vRtrIsIsStatus to true."

        VARIATION   isisSysExistState
            SYNTAX  INTEGER {
                       active               (1)
                    }
            ACCESS  read-only
            DESCRIPTION
                 "RowStatus object. read-only implementation."

        VARIATION   isisSysID
            ACCESS  read-only
            DESCRIPTION
                 "read-only implementation."

        VARIATION   isisSysL2toL1Leaking
            ACCESS  read-only
            DESCRIPTION
                 "read-only implementation."

        VARIATION   isisSysLSPIgnoreErrors
            ACCESS  read-only
            DESCRIPTION
                 "read-only implementation."

        VARIATION   isisSysLogAdjacencyChanges
            ACCESS  read-only
            DESCRIPTION
                 "read-only implementation."

        VARIATION   isisSysMaxAreaAddresses
            ACCESS  read-only
            DESCRIPTION
                 "read-only implementation."

        VARIATION   isisSysMaxPathSplits
            ACCESS  read-only
            DESCRIPTION
                 "read-only implementation."

        VARIATION   isisSysMinL1LSPGenInt
            ACCESS  read-only
            DESCRIPTION
                 "read-only implementation."

        VARIATION   isisSysMinL2LSPGenInt
            ACCESS  read-only
            DESCRIPTION
                 "read-only implementation."

        VARIATION   isisSysOrigL1LSPBuffSize
            ACCESS  not-implemented
            DESCRIPTION
                 "No longer supported. It has been replaced by
                  TIMETRA-ISIS-MIB::vRtrIsisSysOrigL1LSPBuffSize."

        VARIATION   isisSysOrigL2LSPBuffSize
            ACCESS  not-implemented
            DESCRIPTION
                 "No longer supported. It has been replaced by
                  TIMETRA-ISIS-MIB::vRtrIsisSysOrigL2LSPBuffSize."

        VARIATION   isisSysPollESHelloRate
            ACCESS  read-only
            DESCRIPTION
                 "read-only implementation."

        VARIATION   isisSysProtSuppExistState
            ACCESS  read-only
            DESCRIPTION
                 "read-only implementation."

    ::= { tmnxSASMxpAgentV9v0   8 }

--
-- SAS LAG CAPABILITIES
--
tmnxSASLagV9v0                    AGENT-CAPABILITIES
    PRODUCT-RELEASE "Alcatel-Lucent SAS"
    STATUS          current
    DESCRIPTION
         "Implementation of Link Aggregation, LAG, capabilities for
          Alcatel-Lucent SAS systems release 9.0."

    SUPPORTS        IEEE8023-LAG-MIB
        INCLUDES {
           dot3adAggGroup,
           dot3adAggPortGroup
        }

        VARIATION   dot3adAggActorAdminKey
            ACCESS  read-write
            DESCRIPTION
                 "The value of dot3adAggActorAdminKey cannot be changed after
                  the row entry has been created. A set to the same value
                  succeeds.

                  The value of dot3adAggActorAdminKey cannot be changed after
                  the row entry has been created. A set to the same value
                  succeeds."

        VARIATION   dot3adAggActorSystemPriority
            ACCESS  read-only
            DESCRIPTION
                 "read-only implementation.

                  read-only implementation."

        VARIATION   dot3adAggCollectorMaxDelay
            ACCESS  read-only
            DESCRIPTION
                 "read-only implementation.

                  read-only implementation."

        VARIATION   dot3adAggEntry
            CREATION-REQUIRES {
                       tLagRowStatus
                    }
            DESCRIPTION
                 "An entry in the dot3adAggTable is created when an entry is
                  created in the tLagConfigTable in TIMETRA-LAG-MIB.

                  An entry in the dot3adAggTable is created when an entry is
                  created in the tLagConfigTable in TIMETRA-LAG-MIB."

        VARIATION   dot3adAggPortActorAdminKey
            ACCESS  read-only
            DESCRIPTION
                 "read-only implementation.

                  read-only implementation."

        VARIATION   dot3adAggPortActorAdminState
            ACCESS  read-only
            DESCRIPTION
                 "read-only implementation.

                  read-only implementation."

        VARIATION   dot3adAggPortActorOperKey
            ACCESS  read-only
            DESCRIPTION
                 "read-only implementation.

                  read-only implementation."

        VARIATION   dot3adAggPortActorSystemPriority
            ACCESS  read-only
            DESCRIPTION
                 "read-only implementation.

                  read-only implementation."

        VARIATION   dot3adAggPortPartnerAdminKey
            ACCESS  read-only
            DESCRIPTION
                 "read-only implementation.

                  read-only implementation."

        VARIATION   dot3adAggPortPartnerAdminPort
            ACCESS  read-only
            DESCRIPTION
                 "read-only implementation.

                  read-only implementation."

        VARIATION   dot3adAggPortPartnerAdminPortPriority
            ACCESS  read-only
            DESCRIPTION
                 "read-only implementation.

                  read-only implementation."

        VARIATION   dot3adAggPortPartnerAdminState
            ACCESS  read-only
            DESCRIPTION
                 "read-only implementation.

                  read-only implementation."

        VARIATION   dot3adAggPortPartnerAdminSystemID
            ACCESS  read-only
            DESCRIPTION
                 "read-only implementation.

                  read-only implementation."

        VARIATION   dot3adAggPortPartnerAdminSystemPriority
            ACCESS  read-only
            DESCRIPTION
                 "read-only implementation.

                  read-only implementation."

    SUPPORTS        TIMETRA-LAG-MIB
        INCLUDES {
           tmnxLagHsmdaV6v0Group,
           tmnxLagInstanceV7v0Group,
           tmnxLagV6v0NotifGroup
        }

        VARIATION   tLagAccessAdaptQos
            ACCESS  not-implemented
            DESCRIPTION
                 "tLagAccessAdaptQos is not supported on 7210 SAS-R.

                  tLagAccessAdaptQos is not supported on 7210 SAS-R."

        VARIATION   tLagPortSubgroup
            SYNTAX  INTEGER (1..2)
            DESCRIPTION
                 "tLagPortSubgroup range for SAS-R is (1..2).

                  tLagPortSubgroup range for SAS-R is (1..2)."

        VARIATION   tLagPortThreshold
            SYNTAX  INTEGER (0..3)
            DESCRIPTION
                 "tLagPortThreshold range for SAS-R is (0..3).

                  tLagPortThreshold range for SAS-R is (0..3)."

        VARIATION   tLagPortType
            ACCESS  not-implemented
            DESCRIPTION
                 "tLagPortType is not supported on 7210 SAS-R.

                  tLagPortType is not supported on 7210 SAS-R."

    ::= { tmnxSASAgentV9v0   5 }

--
-- SAS LAG CAPABILITIES
--
tmnxSASLagV9v0                    AGENT-CAPABILITIES
    PRODUCT-RELEASE "Alcatel-Lucent SAS"
    STATUS          current
    DESCRIPTION
         "Implementation of Link Aggregation, LAG, capabilities for
          Alcatel-Lucent SAS systems release 9.0."

    SUPPORTS        IEEE8023-LAG-MIB
        INCLUDES {
           dot3adAggGroup,
           dot3adAggPortGroup
        }

        VARIATION   dot3adAggActorAdminKey
            ACCESS  read-write
            DESCRIPTION
                 "The value of dot3adAggActorAdminKey cannot be changed after
                  the row entry has been created. A set to the same value
                  succeeds.

                  The value of dot3adAggActorAdminKey cannot be changed after
                  the row entry has been created. A set to the same value
                  succeeds."

        VARIATION   dot3adAggActorSystemPriority
            ACCESS  read-only
            DESCRIPTION
                 "read-only implementation.

                  read-only implementation."

        VARIATION   dot3adAggCollectorMaxDelay
            ACCESS  read-only
            DESCRIPTION
                 "read-only implementation.

                  read-only implementation."

        VARIATION   dot3adAggEntry
            CREATION-REQUIRES {
                       tLagRowStatus
                    }
            DESCRIPTION
                 "An entry in the dot3adAggTable is created when an entry is
                  created in the tLagConfigTable in TIMETRA-LAG-MIB.

                  An entry in the dot3adAggTable is created when an entry is
                  created in the tLagConfigTable in TIMETRA-LAG-MIB."

        VARIATION   dot3adAggPortActorAdminKey
            ACCESS  read-only
            DESCRIPTION
                 "read-only implementation.

                  read-only implementation."

        VARIATION   dot3adAggPortActorAdminState
            ACCESS  read-only
            DESCRIPTION
                 "read-only implementation.

                  read-only implementation."

        VARIATION   dot3adAggPortActorOperKey
            ACCESS  read-only
            DESCRIPTION
                 "read-only implementation.

                  read-only implementation."

        VARIATION   dot3adAggPortActorSystemPriority
            ACCESS  read-only
            DESCRIPTION
                 "read-only implementation.

                  read-only implementation."

        VARIATION   dot3adAggPortPartnerAdminKey
            ACCESS  read-only
            DESCRIPTION
                 "read-only implementation.

                  read-only implementation."

        VARIATION   dot3adAggPortPartnerAdminPort
            ACCESS  read-only
            DESCRIPTION
                 "read-only implementation.

                  read-only implementation."

        VARIATION   dot3adAggPortPartnerAdminPortPriority
            ACCESS  read-only
            DESCRIPTION
                 "read-only implementation.

                  read-only implementation."

        VARIATION   dot3adAggPortPartnerAdminState
            ACCESS  read-only
            DESCRIPTION
                 "read-only implementation.

                  read-only implementation."

        VARIATION   dot3adAggPortPartnerAdminSystemID
            ACCESS  read-only
            DESCRIPTION
                 "read-only implementation.

                  read-only implementation."

        VARIATION   dot3adAggPortPartnerAdminSystemPriority
            ACCESS  read-only
            DESCRIPTION
                 "read-only implementation.

                  read-only implementation."

    SUPPORTS        TIMETRA-LAG-MIB
        INCLUDES {
           tmnxLagHsmdaV6v0Group,
           tmnxLagInstanceV7v0Group,
           tmnxLagV6v0NotifGroup
        }

        VARIATION   tLagAccessAdaptQos
            ACCESS  not-implemented
            DESCRIPTION
                 "tLagAccessAdaptQos is not supported on 7210 SAS-R.

                  tLagAccessAdaptQos is not supported on 7210 SAS-R."

        VARIATION   tLagPortSubgroup
            SYNTAX  INTEGER (1..2)
            DESCRIPTION
                 "tLagPortSubgroup range for SAS-R is (1..2).

                  tLagPortSubgroup range for SAS-R is (1..2)."

        VARIATION   tLagPortThreshold
            SYNTAX  INTEGER (0..3)
            DESCRIPTION
                 "tLagPortThreshold range for SAS-R is (0..3).

                  tLagPortThreshold range for SAS-R is (0..3)."

        VARIATION   tLagPortType
            ACCESS  not-implemented
            DESCRIPTION
                 "tLagPortType is not supported on 7210 SAS-R.

                  tLagPortType is not supported on 7210 SAS-R."

    ::= { tmnxSASAgentV9v0   5 }

--
-- SASR LDP CAPABILITIES
--
tmnxSASRLdpV9v0                   AGENT-CAPABILITIES
    PRODUCT-RELEASE "Alcatel-Lucent SAS"
    STATUS          current
    DESCRIPTION
         "Implementation of LDP capabilities for Alcatel-Lucent SASR systems
          release 9.0."

    SUPPORTS        MPLS-LDP-MIB
        INCLUDES {
-- EXCLUDE mplsFecIndexNext
-- EXCLUDE mplsFecTable
-- EXCLUDE mplsLdpAtmGroup
-- EXCLUDE mplsLdpAtmSessionTable
-- EXCLUDE mplsLdpEntityAtmObjects
-- EXCLUDE mplsLdpEntityFrameRelayObjects
-- EXCLUDE mplsLdpEntityGenericObjects
-- EXCLUDE mplsLdpEntityIndexNext
-- EXCLUDE mplsLdpEntityStatsTable
-- EXCLUDE mplsLdpFrameRelayGroup
-- EXCLUDE mplsLdpFrameRelaySessionTable
           mplsLdpGeneralGroup,
           mplsLdpNotificationsGroup
-- EXCLUDE mplsLdpSessionInLabelMapTable
-- EXCLUDE mplsLdpSessionOutLabelMapTable
-- EXCLUDE mplsLdpSessionPeerAddressTable
-- EXCLUDE mplsLdpSessionStatsTable
-- EXCLUDE mplsLdpSessionUpDownTrapEnable
-- EXCLUDE mplsLdpSessionXCMapTable
-- EXCLUDE mplsXCsFecsTable
        }

        VARIATION   mplsFecAddress
            ACCESS  not-implemented
            DESCRIPTION
                 "Not supported."

        VARIATION   mplsFecAddressFamily
            ACCESS  not-implemented
            DESCRIPTION
                 "Not supported."

        VARIATION   mplsFecAddressLength
            ACCESS  not-implemented
            DESCRIPTION
                 "Not supported."

        VARIATION   mplsFecIndexNext
            ACCESS  not-implemented
            DESCRIPTION
                 "Not supported."

        VARIATION   mplsFecRowStatus
            ACCESS  not-implemented
            DESCRIPTION
                 "Not supported."

        VARIATION   mplsFecStorageType
            ACCESS  not-implemented
            DESCRIPTION
                 "Not supported."

        VARIATION   mplsFecType
            ACCESS  not-implemented
            DESCRIPTION
                 "Not supported."

        VARIATION   mplsLdpAttemptedSessions
            ACCESS  not-implemented
            DESCRIPTION
                 "Not supported. It is implemented through
                  vRtrLdpStatsAttemptedSessions in TIMETRA-LDP-MIB."

        VARIATION   mplsLdpBadLdpIdentifierErrors
            ACCESS  not-implemented
            DESCRIPTION
                 "Not supported. It is implemented through
                  vRtrLdpStatsBadLdpIdentifierErrors in TIMETRA-LDP-MIB."

        VARIATION   mplsLdpBadMessageLengthErrors
            ACCESS  not-implemented
            DESCRIPTION
                 "Not supported. It is implemented through
                  vRtrLdpStatsBadMessageLengthErrors in TIMETRA-LDP-MIB."

        VARIATION   mplsLdpBadPduLengthErrors
            ACCESS  not-implemented
            DESCRIPTION
                 "Not supported. It is implemented through
                  vRtrLdpStatsBadPduLengthErrors in TIMETRA-LDP-MIB."

        VARIATION   mplsLdpBadTlvLengthErrors
            ACCESS  not-implemented
            DESCRIPTION
                 "Not supported. It is implemented through
                  vRtrLdpStatsBadTlvLengthErrors in TIMETRA-LDP-MIB."

        VARIATION   mplsLdpEntityAdminStatus
            ACCESS  read-only
            DESCRIPTION
                 "read-only implementation."

        VARIATION   mplsLdpEntityEntry
            CREATION-REQUIRES {
                       vRtrLdpStatus
                    }
            DESCRIPTION
                 "Row entries cannot be created by SNMP SET requests.

                  Row entries in the mplsLdpEntityTable are created by setting
                  TIMETRA-VRTR-MIB::vRtrLdpStatus to 'create'."

        VARIATION   mplsLdpEntityFailedInitSessionThreshold
            ACCESS  read-only
            DESCRIPTION
                 "read-only implementation."

        VARIATION   mplsLdpEntityFailedInitSessionTrapEnable
            ACCESS  read-only
            DESCRIPTION
                 "read-only implementation."

        VARIATION   mplsLdpEntityHelloHoldTimer
            ACCESS  read-only
            DESCRIPTION
                 "read-only implementation."

        VARIATION   mplsLdpEntityHopCountLimit
            ACCESS  read-only
            DESCRIPTION
                 "read-only implementation."

        VARIATION   mplsLdpEntityIndexNext
            ACCESS  not-implemented
            DESCRIPTION
                 "read-only implementation."

        VARIATION   mplsLdpEntityKeepAliveHoldTimer
            ACCESS  read-only
            DESCRIPTION
                 "read-only implementation."

        VARIATION   mplsLdpEntityLabelDistributionMethod
            ACCESS  read-only
            DESCRIPTION
                 "read-only implementation."

        VARIATION   mplsLdpEntityLabelRetentionMode
            ACCESS  read-only
            DESCRIPTION
                 "read-only implementation."

        VARIATION   mplsLdpEntityMaxPduLength
            ACCESS  read-only
            DESCRIPTION
                 "read-only implementation."

        VARIATION   mplsLdpEntityOptionalParameters
            ACCESS  read-only
            DESCRIPTION
                 "read-only implementation."

        VARIATION   mplsLdpEntityPVLimitMismatchTrapEnable
            ACCESS  read-only
            DESCRIPTION
                 "read-only implementation."

        VARIATION   mplsLdpEntityPathVectorLimit
            ACCESS  read-only
            DESCRIPTION
                 "read-only implementation."

        VARIATION   mplsLdpEntityProtocolVersion
            ACCESS  read-only
            DESCRIPTION
                 "read-only implementation."

        VARIATION   mplsLdpEntityRowStatus
            ACCESS  read-only
            DESCRIPTION
                 "read-only implementation. Row entries cannot be created by
                  SNMP SET requests. LDP Entities are created in TIMETRA-LDP-MIB
                  and this table when TIMETRA-VRTR-MIB::vRtrLdpStatus is set to
                  'create'."

        VARIATION   mplsLdpEntityStorageType
            ACCESS  read-only
            DESCRIPTION
                 "read-only implementation."

        VARIATION   mplsLdpEntityTargetedPeer
            ACCESS  read-only
            DESCRIPTION
                 "read-only implementation."

        VARIATION   mplsLdpEntityTargetedPeerAddr
            ACCESS  read-only
            DESCRIPTION
                 "read-only implementation."

        VARIATION   mplsLdpEntityTargetedPeerAddrType
            ACCESS  read-only
            DESCRIPTION
                 "read-only implementation."

        VARIATION   mplsLdpEntityWellKnownTcpDiscoveryPort
            ACCESS  read-only
            DESCRIPTION
                 "read-only implementation."

        VARIATION   mplsLdpEntityWellKnownUdpDiscoveryPort
            ACCESS  read-only
            DESCRIPTION
                 "read-only implementation."

        VARIATION   mplsLdpFailedInitSessionThresholdExceeded
            ACCESS  not-implemented
            DESCRIPTION
                 "Not supported."

        VARIATION   mplsLdpKeepAliveTimerExpiredErrors
            ACCESS  not-implemented
            DESCRIPTION
                 "Not supported. It is implemented through
                  vRtrLdpStatsKeepAliveExpiredErrors in TIMETRA-LDP-MIB."

        VARIATION   mplsLdpMalformedTlvValueErrors
            ACCESS  not-implemented
            DESCRIPTION
                 "Not supported. It is implemented through
                  vRtrLdpStatsMalformedTlvValueErrors in TIMETRA-LDP-MIB."

        VARIATION   mplsLdpPathVectorLimitMismatch
            ACCESS  not-implemented
            DESCRIPTION
                 "Not supported."

        VARIATION   mplsLdpSessionDown
            ACCESS  not-implemented
            DESCRIPTION
                 "Not supported."

        VARIATION   mplsLdpSessionPeerNextHopAddress
            ACCESS  not-implemented
            DESCRIPTION
                 "Not supported."

        VARIATION   mplsLdpSessionPeerNextHopAddressType
            ACCESS  not-implemented
            DESCRIPTION
                 "Not supported."

        VARIATION   mplsLdpSessionRejectedAdvertisementErrors
            ACCESS  not-implemented
            DESCRIPTION
                 "Not supported. It is implemented through
                  vRtrLdpStatsSessRejAdvErrors in TIMETRA-LDP-MIB."

        VARIATION   mplsLdpSessionRejectedLabelRangeErrors
            ACCESS  not-implemented
            DESCRIPTION
                 "Not supported. It is implemented through
                  vRtrLdpStatsSessRejLabelRangeErrors in TIMETRA-LDP-MIB."

        VARIATION   mplsLdpSessionRejectedMaxPduErrors
            ACCESS  not-implemented
            DESCRIPTION
                 "Not supported. It is implemented through
                  vRtrLdpStatsSessRejMaxPduErrors in TIMETRA-LDP-MIB."

        VARIATION   mplsLdpSessionRejectedNoHelloErrors
            ACCESS  not-implemented
            DESCRIPTION
                 "Not supported. It is implemented through
                  vRtrLdpStatsSessRejNoHelloErrors in TIMETRA-LDP-MIB."

        VARIATION   mplsLdpSessionStatsUnknownMessageTypeErrors
            ACCESS  not-implemented
            DESCRIPTION
                 "Not supported."

        VARIATION   mplsLdpSessionStatsUnknownTlvErrors
            ACCESS  not-implemented
            DESCRIPTION
                 "Not supported."

        VARIATION   mplsLdpSessionUp
            ACCESS  not-implemented
            DESCRIPTION
                 "Not supported."

        VARIATION   mplsLdpSessionUpDownTrapEnable
            ACCESS  not-implemented
            DESCRIPTION
                 "generation of MPLS LDP traps is controled by the
                  tmnxEventTable in TIMETRA-LOG-MIB."

        VARIATION   mplsLdpShutdownNotifReceived
            ACCESS  not-implemented
            DESCRIPTION
                 "Not supported. It is implemented through
                  vRtrLdpStatsShutdownNotifRecv in TIMETRA-LDP-MIB."

        VARIATION   mplsLdpShutdownNotifSent
            ACCESS  not-implemented
            DESCRIPTION
                 "Not supported. It is implemented through
                  vRtrLdpStatsShutdownNotifSent in TIMETRA-LDP-MIB."

    SUPPORTS        TIMETRA-LDP-MIB
        INCLUDES {
           tmnxLdpAddrFecV5v0Group,
           tmnxLdpAdjR2r1Group,
           tmnxLdpAggrPreMatchV7v0Group,
           tmnxLdpGlobalV5v0Group,
           tmnxLdpGlobalV8v0Group,
           tmnxLdpIfV5v0Group,
           tmnxLdpNotificationGroup,
           tmnxLdpPeerV7v0Group,
           tmnxLdpServFecV6v0Group,
           tmnxLdpSessionV5v0Group
-- EXCLUDE vRtrLdpAdjBackoffTable
-- EXCLUDE vRtrLdpIfTableSpinlock
-- EXCLUDE vRtrLdpPolicyTable
        }

        VARIATION   vRtrLdpEgrStatFecPfxRowStatus
            DESCRIPTION
                 "vRtrLdpEgrStatFecPfxRowStatus supports only 'ipv4' indices. If
                  an attempt is made to create a row entry with the
                  vRtrLdpEgrStatFecPfxAddrType index set to a value other than
                  'ipv4', a 'noCreation' error will be returned."

        VARIATION   vRtrLdpEgrStatFecPfxTblLastChgd
            ACCESS  not-implemented
            DESCRIPTION
                 "Not supported."

        VARIATION   vRtrLdpGenBackoffTime
            ACCESS  read-only
            DESCRIPTION
                 "read-only implementation."

        VARIATION   vRtrLdpGenHopLimit
            ACCESS  read-only
            DESCRIPTION
                 "read-only implementation."

        VARIATION   vRtrLdpGenLoopDetectCapable
            ACCESS  read-only
            DESCRIPTION
                 "read-only implementation."

        VARIATION   vRtrLdpGenMaxBackoffTime
            ACCESS  read-only
            DESCRIPTION
                 "read-only implementation."

        VARIATION   vRtrLdpGenPathVectorLimit
            ACCESS  read-only
            DESCRIPTION
                 "read-only implementation."

        VARIATION   vRtrLdpGenShortTTLPropLocal
            ACCESS  not-implemented
            DESCRIPTION
                 "Not supported."

        VARIATION   vRtrLdpGenShortTTLPropTransit
            ACCESS  not-implemented
            DESCRIPTION
                 "Not supported."

        VARIATION   vRtrLdpGenTargPassiveMode
            ACCESS  read-only
            DESCRIPTION
                 "read-only implementation."

        VARIATION   vRtrLdpGenTrustList
            ACCESS  not-implemented
            DESCRIPTION
                 "vRtrLdpGenTrustList is not implemented."

        VARIATION   vRtrLdpIfBackoffTime
            ACCESS  read-only
            DESCRIPTION
                 "read-only implementation."

        VARIATION   vRtrLdpIfMaxBackoffTime
            ACCESS  read-only
            DESCRIPTION
                 "read-only implementation."

        VARIATION   vRtrLdpIfPassiveMode
            ACCESS  read-only
            DESCRIPTION
                 "read-only implementation."

        VARIATION   vRtrLdpIfTableSpinlock
            ACCESS  not-implemented
            DESCRIPTION
                 "read-only implementation."

        VARIATION   vRtrLdpPeerTTLLogId
            ACCESS  not-implemented
            DESCRIPTION
                 "vRtrLdpPeerTTLLogId is not implemented."

        VARIATION   vRtrLdpStatsEgrFecPfxCount
            ACCESS  not-implemented
            DESCRIPTION
                 "Not supported."

        VARIATION   vRtrLdpTargExportPolicy1
            ACCESS  not-implemented
            DESCRIPTION
                 "Not supported."

        VARIATION   vRtrLdpTargExportPolicy2
            ACCESS  not-implemented
            DESCRIPTION
                 "Not supported."

        VARIATION   vRtrLdpTargExportPolicy3
            ACCESS  not-implemented
            DESCRIPTION
                 "Not supported."

        VARIATION   vRtrLdpTargExportPolicy4
            ACCESS  not-implemented
            DESCRIPTION
                 "Not supported."

        VARIATION   vRtrLdpTargExportPolicy5
            ACCESS  not-implemented
            DESCRIPTION
                 "Not supported."

        VARIATION   vRtrLdpTargImportPolicy1
            ACCESS  not-implemented
            DESCRIPTION
                 "Not supported."

        VARIATION   vRtrLdpTargImportPolicy2
            ACCESS  not-implemented
            DESCRIPTION
                 "Not supported."

        VARIATION   vRtrLdpTargImportPolicy3
            ACCESS  not-implemented
            DESCRIPTION
                 "Not supported."

        VARIATION   vRtrLdpTargImportPolicy4
            ACCESS  not-implemented
            DESCRIPTION
                 "Not supported."

        VARIATION   vRtrLdpTargImportPolicy5
            ACCESS  not-implemented
            DESCRIPTION
                 "Not supported."

    ::= { tmnxSASRAgentV9v0   9 }

--
-- SASX LDP CAPABILITIES
--
tmnxSASXLdpV9v0                   AGENT-CAPABILITIES
    PRODUCT-RELEASE "Alcatel-Lucent SAS"
    STATUS          current
    DESCRIPTION
         "Implementation of LDP capabilities for Alcatel-Lucent SASX systems
          release 9.0."

    SUPPORTS        MPLS-LDP-MIB
        INCLUDES {
-- EXCLUDE mplsFecIndexNext
-- EXCLUDE mplsFecTable
-- EXCLUDE mplsLdpAtmGroup
-- EXCLUDE mplsLdpAtmSessionTable
-- EXCLUDE mplsLdpEntityAtmObjects
-- EXCLUDE mplsLdpEntityFrameRelayObjects
-- EXCLUDE mplsLdpEntityGenericObjects
-- EXCLUDE mplsLdpEntityIndexNext
-- EXCLUDE mplsLdpEntityStatsTable
-- EXCLUDE mplsLdpFrameRelayGroup
-- EXCLUDE mplsLdpFrameRelaySessionTable
           mplsLdpGeneralGroup,
           mplsLdpNotificationsGroup
-- EXCLUDE mplsLdpSessionInLabelMapTable
-- EXCLUDE mplsLdpSessionOutLabelMapTable
-- EXCLUDE mplsLdpSessionPeerAddressTable
-- EXCLUDE mplsLdpSessionStatsTable
-- EXCLUDE mplsLdpSessionUpDownTrapEnable
-- EXCLUDE mplsLdpSessionXCMapTable
-- EXCLUDE mplsXCsFecsTable
        }

        VARIATION   mplsFecAddress
            ACCESS  not-implemented
            DESCRIPTION
                 "Not supported."

        VARIATION   mplsFecAddressFamily
            ACCESS  not-implemented
            DESCRIPTION
                 "Not supported."

        VARIATION   mplsFecAddressLength
            ACCESS  not-implemented
            DESCRIPTION
                 "Not supported."

        VARIATION   mplsFecIndexNext
            ACCESS  not-implemented
            DESCRIPTION
                 "Not supported."

        VARIATION   mplsFecRowStatus
            ACCESS  not-implemented
            DESCRIPTION
                 "Not supported."

        VARIATION   mplsFecStorageType
            ACCESS  not-implemented
            DESCRIPTION
                 "Not supported."

        VARIATION   mplsFecType
            ACCESS  not-implemented
            DESCRIPTION
                 "Not supported."

        VARIATION   mplsLdpAttemptedSessions
            ACCESS  not-implemented
            DESCRIPTION
                 "Not supported. It is implemented through
                  vRtrLdpStatsAttemptedSessions in TIMETRA-LDP-MIB."

        VARIATION   mplsLdpBadLdpIdentifierErrors
            ACCESS  not-implemented
            DESCRIPTION
                 "Not supported. It is implemented through
                  vRtrLdpStatsBadLdpIdentifierErrors in TIMETRA-LDP-MIB."

        VARIATION   mplsLdpBadMessageLengthErrors
            ACCESS  not-implemented
            DESCRIPTION
                 "Not supported. It is implemented through
                  vRtrLdpStatsBadMessageLengthErrors in TIMETRA-LDP-MIB."

        VARIATION   mplsLdpBadPduLengthErrors
            ACCESS  not-implemented
            DESCRIPTION
                 "Not supported. It is implemented through
                  vRtrLdpStatsBadPduLengthErrors in TIMETRA-LDP-MIB."

        VARIATION   mplsLdpBadTlvLengthErrors
            ACCESS  not-implemented
            DESCRIPTION
                 "Not supported. It is implemented through
                  vRtrLdpStatsBadTlvLengthErrors in TIMETRA-LDP-MIB."

        VARIATION   mplsLdpEntityAdminStatus
            ACCESS  read-only
            DESCRIPTION
                 "read-only implementation."

        VARIATION   mplsLdpEntityEntry
            CREATION-REQUIRES {
                       vRtrLdpStatus
                    }
            DESCRIPTION
                 "Row entries cannot be created by SNMP SET requests.

                  Row entries in the mplsLdpEntityTable are created by setting
                  TIMETRA-VRTR-MIB::vRtrLdpStatus to 'create'."

        VARIATION   mplsLdpEntityFailedInitSessionThreshold
            ACCESS  read-only
            DESCRIPTION
                 "read-only implementation."

        VARIATION   mplsLdpEntityFailedInitSessionTrapEnable
            ACCESS  read-only
            DESCRIPTION
                 "read-only implementation."

        VARIATION   mplsLdpEntityHelloHoldTimer
            ACCESS  read-only
            DESCRIPTION
                 "read-only implementation."

        VARIATION   mplsLdpEntityHopCountLimit
            ACCESS  read-only
            DESCRIPTION
                 "read-only implementation."

        VARIATION   mplsLdpEntityIndexNext
            ACCESS  not-implemented
            DESCRIPTION
                 "read-only implementation."

        VARIATION   mplsLdpEntityKeepAliveHoldTimer
            ACCESS  read-only
            DESCRIPTION
                 "read-only implementation."

        VARIATION   mplsLdpEntityLabelDistributionMethod
            ACCESS  read-only
            DESCRIPTION
                 "read-only implementation."

        VARIATION   mplsLdpEntityLabelRetentionMode
            ACCESS  read-only
            DESCRIPTION
                 "read-only implementation."

        VARIATION   mplsLdpEntityMaxPduLength
            ACCESS  read-only
            DESCRIPTION
                 "read-only implementation."

        VARIATION   mplsLdpEntityOptionalParameters
            ACCESS  read-only
            DESCRIPTION
                 "read-only implementation."

        VARIATION   mplsLdpEntityPVLimitMismatchTrapEnable
            ACCESS  read-only
            DESCRIPTION
                 "read-only implementation."

        VARIATION   mplsLdpEntityPathVectorLimit
            ACCESS  read-only
            DESCRIPTION
                 "read-only implementation."

        VARIATION   mplsLdpEntityProtocolVersion
            ACCESS  read-only
            DESCRIPTION
                 "read-only implementation."

        VARIATION   mplsLdpEntityRowStatus
            ACCESS  read-only
            DESCRIPTION
                 "read-only implementation. Row entries cannot be created by
                  SNMP SET requests. LDP Entities are created in TIMETRA-LDP-MIB
                  and this table when TIMETRA-VRTR-MIB::vRtrLdpStatus is set to
                  'create'."

        VARIATION   mplsLdpEntityStorageType
            ACCESS  read-only
            DESCRIPTION
                 "read-only implementation."

        VARIATION   mplsLdpEntityTargetedPeer
            ACCESS  read-only
            DESCRIPTION
                 "read-only implementation."

        VARIATION   mplsLdpEntityTargetedPeerAddr
            ACCESS  read-only
            DESCRIPTION
                 "read-only implementation."

        VARIATION   mplsLdpEntityTargetedPeerAddrType
            ACCESS  read-only
            DESCRIPTION
                 "read-only implementation."

        VARIATION   mplsLdpEntityWellKnownTcpDiscoveryPort
            ACCESS  read-only
            DESCRIPTION
                 "read-only implementation."

        VARIATION   mplsLdpEntityWellKnownUdpDiscoveryPort
            ACCESS  read-only
            DESCRIPTION
                 "read-only implementation."

        VARIATION   mplsLdpFailedInitSessionThresholdExceeded
            ACCESS  not-implemented
            DESCRIPTION
                 "Not supported."

        VARIATION   mplsLdpKeepAliveTimerExpiredErrors
            ACCESS  not-implemented
            DESCRIPTION
                 "Not supported. It is implemented through
                  vRtrLdpStatsKeepAliveExpiredErrors in TIMETRA-LDP-MIB."

        VARIATION   mplsLdpMalformedTlvValueErrors
            ACCESS  not-implemented
            DESCRIPTION
                 "Not supported. It is implemented through
                  vRtrLdpStatsMalformedTlvValueErrors in TIMETRA-LDP-MIB."

        VARIATION   mplsLdpPathVectorLimitMismatch
            ACCESS  not-implemented
            DESCRIPTION
                 "Not supported."

        VARIATION   mplsLdpSessionDown
            ACCESS  not-implemented
            DESCRIPTION
                 "Not supported."

        VARIATION   mplsLdpSessionPeerNextHopAddress
            ACCESS  not-implemented
            DESCRIPTION
                 "Not supported."

        VARIATION   mplsLdpSessionPeerNextHopAddressType
            ACCESS  not-implemented
            DESCRIPTION
                 "Not supported."

        VARIATION   mplsLdpSessionRejectedAdvertisementErrors
            ACCESS  not-implemented
            DESCRIPTION
                 "Not supported. It is implemented through
                  vRtrLdpStatsSessRejAdvErrors in TIMETRA-LDP-MIB."

        VARIATION   mplsLdpSessionRejectedLabelRangeErrors
            ACCESS  not-implemented
            DESCRIPTION
                 "Not supported. It is implemented through
                  vRtrLdpStatsSessRejLabelRangeErrors in TIMETRA-LDP-MIB."

        VARIATION   mplsLdpSessionRejectedMaxPduErrors
            ACCESS  not-implemented
            DESCRIPTION
                 "Not supported. It is implemented through
                  vRtrLdpStatsSessRejMaxPduErrors in TIMETRA-LDP-MIB."

        VARIATION   mplsLdpSessionRejectedNoHelloErrors
            ACCESS  not-implemented
            DESCRIPTION
                 "Not supported. It is implemented through
                  vRtrLdpStatsSessRejNoHelloErrors in TIMETRA-LDP-MIB."

        VARIATION   mplsLdpSessionStatsUnknownMessageTypeErrors
            ACCESS  not-implemented
            DESCRIPTION
                 "Not supported."

        VARIATION   mplsLdpSessionStatsUnknownTlvErrors
            ACCESS  not-implemented
            DESCRIPTION
                 "Not supported."

        VARIATION   mplsLdpSessionUp
            ACCESS  not-implemented
            DESCRIPTION
                 "Not supported."

        VARIATION   mplsLdpSessionUpDownTrapEnable
            ACCESS  not-implemented
            DESCRIPTION
                 "generation of MPLS LDP traps is controled by the
                  tmnxEventTable in TIMETRA-LOG-MIB."

        VARIATION   mplsLdpShutdownNotifReceived
            ACCESS  not-implemented
            DESCRIPTION
                 "Not supported. It is implemented through
                  vRtrLdpStatsShutdownNotifRecv in TIMETRA-LDP-MIB."

        VARIATION   mplsLdpShutdownNotifSent
            ACCESS  not-implemented
            DESCRIPTION
                 "Not supported. It is implemented through
                  vRtrLdpStatsShutdownNotifSent in TIMETRA-LDP-MIB."

    SUPPORTS        TIMETRA-LDP-MIB
        INCLUDES {
           tmnxLdpAddrFecV5v0Group,
           tmnxLdpAdjR2r1Group,
           tmnxLdpAggrPreMatchV7v0Group,
           tmnxLdpGlobalV5v0Group,
           tmnxLdpGlobalV8v0Group,
           tmnxLdpIfV5v0Group,
           tmnxLdpNotificationGroup,
           tmnxLdpPeerV7v0Group,
           tmnxLdpServFecV6v0Group,
           tmnxLdpSessionV5v0Group
-- EXCLUDE vRtrLdpAdjBackoffTable
-- EXCLUDE vRtrLdpIfTableSpinlock
-- EXCLUDE vRtrLdpPolicyTable
        }

        VARIATION   vRtrLdpEgrStatFecPfxRowStatus
            DESCRIPTION
                 "vRtrLdpEgrStatFecPfxRowStatus supports only 'ipv4' indices. If
                  an attempt is made to create a row entry with the
                  vRtrLdpEgrStatFecPfxAddrType index set to a value other than
                  'ipv4', a 'noCreation' error will be returned."

        VARIATION   vRtrLdpEgrStatFecPfxTblLastChgd
            ACCESS  not-implemented
            DESCRIPTION
                 "Not supported."

        VARIATION   vRtrLdpGenBackoffTime
            ACCESS  read-only
            DESCRIPTION
                 "read-only implementation."

        VARIATION   vRtrLdpGenHopLimit
            ACCESS  read-only
            DESCRIPTION
                 "read-only implementation."

        VARIATION   vRtrLdpGenLoopDetectCapable
            ACCESS  read-only
            DESCRIPTION
                 "read-only implementation."

        VARIATION   vRtrLdpGenMaxBackoffTime
            ACCESS  read-only
            DESCRIPTION
                 "read-only implementation."

        VARIATION   vRtrLdpGenPathVectorLimit
            ACCESS  read-only
            DESCRIPTION
                 "read-only implementation."

        VARIATION   vRtrLdpGenShortTTLPropLocal
            ACCESS  not-implemented
            DESCRIPTION
                 "Not supported."

        VARIATION   vRtrLdpGenShortTTLPropTransit
            ACCESS  not-implemented
            DESCRIPTION
                 "Not supported."

        VARIATION   vRtrLdpGenTargPassiveMode
            ACCESS  read-only
            DESCRIPTION
                 "read-only implementation."

        VARIATION   vRtrLdpGenTrustList
            ACCESS  not-implemented
            DESCRIPTION
                 "vRtrLdpGenTrustList is not implemented."

        VARIATION   vRtrLdpIfBackoffTime
            ACCESS  read-only
            DESCRIPTION
                 "read-only implementation."

        VARIATION   vRtrLdpIfMaxBackoffTime
            ACCESS  read-only
            DESCRIPTION
                 "read-only implementation."

        VARIATION   vRtrLdpIfPassiveMode
            ACCESS  read-only
            DESCRIPTION
                 "read-only implementation."

        VARIATION   vRtrLdpIfTableSpinlock
            ACCESS  not-implemented
            DESCRIPTION
                 "read-only implementation."

        VARIATION   vRtrLdpPeerTTLLogId
            ACCESS  not-implemented
            DESCRIPTION
                 "vRtrLdpPeerTTLLogId is not implemented."

        VARIATION   vRtrLdpStatsEgrFecPfxCount
            ACCESS  not-implemented
            DESCRIPTION
                 "Not supported."

        VARIATION   vRtrLdpTargExportPolicy1
            ACCESS  not-implemented
            DESCRIPTION
                 "Not supported."

        VARIATION   vRtrLdpTargExportPolicy2
            ACCESS  not-implemented
            DESCRIPTION
                 "Not supported."

        VARIATION   vRtrLdpTargExportPolicy3
            ACCESS  not-implemented
            DESCRIPTION
                 "Not supported."

        VARIATION   vRtrLdpTargExportPolicy4
            ACCESS  not-implemented
            DESCRIPTION
                 "Not supported."

        VARIATION   vRtrLdpTargExportPolicy5
            ACCESS  not-implemented
            DESCRIPTION
                 "Not supported."

        VARIATION   vRtrLdpTargImportPolicy1
            ACCESS  not-implemented
            DESCRIPTION
                 "Not supported."

        VARIATION   vRtrLdpTargImportPolicy2
            ACCESS  not-implemented
            DESCRIPTION
                 "Not supported."

        VARIATION   vRtrLdpTargImportPolicy3
            ACCESS  not-implemented
            DESCRIPTION
                 "Not supported."

        VARIATION   vRtrLdpTargImportPolicy4
            ACCESS  not-implemented
            DESCRIPTION
                 "Not supported."

        VARIATION   vRtrLdpTargImportPolicy5
            ACCESS  not-implemented
            DESCRIPTION
                 "Not supported."

    ::= { tmnxSASXAgentV9v0   9 }

--
-- SASM LDP CAPABILITIES
--
tmnxSASMLdpV9v0                   AGENT-CAPABILITIES
    PRODUCT-RELEASE "Alcatel-Lucent SAS"
    STATUS          current
    DESCRIPTION
         "Implementation of LDP capabilities for Alcatel-Lucent SASM systems
          release 9.0."

    SUPPORTS        MPLS-LDP-MIB
        INCLUDES {
-- EXCLUDE mplsFecIndexNext
-- EXCLUDE mplsFecTable
-- EXCLUDE mplsLdpAtmGroup
-- EXCLUDE mplsLdpAtmSessionTable
-- EXCLUDE mplsLdpEntityAtmObjects
-- EXCLUDE mplsLdpEntityFrameRelayObjects
-- EXCLUDE mplsLdpEntityGenericObjects
-- EXCLUDE mplsLdpEntityIndexNext
-- EXCLUDE mplsLdpEntityStatsTable
-- EXCLUDE mplsLdpFrameRelayGroup
-- EXCLUDE mplsLdpFrameRelaySessionTable
           mplsLdpGeneralGroup,
           mplsLdpNotificationsGroup
-- EXCLUDE mplsLdpSessionInLabelMapTable
-- EXCLUDE mplsLdpSessionOutLabelMapTable
-- EXCLUDE mplsLdpSessionPeerAddressTable
-- EXCLUDE mplsLdpSessionStatsTable
-- EXCLUDE mplsLdpSessionUpDownTrapEnable
-- EXCLUDE mplsLdpSessionXCMapTable
-- EXCLUDE mplsXCsFecsTable
        }

        VARIATION   mplsFecAddress
            ACCESS  not-implemented
            DESCRIPTION
                 "Not supported."

        VARIATION   mplsFecAddressFamily
            ACCESS  not-implemented
            DESCRIPTION
                 "Not supported."

        VARIATION   mplsFecAddressLength
            ACCESS  not-implemented
            DESCRIPTION
                 "Not supported."

        VARIATION   mplsFecIndexNext
            ACCESS  not-implemented
            DESCRIPTION
                 "Not supported."

        VARIATION   mplsFecRowStatus
            ACCESS  not-implemented
            DESCRIPTION
                 "Not supported."

        VARIATION   mplsFecStorageType
            ACCESS  not-implemented
            DESCRIPTION
                 "Not supported."

        VARIATION   mplsFecType
            ACCESS  not-implemented
            DESCRIPTION
                 "Not supported."

        VARIATION   mplsLdpAttemptedSessions
            ACCESS  not-implemented
            DESCRIPTION
                 "Not supported. It is implemented through
                  vRtrLdpStatsAttemptedSessions in TIMETRA-LDP-MIB."

        VARIATION   mplsLdpBadLdpIdentifierErrors
            ACCESS  not-implemented
            DESCRIPTION
                 "Not supported. It is implemented through
                  vRtrLdpStatsBadLdpIdentifierErrors in TIMETRA-LDP-MIB."

        VARIATION   mplsLdpBadMessageLengthErrors
            ACCESS  not-implemented
            DESCRIPTION
                 "Not supported. It is implemented through
                  vRtrLdpStatsBadMessageLengthErrors in TIMETRA-LDP-MIB."

        VARIATION   mplsLdpBadPduLengthErrors
            ACCESS  not-implemented
            DESCRIPTION
                 "Not supported. It is implemented through
                  vRtrLdpStatsBadPduLengthErrors in TIMETRA-LDP-MIB."

        VARIATION   mplsLdpBadTlvLengthErrors
            ACCESS  not-implemented
            DESCRIPTION
                 "Not supported. It is implemented through
                  vRtrLdpStatsBadTlvLengthErrors in TIMETRA-LDP-MIB."

        VARIATION   mplsLdpEntityAdminStatus
            ACCESS  read-only
            DESCRIPTION
                 "read-only implementation."

        VARIATION   mplsLdpEntityEntry
            CREATION-REQUIRES {
                       vRtrLdpStatus
                    }
            DESCRIPTION
                 "Row entries cannot be created by SNMP SET requests.

                  Row entries in the mplsLdpEntityTable are created by setting
                  TIMETRA-VRTR-MIB::vRtrLdpStatus to 'create'."

        VARIATION   mplsLdpEntityFailedInitSessionThreshold
            ACCESS  read-only
            DESCRIPTION
                 "read-only implementation."

        VARIATION   mplsLdpEntityFailedInitSessionTrapEnable
            ACCESS  read-only
            DESCRIPTION
                 "read-only implementation."

        VARIATION   mplsLdpEntityHelloHoldTimer
            ACCESS  read-only
            DESCRIPTION
                 "read-only implementation."

        VARIATION   mplsLdpEntityHopCountLimit
            ACCESS  read-only
            DESCRIPTION
                 "read-only implementation."

        VARIATION   mplsLdpEntityIndexNext
            ACCESS  not-implemented
            DESCRIPTION
                 "read-only implementation."

        VARIATION   mplsLdpEntityKeepAliveHoldTimer
            ACCESS  read-only
            DESCRIPTION
                 "read-only implementation."

        VARIATION   mplsLdpEntityLabelDistributionMethod
            ACCESS  read-only
            DESCRIPTION
                 "read-only implementation."

        VARIATION   mplsLdpEntityLabelRetentionMode
            ACCESS  read-only
            DESCRIPTION
                 "read-only implementation."

        VARIATION   mplsLdpEntityMaxPduLength
            ACCESS  read-only
            DESCRIPTION
                 "read-only implementation."

        VARIATION   mplsLdpEntityOptionalParameters
            ACCESS  read-only
            DESCRIPTION
                 "read-only implementation."

        VARIATION   mplsLdpEntityPVLimitMismatchTrapEnable
            ACCESS  read-only
            DESCRIPTION
                 "read-only implementation."

        VARIATION   mplsLdpEntityPathVectorLimit
            ACCESS  read-only
            DESCRIPTION
                 "read-only implementation."

        VARIATION   mplsLdpEntityProtocolVersion
            ACCESS  read-only
            DESCRIPTION
                 "read-only implementation."

        VARIATION   mplsLdpEntityRowStatus
            ACCESS  read-only
            DESCRIPTION
                 "read-only implementation. Row entries cannot be created by
                  SNMP SET requests. LDP Entities are created in TIMETRA-LDP-MIB
                  and this table when TIMETRA-VRTR-MIB::vRtrLdpStatus is set to
                  'create'."

        VARIATION   mplsLdpEntityStorageType
            ACCESS  read-only
            DESCRIPTION
                 "read-only implementation."

        VARIATION   mplsLdpEntityTargetedPeer
            ACCESS  read-only
            DESCRIPTION
                 "read-only implementation."

        VARIATION   mplsLdpEntityTargetedPeerAddr
            ACCESS  read-only
            DESCRIPTION
                 "read-only implementation."

        VARIATION   mplsLdpEntityTargetedPeerAddrType
            ACCESS  read-only
            DESCRIPTION
                 "read-only implementation."

        VARIATION   mplsLdpEntityWellKnownTcpDiscoveryPort
            ACCESS  read-only
            DESCRIPTION
                 "read-only implementation."

        VARIATION   mplsLdpEntityWellKnownUdpDiscoveryPort
            ACCESS  read-only
            DESCRIPTION
                 "read-only implementation."

        VARIATION   mplsLdpFailedInitSessionThresholdExceeded
            ACCESS  not-implemented
            DESCRIPTION
                 "Not supported."

        VARIATION   mplsLdpKeepAliveTimerExpiredErrors
            ACCESS  not-implemented
            DESCRIPTION
                 "Not supported. It is implemented through
                  vRtrLdpStatsKeepAliveExpiredErrors in TIMETRA-LDP-MIB."

        VARIATION   mplsLdpMalformedTlvValueErrors
            ACCESS  not-implemented
            DESCRIPTION
                 "Not supported. It is implemented through
                  vRtrLdpStatsMalformedTlvValueErrors in TIMETRA-LDP-MIB."

        VARIATION   mplsLdpPathVectorLimitMismatch
            ACCESS  not-implemented
            DESCRIPTION
                 "Not supported."

        VARIATION   mplsLdpSessionDown
            ACCESS  not-implemented
            DESCRIPTION
                 "Not supported."

        VARIATION   mplsLdpSessionPeerNextHopAddress
            ACCESS  not-implemented
            DESCRIPTION
                 "Not supported."

        VARIATION   mplsLdpSessionPeerNextHopAddressType
            ACCESS  not-implemented
            DESCRIPTION
                 "Not supported."

        VARIATION   mplsLdpSessionRejectedAdvertisementErrors
            ACCESS  not-implemented
            DESCRIPTION
                 "Not supported. It is implemented through
                  vRtrLdpStatsSessRejAdvErrors in TIMETRA-LDP-MIB."

        VARIATION   mplsLdpSessionRejectedLabelRangeErrors
            ACCESS  not-implemented
            DESCRIPTION
                 "Not supported. It is implemented through
                  vRtrLdpStatsSessRejLabelRangeErrors in TIMETRA-LDP-MIB."

        VARIATION   mplsLdpSessionRejectedMaxPduErrors
            ACCESS  not-implemented
            DESCRIPTION
                 "Not supported. It is implemented through
                  vRtrLdpStatsSessRejMaxPduErrors in TIMETRA-LDP-MIB."

        VARIATION   mplsLdpSessionRejectedNoHelloErrors
            ACCESS  not-implemented
            DESCRIPTION
                 "Not supported. It is implemented through
                  vRtrLdpStatsSessRejNoHelloErrors in TIMETRA-LDP-MIB."

        VARIATION   mplsLdpSessionStatsUnknownMessageTypeErrors
            ACCESS  not-implemented
            DESCRIPTION
                 "Not supported."

        VARIATION   mplsLdpSessionStatsUnknownTlvErrors
            ACCESS  not-implemented
            DESCRIPTION
                 "Not supported."

        VARIATION   mplsLdpSessionUp
            ACCESS  not-implemented
            DESCRIPTION
                 "Not supported."

        VARIATION   mplsLdpSessionUpDownTrapEnable
            ACCESS  not-implemented
            DESCRIPTION
                 "generation of MPLS LDP traps is controled by the
                  tmnxEventTable in TIMETRA-LOG-MIB."

        VARIATION   mplsLdpShutdownNotifReceived
            ACCESS  not-implemented
            DESCRIPTION
                 "Not supported. It is implemented through
                  vRtrLdpStatsShutdownNotifRecv in TIMETRA-LDP-MIB."

        VARIATION   mplsLdpShutdownNotifSent
            ACCESS  not-implemented
            DESCRIPTION
                 "Not supported. It is implemented through
                  vRtrLdpStatsShutdownNotifSent in TIMETRA-LDP-MIB."

    SUPPORTS        TIMETRA-LDP-MIB
        INCLUDES {
           tmnxLdpAddrFecV5v0Group,
           tmnxLdpAdjR2r1Group,
           tmnxLdpAggrPreMatchV7v0Group,
           tmnxLdpGlobalV5v0Group,
           tmnxLdpGlobalV8v0Group,
           tmnxLdpIfV5v0Group,
           tmnxLdpNotificationGroup,
           tmnxLdpPeerV7v0Group,
           tmnxLdpServFecV6v0Group,
           tmnxLdpSessionV5v0Group
-- EXCLUDE vRtrLdpAdjBackoffTable
-- EXCLUDE vRtrLdpIfTableSpinlock
-- EXCLUDE vRtrLdpPolicyTable
        }

        VARIATION   vRtrLdpEgrStatFecPfxRowStatus
            DESCRIPTION
                 "vRtrLdpEgrStatFecPfxRowStatus supports only 'ipv4' indices. If
                  an attempt is made to create a row entry with the
                  vRtrLdpEgrStatFecPfxAddrType index set to a value other than
                  'ipv4', a 'noCreation' error will be returned."

        VARIATION   vRtrLdpEgrStatFecPfxTblLastChgd
            ACCESS  not-implemented
            DESCRIPTION
                 "Not supported."

        VARIATION   vRtrLdpGenBackoffTime
            ACCESS  read-only
            DESCRIPTION
                 "read-only implementation."

        VARIATION   vRtrLdpGenHopLimit
            ACCESS  read-only
            DESCRIPTION
                 "read-only implementation."

        VARIATION   vRtrLdpGenLoopDetectCapable
            ACCESS  read-only
            DESCRIPTION
                 "read-only implementation."

        VARIATION   vRtrLdpGenMaxBackoffTime
            ACCESS  read-only
            DESCRIPTION
                 "read-only implementation."

        VARIATION   vRtrLdpGenPathVectorLimit
            ACCESS  read-only
            DESCRIPTION
                 "read-only implementation."

        VARIATION   vRtrLdpGenShortTTLPropLocal
            ACCESS  not-implemented
            DESCRIPTION
                 "Not supported."

        VARIATION   vRtrLdpGenShortTTLPropTransit
            ACCESS  not-implemented
            DESCRIPTION
                 "Not supported."

        VARIATION   vRtrLdpGenTargPassiveMode
            ACCESS  read-only
            DESCRIPTION
                 "read-only implementation."

        VARIATION   vRtrLdpGenTrustList
            ACCESS  not-implemented
            DESCRIPTION
                 "vRtrLdpGenTrustList is not implemented."

        VARIATION   vRtrLdpIfBackoffTime
            ACCESS  read-only
            DESCRIPTION
                 "read-only implementation."

        VARIATION   vRtrLdpIfMaxBackoffTime
            ACCESS  read-only
            DESCRIPTION
                 "read-only implementation."

        VARIATION   vRtrLdpIfPassiveMode
            ACCESS  read-only
            DESCRIPTION
                 "read-only implementation."

        VARIATION   vRtrLdpIfTableSpinlock
            ACCESS  not-implemented
            DESCRIPTION
                 "read-only implementation."

        VARIATION   vRtrLdpPeerTTLLogId
            ACCESS  not-implemented
            DESCRIPTION
                 "vRtrLdpPeerTTLLogId is not implemented."

        VARIATION   vRtrLdpStatsEgrFecPfxCount
            ACCESS  not-implemented
            DESCRIPTION
                 "Not supported."

        VARIATION   vRtrLdpTargExportPolicy1
            ACCESS  not-implemented
            DESCRIPTION
                 "Not supported."

        VARIATION   vRtrLdpTargExportPolicy2
            ACCESS  not-implemented
            DESCRIPTION
                 "Not supported."

        VARIATION   vRtrLdpTargExportPolicy3
            ACCESS  not-implemented
            DESCRIPTION
                 "Not supported."

        VARIATION   vRtrLdpTargExportPolicy4
            ACCESS  not-implemented
            DESCRIPTION
                 "Not supported."

        VARIATION   vRtrLdpTargExportPolicy5
            ACCESS  not-implemented
            DESCRIPTION
                 "Not supported."

        VARIATION   vRtrLdpTargImportPolicy1
            ACCESS  not-implemented
            DESCRIPTION
                 "Not supported."

        VARIATION   vRtrLdpTargImportPolicy2
            ACCESS  not-implemented
            DESCRIPTION
                 "Not supported."

        VARIATION   vRtrLdpTargImportPolicy3
            ACCESS  not-implemented
            DESCRIPTION
                 "Not supported."

        VARIATION   vRtrLdpTargImportPolicy4
            ACCESS  not-implemented
            DESCRIPTION
                 "Not supported."

        VARIATION   vRtrLdpTargImportPolicy5
            ACCESS  not-implemented
            DESCRIPTION
                 "Not supported."

    ::= { tmnxSASMAgentV9v0   9 }

--
-- SASMxp LDP CAPABILITIES
--
tmnxSASMxpLdpV9v0                 AGENT-CAPABILITIES
    PRODUCT-RELEASE "Alcatel-Lucent SAS"
    STATUS          current
    DESCRIPTION
         "Implementation of LDP capabilities for Alcatel-Lucent SASM xp systems
          release 9.0."

    SUPPORTS        MPLS-LDP-MIB
        INCLUDES {
-- EXCLUDE mplsFecIndexNext
-- EXCLUDE mplsFecTable
-- EXCLUDE mplsLdpAtmGroup
-- EXCLUDE mplsLdpAtmSessionTable
-- EXCLUDE mplsLdpEntityAtmObjects
-- EXCLUDE mplsLdpEntityFrameRelayObjects
-- EXCLUDE mplsLdpEntityGenericObjects
-- EXCLUDE mplsLdpEntityIndexNext
-- EXCLUDE mplsLdpEntityStatsTable
-- EXCLUDE mplsLdpFrameRelayGroup
-- EXCLUDE mplsLdpFrameRelaySessionTable
           mplsLdpGeneralGroup,
           mplsLdpNotificationsGroup
-- EXCLUDE mplsLdpSessionInLabelMapTable
-- EXCLUDE mplsLdpSessionOutLabelMapTable
-- EXCLUDE mplsLdpSessionPeerAddressTable
-- EXCLUDE mplsLdpSessionStatsTable
-- EXCLUDE mplsLdpSessionUpDownTrapEnable
-- EXCLUDE mplsLdpSessionXCMapTable
-- EXCLUDE mplsXCsFecsTable
        }

        VARIATION   mplsFecAddress
            ACCESS  not-implemented
            DESCRIPTION
                 "Not supported."

        VARIATION   mplsFecAddressFamily
            ACCESS  not-implemented
            DESCRIPTION
                 "Not supported."

        VARIATION   mplsFecAddressLength
            ACCESS  not-implemented
            DESCRIPTION
                 "Not supported."

        VARIATION   mplsFecIndexNext
            ACCESS  not-implemented
            DESCRIPTION
                 "Not supported."

        VARIATION   mplsFecRowStatus
            ACCESS  not-implemented
            DESCRIPTION
                 "Not supported."

        VARIATION   mplsFecStorageType
            ACCESS  not-implemented
            DESCRIPTION
                 "Not supported."

        VARIATION   mplsFecType
            ACCESS  not-implemented
            DESCRIPTION
                 "Not supported."

        VARIATION   mplsLdpAttemptedSessions
            ACCESS  not-implemented
            DESCRIPTION
                 "Not supported. It is implemented through
                  vRtrLdpStatsAttemptedSessions in TIMETRA-LDP-MIB."

        VARIATION   mplsLdpBadLdpIdentifierErrors
            ACCESS  not-implemented
            DESCRIPTION
                 "Not supported. It is implemented through
                  vRtrLdpStatsBadLdpIdentifierErrors in TIMETRA-LDP-MIB."

        VARIATION   mplsLdpBadMessageLengthErrors
            ACCESS  not-implemented
            DESCRIPTION
                 "Not supported. It is implemented through
                  vRtrLdpStatsBadMessageLengthErrors in TIMETRA-LDP-MIB."

        VARIATION   mplsLdpBadPduLengthErrors
            ACCESS  not-implemented
            DESCRIPTION
                 "Not supported. It is implemented through
                  vRtrLdpStatsBadPduLengthErrors in TIMETRA-LDP-MIB."

        VARIATION   mplsLdpBadTlvLengthErrors
            ACCESS  not-implemented
            DESCRIPTION
                 "Not supported. It is implemented through
                  vRtrLdpStatsBadTlvLengthErrors in TIMETRA-LDP-MIB."

        VARIATION   mplsLdpEntityAdminStatus
            ACCESS  read-only
            DESCRIPTION
                 "read-only implementation."

        VARIATION   mplsLdpEntityEntry
            CREATION-REQUIRES {
                       vRtrLdpStatus
                    }
            DESCRIPTION
                 "Row entries cannot be created by SNMP SET requests.

                  Row entries in the mplsLdpEntityTable are created by setting
                  TIMETRA-VRTR-MIB::vRtrLdpStatus to 'create'."

        VARIATION   mplsLdpEntityFailedInitSessionThreshold
            ACCESS  read-only
            DESCRIPTION
                 "read-only implementation."

        VARIATION   mplsLdpEntityFailedInitSessionTrapEnable
            ACCESS  read-only
            DESCRIPTION
                 "read-only implementation."

        VARIATION   mplsLdpEntityHelloHoldTimer
            ACCESS  read-only
            DESCRIPTION
                 "read-only implementation."

        VARIATION   mplsLdpEntityHopCountLimit
            ACCESS  read-only
            DESCRIPTION
                 "read-only implementation."

        VARIATION   mplsLdpEntityIndexNext
            ACCESS  not-implemented
            DESCRIPTION
                 "read-only implementation."

        VARIATION   mplsLdpEntityKeepAliveHoldTimer
            ACCESS  read-only
            DESCRIPTION
                 "read-only implementation."

        VARIATION   mplsLdpEntityLabelDistributionMethod
            ACCESS  read-only
            DESCRIPTION
                 "read-only implementation."

        VARIATION   mplsLdpEntityLabelRetentionMode
            ACCESS  read-only
            DESCRIPTION
                 "read-only implementation."

        VARIATION   mplsLdpEntityMaxPduLength
            ACCESS  read-only
            DESCRIPTION
                 "read-only implementation."

        VARIATION   mplsLdpEntityOptionalParameters
            ACCESS  read-only
            DESCRIPTION
                 "read-only implementation."

        VARIATION   mplsLdpEntityPVLimitMismatchTrapEnable
            ACCESS  read-only
            DESCRIPTION
                 "read-only implementation."

        VARIATION   mplsLdpEntityPathVectorLimit
            ACCESS  read-only
            DESCRIPTION
                 "read-only implementation."

        VARIATION   mplsLdpEntityProtocolVersion
            ACCESS  read-only
            DESCRIPTION
                 "read-only implementation."

        VARIATION   mplsLdpEntityRowStatus
            ACCESS  read-only
            DESCRIPTION
                 "read-only implementation. Row entries cannot be created by
                  SNMP SET requests. LDP Entities are created in TIMETRA-LDP-MIB
                  and this table when TIMETRA-VRTR-MIB::vRtrLdpStatus is set to
                  'create'."

        VARIATION   mplsLdpEntityStorageType
            ACCESS  read-only
            DESCRIPTION
                 "read-only implementation."

        VARIATION   mplsLdpEntityTargetedPeer
            ACCESS  read-only
            DESCRIPTION
                 "read-only implementation."

        VARIATION   mplsLdpEntityTargetedPeerAddr
            ACCESS  read-only
            DESCRIPTION
                 "read-only implementation."

        VARIATION   mplsLdpEntityTargetedPeerAddrType
            ACCESS  read-only
            DESCRIPTION
                 "read-only implementation."

        VARIATION   mplsLdpEntityWellKnownTcpDiscoveryPort
            ACCESS  read-only
            DESCRIPTION
                 "read-only implementation."

        VARIATION   mplsLdpEntityWellKnownUdpDiscoveryPort
            ACCESS  read-only
            DESCRIPTION
                 "read-only implementation."

        VARIATION   mplsLdpFailedInitSessionThresholdExceeded
            ACCESS  not-implemented
            DESCRIPTION
                 "Not supported."

        VARIATION   mplsLdpKeepAliveTimerExpiredErrors
            ACCESS  not-implemented
            DESCRIPTION
                 "Not supported. It is implemented through
                  vRtrLdpStatsKeepAliveExpiredErrors in TIMETRA-LDP-MIB."

        VARIATION   mplsLdpMalformedTlvValueErrors
            ACCESS  not-implemented
            DESCRIPTION
                 "Not supported. It is implemented through
                  vRtrLdpStatsMalformedTlvValueErrors in TIMETRA-LDP-MIB."

        VARIATION   mplsLdpPathVectorLimitMismatch
            ACCESS  not-implemented
            DESCRIPTION
                 "Not supported."

        VARIATION   mplsLdpSessionDown
            ACCESS  not-implemented
            DESCRIPTION
                 "Not supported."

        VARIATION   mplsLdpSessionPeerNextHopAddress
            ACCESS  not-implemented
            DESCRIPTION
                 "Not supported."

        VARIATION   mplsLdpSessionPeerNextHopAddressType
            ACCESS  not-implemented
            DESCRIPTION
                 "Not supported."

        VARIATION   mplsLdpSessionRejectedAdvertisementErrors
            ACCESS  not-implemented
            DESCRIPTION
                 "Not supported. It is implemented through
                  vRtrLdpStatsSessRejAdvErrors in TIMETRA-LDP-MIB."

        VARIATION   mplsLdpSessionRejectedLabelRangeErrors
            ACCESS  not-implemented
            DESCRIPTION
                 "Not supported. It is implemented through
                  vRtrLdpStatsSessRejLabelRangeErrors in TIMETRA-LDP-MIB."

        VARIATION   mplsLdpSessionRejectedMaxPduErrors
            ACCESS  not-implemented
            DESCRIPTION
                 "Not supported. It is implemented through
                  vRtrLdpStatsSessRejMaxPduErrors in TIMETRA-LDP-MIB."

        VARIATION   mplsLdpSessionRejectedNoHelloErrors
            ACCESS  not-implemented
            DESCRIPTION
                 "Not supported. It is implemented through
                  vRtrLdpStatsSessRejNoHelloErrors in TIMETRA-LDP-MIB."

        VARIATION   mplsLdpSessionStatsUnknownMessageTypeErrors
            ACCESS  not-implemented
            DESCRIPTION
                 "Not supported."

        VARIATION   mplsLdpSessionStatsUnknownTlvErrors
            ACCESS  not-implemented
            DESCRIPTION
                 "Not supported."

        VARIATION   mplsLdpSessionUp
            ACCESS  not-implemented
            DESCRIPTION
                 "Not supported."

        VARIATION   mplsLdpSessionUpDownTrapEnable
            ACCESS  not-implemented
            DESCRIPTION
                 "generation of MPLS LDP traps is controled by the
                  tmnxEventTable in TIMETRA-LOG-MIB."

        VARIATION   mplsLdpShutdownNotifReceived
            ACCESS  not-implemented
            DESCRIPTION
                 "Not supported. It is implemented through
                  vRtrLdpStatsShutdownNotifRecv in TIMETRA-LDP-MIB."

        VARIATION   mplsLdpShutdownNotifSent
            ACCESS  not-implemented
            DESCRIPTION
                 "Not supported. It is implemented through
                  vRtrLdpStatsShutdownNotifSent in TIMETRA-LDP-MIB."

    SUPPORTS        TIMETRA-LDP-MIB
        INCLUDES {
           tmnxLdpAddrFecV5v0Group,
           tmnxLdpAdjR2r1Group,
           tmnxLdpAggrPreMatchV7v0Group,
           tmnxLdpGlobalV5v0Group,
           tmnxLdpGlobalV8v0Group,
           tmnxLdpIfV5v0Group,
           tmnxLdpNotificationGroup,
           tmnxLdpPeerV7v0Group,
           tmnxLdpServFecV6v0Group,
           tmnxLdpSessionV5v0Group
-- EXCLUDE vRtrLdpAdjBackoffTable
-- EXCLUDE vRtrLdpIfTableSpinlock
-- EXCLUDE vRtrLdpPolicyTable
        }

        VARIATION   vRtrLdpEgrStatFecPfxRowStatus
            DESCRIPTION
                 "vRtrLdpEgrStatFecPfxRowStatus supports only 'ipv4' indices. If
                  an attempt is made to create a row entry with the
                  vRtrLdpEgrStatFecPfxAddrType index set to a value other than
                  'ipv4', a 'noCreation' error will be returned."

        VARIATION   vRtrLdpEgrStatFecPfxTblLastChgd
            ACCESS  not-implemented
            DESCRIPTION
                 "Not supported."

        VARIATION   vRtrLdpGenBackoffTime
            ACCESS  read-only
            DESCRIPTION
                 "read-only implementation."

        VARIATION   vRtrLdpGenHopLimit
            ACCESS  read-only
            DESCRIPTION
                 "read-only implementation."

        VARIATION   vRtrLdpGenLoopDetectCapable
            ACCESS  read-only
            DESCRIPTION
                 "read-only implementation."

        VARIATION   vRtrLdpGenMaxBackoffTime
            ACCESS  read-only
            DESCRIPTION
                 "read-only implementation."

        VARIATION   vRtrLdpGenPathVectorLimit
            ACCESS  read-only
            DESCRIPTION
                 "read-only implementation."

        VARIATION   vRtrLdpGenShortTTLPropLocal
            ACCESS  not-implemented
            DESCRIPTION
                 "Not supported."

        VARIATION   vRtrLdpGenShortTTLPropTransit
            ACCESS  not-implemented
            DESCRIPTION
                 "Not supported."

        VARIATION   vRtrLdpGenTargPassiveMode
            ACCESS  read-only
            DESCRIPTION
                 "read-only implementation."

        VARIATION   vRtrLdpGenTrustList
            ACCESS  not-implemented
            DESCRIPTION
                 "vRtrLdpGenTrustList is not implemented."

        VARIATION   vRtrLdpIfBackoffTime
            ACCESS  read-only
            DESCRIPTION
                 "read-only implementation."

        VARIATION   vRtrLdpIfMaxBackoffTime
            ACCESS  read-only
            DESCRIPTION
                 "read-only implementation."

        VARIATION   vRtrLdpIfPassiveMode
            ACCESS  read-only
            DESCRIPTION
                 "read-only implementation."

        VARIATION   vRtrLdpIfTableSpinlock
            ACCESS  not-implemented
            DESCRIPTION
                 "read-only implementation."

        VARIATION   vRtrLdpPeerTTLLogId
            ACCESS  not-implemented
            DESCRIPTION
                 "vRtrLdpPeerTTLLogId is not implemented."

        VARIATION   vRtrLdpStatsEgrFecPfxCount
            ACCESS  not-implemented
            DESCRIPTION
                 "Not supported."

        VARIATION   vRtrLdpTargExportPolicy1
            ACCESS  not-implemented
            DESCRIPTION
                 "Not supported."

        VARIATION   vRtrLdpTargExportPolicy2
            ACCESS  not-implemented
            DESCRIPTION
                 "Not supported."

        VARIATION   vRtrLdpTargExportPolicy3
            ACCESS  not-implemented
            DESCRIPTION
                 "Not supported."

        VARIATION   vRtrLdpTargExportPolicy4
            ACCESS  not-implemented
            DESCRIPTION
                 "Not supported."

        VARIATION   vRtrLdpTargExportPolicy5
            ACCESS  not-implemented
            DESCRIPTION
                 "Not supported."

        VARIATION   vRtrLdpTargImportPolicy1
            ACCESS  not-implemented
            DESCRIPTION
                 "Not supported."

        VARIATION   vRtrLdpTargImportPolicy2
            ACCESS  not-implemented
            DESCRIPTION
                 "Not supported."

        VARIATION   vRtrLdpTargImportPolicy3
            ACCESS  not-implemented
            DESCRIPTION
                 "Not supported."

        VARIATION   vRtrLdpTargImportPolicy4
            ACCESS  not-implemented
            DESCRIPTION
                 "Not supported."

        VARIATION   vRtrLdpTargImportPolicy5
            ACCESS  not-implemented
            DESCRIPTION
                 "Not supported."

    ::= { tmnxSASMxpAgentV9v0   9 }

--
-- SAS LLDP CAPABILITIES
--
tmnxSASLldpV9v0                   AGENT-CAPABILITIES
    PRODUCT-RELEASE "Alcatel-Lucent SAS"
    STATUS          current
    DESCRIPTION
         "Implementation of LLDP capabilities for Alcatel-Lucent SAS systems
          release 9.0."

    SUPPORTS        LLDP-MIB
        INCLUDES {
           lldpConfigRxGroup,
           lldpConfigTxGroup,
           lldpLocSysGroup,
           lldpNotificationsGroup,
           lldpStatsRxGroup
        }

        VARIATION   lldpConfigManAddrPortsTxEnable
            ACCESS  not-implemented
            DESCRIPTION
                 "lldpConfigManAddrPortsTxEnable has been replaced by
                  TIMETRA-LLDP-MIB::tmnxLldpPortCfgManAddrTxEnabled.

                  lldpConfigManAddrPortsTxEnable has been replaced by
                  TIMETRA-LLDP-MIB::tmnxLldpPortCfgManAddrTxEnabled."

        VARIATION   lldpLocPortDesc
            ACCESS  not-implemented
            DESCRIPTION
                 "lldpLocPortDesc has been replaced by
                  TIMETRA-LLDP-MIB::tmnxLldpLocPortDesc.

                  lldpLocPortDesc has been replaced by
                  TIMETRA-LLDP-MIB::tmnxLldpLocPortDesc."

        VARIATION   lldpLocPortId
            ACCESS  not-implemented
            DESCRIPTION
                 "lldpLocPortId has been replaced by
                  TIMETRA-LLDP-MIB::tmnxLldpLocPortId.

                  lldpLocPortId has been replaced by
                  TIMETRA-LLDP-MIB::tmnxLldpLocPortId."

        VARIATION   lldpLocPortIdSubtype
            ACCESS  not-implemented
            DESCRIPTION
                 "lldpLocPortIdSubtype has been replaced by
                  TIMETRA-LLDP-MIB::tmnxLldpLocPortIdSubtype.

                  lldpLocPortIdSubtype has been replaced by
                  TIMETRA-LLDP-MIB::tmnxLldpLocPortIdSubtype."

        VARIATION   lldpPortConfigNotificationEnable
            ACCESS  not-implemented
            DESCRIPTION
                 "lldpPortConfigNotificationEnable has been replaced by
                  TIMETRA-LLDP-MIB::tmnxLldpPortCfgNotifyEnable.

                  lldpPortConfigNotificationEnable has been replaced by
                  TIMETRA-LLDP-MIB::tmnxLldpPortCfgNotifyEnable."

        VARIATION   lldpPortConfigTLVsTxEnable
            ACCESS  not-implemented
            DESCRIPTION
                 "lldpPortConfigTLVsTxEnable has been replaced by
                  TIMETRA-LLDP-MIB::tmnxLldpPortCfgTLVsTxEnable.

                  lldpPortConfigTLVsTxEnable has been replaced by
                  TIMETRA-LLDP-MIB::tmnxLldpPortCfgTLVsTxEnable."

        VARIATION   lldpStatsRxPortAgeoutsTotal
            ACCESS  not-implemented
            DESCRIPTION
                 "lldpStatsRxPortAgeoutsTotal has been replaced by
                  TIMETRA-LLDP-MIB::tmnxLldpStatsRxPortAgeouts.

                  lldpStatsRxPortAgeoutsTotal has been replaced by
                  TIMETRA-LLDP-MIB::tmnxLldpStatsRxPortAgeouts."

        VARIATION   lldpStatsRxPortFramesDiscardedTotal
            ACCESS  not-implemented
            DESCRIPTION
                 "lldpStatsRxPortFramesDiscardedTotal has been replaced b
                  TIMETRA-LLDP-MIB::tmnxLldpStatsRxPortFrameDiscard.

                  lldpStatsRxPortFramesDiscardedTotal has been replaced b
                  TIMETRA-LLDP-MIB::tmnxLldpStatsRxPortFrameDiscard."

        VARIATION   lldpStatsRxPortFramesErrors
            ACCESS  not-implemented
            DESCRIPTION
                 "lldpStatsRxPortFramesErrors has been replaced by
                  TIMETRA-LLDP-MIB::tmnxLldpStatsRxPortFrameErrs.

                  lldpStatsRxPortFramesErrors has been replaced by
                  TIMETRA-LLDP-MIB::tmnxLldpStatsRxPortFrameErrs."

        VARIATION   lldpStatsRxPortFramesTotal
            ACCESS  not-implemented
            DESCRIPTION
                 "lldpStatsRxPortFramesTotal has been replaced by
                  TIMETRA-LLDP-MIB::tmnxLldpStatsRxPortFrames.

                  lldpStatsRxPortFramesTotal has been replaced by
                  TIMETRA-LLDP-MIB::tmnxLldpStatsRxPortFrames."

        VARIATION   lldpStatsRxPortTLVsDiscardedTotal
            ACCESS  not-implemented
            DESCRIPTION
                 "lldpStatsRxPortTLVsDiscardedTotal has been replaced by
                  TIMETRA-LLDP-MIB::tmnxLldpStatsRxPortTLVDiscard.

                  lldpStatsRxPortTLVsDiscardedTotal has been replaced by
                  TIMETRA-LLDP-MIB::tmnxLldpStatsRxPortTLVDiscard."

        VARIATION   lldpStatsRxPortTLVsUnrecognizedTotal
            ACCESS  not-implemented
            DESCRIPTION
                 "lldpStatsRxPortTLVsUnrecognizedTotal has been replaced with
                  TIMETRA-LLDP-MIB::tmnxLldpStatsRxPortTLVUnknown.

                  lldpStatsRxPortTLVsUnrecognizedTotal has been replaced with
                  TIMETRA-LLDP-MIB::tmnxLldpStatsRxPortTLVUnknown."

        VARIATION   lldpTxDelay
            ACCESS  not-implemented
            DESCRIPTION
                 "lldpTxDelay is not implemented.

                  lldpTxDelay is not implemented."

    SUPPORTS        TIMETRA-LLDP-MIB
        INCLUDES {
           tmnxLldpConfigGroup,
           tmnxLldpLocSysGroup,
           tmnxLldpRemManAddrGroup,
           tmnxLldpRemSysGroup,
           tmnxLldpStatsRxGroup,
           tmnxLldpStatsTxGroup
        }

    ::= { tmnxSASAgentV9v0  28 }

--
-- SAS LLDP CAPABILITIES
--
tmnxSASLldpV9v0                   AGENT-CAPABILITIES
    PRODUCT-RELEASE "Alcatel-Lucent SAS"
    STATUS          current
    DESCRIPTION
         "Implementation of LLDP capabilities for Alcatel-Lucent SAS systems
          release 9.0."

    SUPPORTS        LLDP-MIB
        INCLUDES {
           lldpConfigRxGroup,
           lldpConfigTxGroup,
           lldpLocSysGroup,
           lldpNotificationsGroup,
           lldpStatsRxGroup
        }

        VARIATION   lldpConfigManAddrPortsTxEnable
            ACCESS  not-implemented
            DESCRIPTION
                 "lldpConfigManAddrPortsTxEnable has been replaced by
                  TIMETRA-LLDP-MIB::tmnxLldpPortCfgManAddrTxEnabled.

                  lldpConfigManAddrPortsTxEnable has been replaced by
                  TIMETRA-LLDP-MIB::tmnxLldpPortCfgManAddrTxEnabled."

        VARIATION   lldpLocPortDesc
            ACCESS  not-implemented
            DESCRIPTION
                 "lldpLocPortDesc has been replaced by
                  TIMETRA-LLDP-MIB::tmnxLldpLocPortDesc.

                  lldpLocPortDesc has been replaced by
                  TIMETRA-LLDP-MIB::tmnxLldpLocPortDesc."

        VARIATION   lldpLocPortId
            ACCESS  not-implemented
            DESCRIPTION
                 "lldpLocPortId has been replaced by
                  TIMETRA-LLDP-MIB::tmnxLldpLocPortId.

                  lldpLocPortId has been replaced by
                  TIMETRA-LLDP-MIB::tmnxLldpLocPortId."

        VARIATION   lldpLocPortIdSubtype
            ACCESS  not-implemented
            DESCRIPTION
                 "lldpLocPortIdSubtype has been replaced by
                  TIMETRA-LLDP-MIB::tmnxLldpLocPortIdSubtype.

                  lldpLocPortIdSubtype has been replaced by
                  TIMETRA-LLDP-MIB::tmnxLldpLocPortIdSubtype."

        VARIATION   lldpPortConfigNotificationEnable
            ACCESS  not-implemented
            DESCRIPTION
                 "lldpPortConfigNotificationEnable has been replaced by
                  TIMETRA-LLDP-MIB::tmnxLldpPortCfgNotifyEnable.

                  lldpPortConfigNotificationEnable has been replaced by
                  TIMETRA-LLDP-MIB::tmnxLldpPortCfgNotifyEnable."

        VARIATION   lldpPortConfigTLVsTxEnable
            ACCESS  not-implemented
            DESCRIPTION
                 "lldpPortConfigTLVsTxEnable has been replaced by
                  TIMETRA-LLDP-MIB::tmnxLldpPortCfgTLVsTxEnable.

                  lldpPortConfigTLVsTxEnable has been replaced by
                  TIMETRA-LLDP-MIB::tmnxLldpPortCfgTLVsTxEnable."

        VARIATION   lldpStatsRxPortAgeoutsTotal
            ACCESS  not-implemented
            DESCRIPTION
                 "lldpStatsRxPortAgeoutsTotal has been replaced by
                  TIMETRA-LLDP-MIB::tmnxLldpStatsRxPortAgeouts.

                  lldpStatsRxPortAgeoutsTotal has been replaced by
                  TIMETRA-LLDP-MIB::tmnxLldpStatsRxPortAgeouts."

        VARIATION   lldpStatsRxPortFramesDiscardedTotal
            ACCESS  not-implemented
            DESCRIPTION
                 "lldpStatsRxPortFramesDiscardedTotal has been replaced b
                  TIMETRA-LLDP-MIB::tmnxLldpStatsRxPortFrameDiscard.

                  lldpStatsRxPortFramesDiscardedTotal has been replaced b
                  TIMETRA-LLDP-MIB::tmnxLldpStatsRxPortFrameDiscard."

        VARIATION   lldpStatsRxPortFramesErrors
            ACCESS  not-implemented
            DESCRIPTION
                 "lldpStatsRxPortFramesErrors has been replaced by
                  TIMETRA-LLDP-MIB::tmnxLldpStatsRxPortFrameErrs.

                  lldpStatsRxPortFramesErrors has been replaced by
                  TIMETRA-LLDP-MIB::tmnxLldpStatsRxPortFrameErrs."

        VARIATION   lldpStatsRxPortFramesTotal
            ACCESS  not-implemented
            DESCRIPTION
                 "lldpStatsRxPortFramesTotal has been replaced by
                  TIMETRA-LLDP-MIB::tmnxLldpStatsRxPortFrames.

                  lldpStatsRxPortFramesTotal has been replaced by
                  TIMETRA-LLDP-MIB::tmnxLldpStatsRxPortFrames."

        VARIATION   lldpStatsRxPortTLVsDiscardedTotal
            ACCESS  not-implemented
            DESCRIPTION
                 "lldpStatsRxPortTLVsDiscardedTotal has been replaced by
                  TIMETRA-LLDP-MIB::tmnxLldpStatsRxPortTLVDiscard.

                  lldpStatsRxPortTLVsDiscardedTotal has been replaced by
                  TIMETRA-LLDP-MIB::tmnxLldpStatsRxPortTLVDiscard."

        VARIATION   lldpStatsRxPortTLVsUnrecognizedTotal
            ACCESS  not-implemented
            DESCRIPTION
                 "lldpStatsRxPortTLVsUnrecognizedTotal has been replaced with
                  TIMETRA-LLDP-MIB::tmnxLldpStatsRxPortTLVUnknown.

                  lldpStatsRxPortTLVsUnrecognizedTotal has been replaced with
                  TIMETRA-LLDP-MIB::tmnxLldpStatsRxPortTLVUnknown."

        VARIATION   lldpTxDelay
            ACCESS  not-implemented
            DESCRIPTION
                 "lldpTxDelay is not implemented.

                  lldpTxDelay is not implemented."

    SUPPORTS        TIMETRA-LLDP-MIB
        INCLUDES {
           tmnxLldpConfigGroup,
           tmnxLldpLocSysGroup,
           tmnxLldpRemManAddrGroup,
           tmnxLldpRemSysGroup,
           tmnxLldpStatsRxGroup,
           tmnxLldpStatsTxGroup
        }

    ::= { tmnxSASAgentV9v0  28 }

--
-- SAS LOG CAPABILITIES
--
tmnxSASLogV9v0                    AGENT-CAPABILITIES
    PRODUCT-RELEASE "Alcatel-Lucent SAS"
    STATUS          current
    DESCRIPTION
         "Implementation of event logging capabilities for Alcatel-Lucent SAS
          systems release 9.0."

    SUPPORTS        NOTIFICATION-LOG-MIB
        INCLUDES {
           notificationLogConfigGroup,
           notificationLogDateGroup,
           notificationLogLogGroup,
           notificationLogStatsGroup
        }

        VARIATION   nlmConfigGlobalAgeOut
            ACCESS  read-only
            DESCRIPTION
                 "read-only implementation.

                  read-only implementation."

        VARIATION   nlmConfigGlobalEntryLimit
            ACCESS  read-only
            DESCRIPTION
                 "read-only implementation.

                  read-only implementation."

        VARIATION   nlmConfigLogEntryStatus
            SYNTAX  INTEGER {
                       active               (1)
                    }
            ACCESS  read-only
            DESCRIPTION
                 "read-only implementation. Row entries cannot be created by
                  SNMP SET requests. Notification logs are created using the
                  TIMETRA-LOG-MIB.

                  read-only implementation. Row entries cannot be created by
                  SNMP SET requests. Notification logs are created using the
                  TIMETRA-LOG-MIB."

        VARIATION   nlmConfigLogStorageType
            ACCESS  read-only
            DESCRIPTION
                 "read-only implementation.

                  read-only implementation."

    SUPPORTS        TIMETRA-LOG-MIB
        INCLUDES {
           tmnxLogAccountingPolicyGroup,
           tmnxLogEventsV5v0Group,
           tmnxLogFileIdGroup,
           tmnxLogGlobalGroup,
           tmnxLogNotificationV6v0Group,
           tmnxLogSyslogV5v0Group,
           tmnxLogV5v0Group,
           tmnxSnmpSetErrsGroup,
           tmnxSnmpTrapV5v0Group
        }

    ::= { tmnxSASAgentV9v0  11 }

--
-- SAS LOG CAPABILITIES
--
tmnxSASLogV9v0                    AGENT-CAPABILITIES
    PRODUCT-RELEASE "Alcatel-Lucent SAS"
    STATUS          current
    DESCRIPTION
         "Implementation of event logging capabilities for Alcatel-Lucent SAS
          systems release 9.0."

    SUPPORTS        NOTIFICATION-LOG-MIB
        INCLUDES {
           notificationLogConfigGroup,
           notificationLogDateGroup,
           notificationLogLogGroup,
           notificationLogStatsGroup
        }

        VARIATION   nlmConfigGlobalAgeOut
            ACCESS  read-only
            DESCRIPTION
                 "read-only implementation.

                  read-only implementation."

        VARIATION   nlmConfigGlobalEntryLimit
            ACCESS  read-only
            DESCRIPTION
                 "read-only implementation.

                  read-only implementation."

        VARIATION   nlmConfigLogEntryStatus
            SYNTAX  INTEGER {
                       active               (1)
                    }
            ACCESS  read-only
            DESCRIPTION
                 "read-only implementation. Row entries cannot be created by
                  SNMP SET requests. Notification logs are created using the
                  TIMETRA-LOG-MIB.

                  read-only implementation. Row entries cannot be created by
                  SNMP SET requests. Notification logs are created using the
                  TIMETRA-LOG-MIB."

        VARIATION   nlmConfigLogStorageType
            ACCESS  read-only
            DESCRIPTION
                 "read-only implementation.

                  read-only implementation."

    SUPPORTS        TIMETRA-LOG-MIB
        INCLUDES {
           tmnxLogAccountingPolicyGroup,
           tmnxLogEventsV5v0Group,
           tmnxLogFileIdGroup,
           tmnxLogGlobalGroup,
           tmnxLogNotificationV6v0Group,
           tmnxLogSyslogV5v0Group,
           tmnxLogV5v0Group,
           tmnxSnmpSetErrsGroup,
           tmnxSnmpTrapV5v0Group
        }

    ::= { tmnxSASAgentV9v0  11 }

--
-- SASR MC_REDUNDANCY CAPABILITIES
--
tmnxSASRMcRedundancyV9v0          AGENT-CAPABILITIES
    PRODUCT-RELEASE "Alcatel-Lucent SAS"
    STATUS          current
    DESCRIPTION
         "Implementation of the Multi-Chassis Redundancy feature on
          Alcatel-Lucent SASR systems release 9.0."

    SUPPORTS        TIMETRA-MC-REDUNDANCY-MIB
        INCLUDES {
           tmnxMcL3RingGroup,
           tmnxMcLagPbbGroup,
           tmnxMcPeerEPGroup,
           tmnxMcPeerEPV7v0NotifGroup,
           tmnxMcPeerSyncGroup,
           tmnxMcRedundancySrrpNotifGroup,
           tmnxMcRedundancyV5v0NotifGroup,
           tmnxMcRedundancyV6v0Group,
           tmnxMcRingV6v0Group,
           tmnxMcRingV6v0NotifGroup,
           tmnxMcsDhcpsV6v0Group,
           tmnxMcsSubHostTrkGroup,
           tmnxSrrpNotifV6v1Group,
           tmnxSrrpV5v0Group,
           tmnxSrrpV6v1Group
        }

        VARIATION   tmnxMcEpipeSapRowStatus
            SYNTAX  INTEGER {
                       active               (1),
                       createAndGo          (4),
                       destroy              (6)
                    }
            DESCRIPTION
                 "tmnxMcEpipeSapRowStatus supports only the values 'active (1)',
                  'createAndGo (4)' and 'destroy (6)'."

        VARIATION   tmnxMcLagConfigLagRowStatus
            SYNTAX  INTEGER {
                       active               (1),
                       createAndGo          (4),
                       destroy              (6)
                    }
            DESCRIPTION
                 "tmnxMcLagConfigLagRowStatus supports only the values 'active
                  (1)', 'createAndGo (4)' and 'destroy (6)'."

        VARIATION   tmnxMcLagConfigPeerAdminstate
            SYNTAX  INTEGER {
                    -- noop                 (1)
                       inService            (2),
                       outOfService         (3)
                    }
            DESCRIPTION
                 "The only allowed values for this object are 'inService (2)'
                  and 'outOfService (3)'."

        VARIATION   tmnxMcRingAdminState
            SYNTAX  INTEGER {
                    -- noop                 (1)
                       inService            (2),
                       outOfService         (3)
                    }
            DESCRIPTION
                 "The only allowed values for this object are 'inService (2)'
                  and 'outOfService (3)'."

        VARIATION   tmnxMcRingInbCtrlDestIp
            SYNTAX  InetAddress (SIZE (0|4))
            DESCRIPTION
                 "tmnxMcRingInbCtrlDestIp supports only InetAddressType values
                  'unknown (0)' and 'ipv4 (1)'."

        VARIATION   tmnxMcRingInbCtrlDestIpType
            SYNTAX  INTEGER {
                       unknown              (0),
                       ipv4                 (1)
                    -- ipv6                 (2)
                    -- ipv4z                (3)
                    -- ipv6z                (4)
                    -- dns                  (16)
                    }
            DESCRIPTION
                 "tmnxMcRingInbCtrlDestIpType supports only InetAddressType
                  values 'unknown (0)' and 'ipv4 (1)'."

        VARIATION   tmnxMcRingInfoInbCtrlSrcIp
            SYNTAX  InetAddress (SIZE (0|4))
            DESCRIPTION
                 "tmnxMcRingInfoInbCtrlSrcIp supports only InetAddressType
                  values 'unknown (0)' and 'ipv4 (1)'."

        VARIATION   tmnxMcRingInfoInbCtrlSrcIpType
            SYNTAX  INTEGER {
                       unknown              (0),
                       ipv4                 (1)
                    -- ipv6                 (2)
                    -- ipv4z                (3)
                    -- ipv6z                (4)
                    -- dns                  (16)
                    }
            DESCRIPTION
                 "tmnxMcRingInfoInbCtrlSrcIpType supports only InetAddressType
                  values 'unknown (0)' and 'ipv4 (1)'."

        VARIATION   tmnxMcRingNodeRncvAdminState
            SYNTAX  INTEGER {
                    -- noop                 (1)
                       inService            (2),
                       outOfService         (3)
                    }
            DESCRIPTION
                 "The only allowed values for this object are 'inService (2)'
                  and 'outOfService (3)'."

        VARIATION   tmnxMcRingNodeRncvDestIp
            SYNTAX  InetAddress (SIZE (0|4))
            DESCRIPTION
                 "tmnxMcRingNodeRncvDestIp supports only InetAddressType values
                  'unknown (0)' and 'ipv4 (1)'."

        VARIATION   tmnxMcRingNodeRncvDestIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvDestIpType supports only InetAddressType
                  values 'unknown (0)' and 'ipv4 (1)'."

        VARIATION   tmnxMcRingNodeRncvSrcIp
            SYNTAX  InetAddress (SIZE (0|4))
            DESCRIPTION
                 "tmnxMcRingNodeRncvSrcIp supports only InetAddressType values
                  'unknown (0)' and 'ipv4 (1)'."

        VARIATION   tmnxMcRingNodeRncvSrcIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvSrcIpType supports only InetAddressType
                  values 'unknown (0)' and 'ipv4 (1)'."

        VARIATION   tmnxMcRingNodeRowStatus
            SYNTAX  INTEGER {
                       active               (1),
                       createAndGo          (4),
                       destroy              (6)
                    }
            DESCRIPTION
                 "tmnxMcRingNodeRowStatus supports only the values 'active (1)',
                  'createAndGo (4)' and 'destroy (6)'."

        VARIATION   tmnxMcRingRowStatus
            SYNTAX  INTEGER {
                       active               (1),
                       createAndGo          (4),
                       destroy              (6)
                    }
            DESCRIPTION
                 "tmnxMcRingRowStatus supports only the values 'active (1)',
                  'createAndGo (4)' and 'destroy (6)'."

        VARIATION   tmnxMcTlsCfgDefGwIp
            SYNTAX  InetAddress (SIZE (0|4))
            DESCRIPTION
                 "tmnxMcTlsCfgDefGwIp supports only InetAddressType values
                  'unknown (0)' and 'ipv4 (1)'."

        VARIATION   tmnxMcTlsCfgDefGwIpType
            SYNTAX  INTEGER {
                       unknown              (0),
                       ipv4                 (1)
                    -- ipv6                 (2)
                    -- ipv4z                (3)
                    -- ipv6z                (4)
                    -- dns                  (16)
                    }
            DESCRIPTION
                 "tmnxMcTlsCfgDefGwIpType supports only InetAddressType values
                  'unknown (0)' and 'ipv4 (1)'."

        VARIATION   tmnxSrrpOperRowStatus
            SYNTAX  INTEGER {
                       active               (1),
                       createAndGo          (4),
                       destroy              (6)
                    }
            DESCRIPTION
                 "tmnxSrrpOperRowStatus supports only the values 'active (1)',
                  'createAndGo (4)' and 'destroy (6)'."

    ::= { tmnxSASRAgentV9v0  30 }

--
-- SASX MC_REDUNDANCY CAPABILITIES
--
tmnxSASXMcRedundancyV9v0          AGENT-CAPABILITIES
    PRODUCT-RELEASE "Alcatel-Lucent SAS"
    STATUS          current
    DESCRIPTION
         "Implementation of the Multi-Chassis Redundancy feature on
          Alcatel-Lucent SASX systems release 9.0."

    SUPPORTS        TIMETRA-MC-REDUNDANCY-MIB
        INCLUDES {
           tmnxMcL3RingGroup,
           tmnxMcLagPbbGroup,
           tmnxMcPeerEPGroup,
           tmnxMcPeerEPV7v0NotifGroup,
           tmnxMcPeerSyncGroup,
           tmnxMcRedundancySrrpNotifGroup,
           tmnxMcRedundancyV5v0NotifGroup,
           tmnxMcRedundancyV6v0Group,
           tmnxMcRingV6v0Group,
           tmnxMcRingV6v0NotifGroup,
           tmnxMcsDhcpsV6v0Group,
           tmnxMcsSubHostTrkGroup,
           tmnxSrrpNotifV6v1Group,
           tmnxSrrpV5v0Group,
           tmnxSrrpV6v1Group
        }

        VARIATION   tmnxMcEpipeSapRowStatus
            SYNTAX  INTEGER {
                       active               (1),
                       createAndGo          (4),
                       destroy              (6)
                    }
            DESCRIPTION
                 "tmnxMcEpipeSapRowStatus supports only the values 'active (1)',
                  'createAndGo (4)' and 'destroy (6)'."

        VARIATION   tmnxMcLagConfigLagRowStatus
            SYNTAX  INTEGER {
                       active               (1),
                       createAndGo          (4),
                       destroy              (6)
                    }
            DESCRIPTION
                 "tmnxMcLagConfigLagRowStatus supports only the values 'active
                  (1)', 'createAndGo (4)' and 'destroy (6)'."

        VARIATION   tmnxMcLagConfigPeerAdminstate
            SYNTAX  INTEGER {
                    -- noop                 (1)
                       inService            (2),
                       outOfService         (3)
                    }
            DESCRIPTION
                 "The only allowed values for this object are 'inService (2)'
                  and 'outOfService (3)'."

        VARIATION   tmnxMcRingAdminState
            SYNTAX  INTEGER {
                    -- noop                 (1)
                       inService            (2),
                       outOfService         (3)
                    }
            DESCRIPTION
                 "The only allowed values for this object are 'inService (2)'
                  and 'outOfService (3)'."

        VARIATION   tmnxMcRingInbCtrlDestIp
            SYNTAX  InetAddress (SIZE (0|4))
            DESCRIPTION
                 "tmnxMcRingInbCtrlDestIp supports only InetAddressType values
                  'unknown (0)' and 'ipv4 (1)'."

        VARIATION   tmnxMcRingInbCtrlDestIpType
            SYNTAX  INTEGER {
                       unknown              (0),
                       ipv4                 (1)
                    -- ipv6                 (2)
                    -- ipv4z                (3)
                    -- ipv6z                (4)
                    -- dns                  (16)
                    }
            DESCRIPTION
                 "tmnxMcRingInbCtrlDestIpType supports only InetAddressType
                  values 'unknown (0)' and 'ipv4 (1)'."

        VARIATION   tmnxMcRingInfoInbCtrlSrcIp
            SYNTAX  InetAddress (SIZE (0|4))
            DESCRIPTION
                 "tmnxMcRingInfoInbCtrlSrcIp supports only InetAddressType
                  values 'unknown (0)' and 'ipv4 (1)'."

        VARIATION   tmnxMcRingInfoInbCtrlSrcIpType
            SYNTAX  INTEGER {
                       unknown              (0),
                       ipv4                 (1)
                    -- ipv6                 (2)
                    -- ipv4z                (3)
                    -- ipv6z                (4)
                    -- dns                  (16)
                    }
            DESCRIPTION
                 "tmnxMcRingInfoInbCtrlSrcIpType supports only InetAddressType
                  values 'unknown (0)' and 'ipv4 (1)'."

        VARIATION   tmnxMcRingNodeRncvAdminState
            SYNTAX  INTEGER {
                    -- noop                 (1)
                       inService            (2),
                       outOfService         (3)
                    }
            DESCRIPTION
                 "The only allowed values for this object are 'inService (2)'
                  and 'outOfService (3)'."

        VARIATION   tmnxMcRingNodeRncvDestIp
            SYNTAX  InetAddress (SIZE (0|4))
            DESCRIPTION
                 "tmnxMcRingNodeRncvDestIp supports only InetAddressType values
                  'unknown (0)' and 'ipv4 (1)'."

        VARIATION   tmnxMcRingNodeRncvDestIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvDestIpType supports only InetAddressType
                  values 'unknown (0)' and 'ipv4 (1)'."

        VARIATION   tmnxMcRingNodeRncvSrcIp
            SYNTAX  InetAddress (SIZE (0|4))
            DESCRIPTION
                 "tmnxMcRingNodeRncvSrcIp supports only InetAddressType values
                  'unknown (0)' and 'ipv4 (1)'."

        VARIATION   tmnxMcRingNodeRncvSrcIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvSrcIpType supports only InetAddressType
                  values 'unknown (0)' and 'ipv4 (1)'."

        VARIATION   tmnxMcRingNodeRowStatus
            SYNTAX  INTEGER {
                       active               (1),
                       createAndGo          (4),
                       destroy              (6)
                    }
            DESCRIPTION
                 "tmnxMcRingNodeRowStatus supports only the values 'active (1)',
                  'createAndGo (4)' and 'destroy (6)'."

        VARIATION   tmnxMcRingRowStatus
            SYNTAX  INTEGER {
                       active               (1),
                       createAndGo          (4),
                       destroy              (6)
                    }
            DESCRIPTION
                 "tmnxMcRingRowStatus supports only the values 'active (1)',
                  'createAndGo (4)' and 'destroy (6)'."

        VARIATION   tmnxMcTlsCfgDefGwIp
            SYNTAX  InetAddress (SIZE (0|4))
            DESCRIPTION
                 "tmnxMcTlsCfgDefGwIp supports only InetAddressType values
                  'unknown (0)' and 'ipv4 (1)'."

        VARIATION   tmnxMcTlsCfgDefGwIpType
            SYNTAX  INTEGER {
                       unknown              (0),
                       ipv4                 (1)
                    -- ipv6                 (2)
                    -- ipv4z                (3)
                    -- ipv6z                (4)
                    -- dns                  (16)
                    }
            DESCRIPTION
                 "tmnxMcTlsCfgDefGwIpType supports only InetAddressType values
                  'unknown (0)' and 'ipv4 (1)'."

        VARIATION   tmnxSrrpOperRowStatus
            SYNTAX  INTEGER {
                       active               (1),
                       createAndGo          (4),
                       destroy              (6)
                    }
            DESCRIPTION
                 "tmnxSrrpOperRowStatus supports only the values 'active (1)',
                  'createAndGo (4)' and 'destroy (6)'."

    ::= { tmnxSASXAgentV9v0  30 }

--
-- SASM MC_REDUNDANCY CAPABILITIES
--
tmnxSASMMcRedundancyV9v0          AGENT-CAPABILITIES
    PRODUCT-RELEASE "Alcatel-Lucent SAS"
    STATUS          current
    DESCRIPTION
         "Implementation of the Multi-Chassis Redundancy feature on
          Alcatel-Lucent SASM systems release 9.0."

    SUPPORTS        TIMETRA-MC-REDUNDANCY-MIB
        INCLUDES {
           tmnxMcL3RingGroup,
           tmnxMcLagPbbGroup,
           tmnxMcPeerEPGroup,
           tmnxMcPeerEPV7v0NotifGroup,
           tmnxMcPeerSyncGroup,
           tmnxMcRedundancySrrpNotifGroup,
           tmnxMcRedundancyV5v0NotifGroup,
           tmnxMcRedundancyV6v0Group,
           tmnxMcRingV6v0Group,
           tmnxMcRingV6v0NotifGroup,
           tmnxMcsDhcpsV6v0Group,
           tmnxMcsSubHostTrkGroup,
           tmnxSrrpNotifV6v1Group,
           tmnxSrrpV5v0Group,
           tmnxSrrpV6v1Group
        }

        VARIATION   tmnxMcEpipeSapRowStatus
            SYNTAX  INTEGER {
                       active               (1),
                       createAndGo          (4),
                       destroy              (6)
                    }
            DESCRIPTION
                 "tmnxMcEpipeSapRowStatus supports only the values 'active (1)',
                  'createAndGo (4)' and 'destroy (6)'."

        VARIATION   tmnxMcLagConfigLagRowStatus
            SYNTAX  INTEGER {
                       active               (1),
                       createAndGo          (4),
                       destroy              (6)
                    }
            DESCRIPTION
                 "tmnxMcLagConfigLagRowStatus supports only the values 'active
                  (1)', 'createAndGo (4)' and 'destroy (6)'."

        VARIATION   tmnxMcLagConfigPeerAdminstate
            SYNTAX  INTEGER {
                    -- noop                 (1)
                       inService            (2),
                       outOfService         (3)
                    }
            DESCRIPTION
                 "The only allowed values for this object are 'inService (2)'
                  and 'outOfService (3)'."

        VARIATION   tmnxMcRingAdminState
            SYNTAX  INTEGER {
                    -- noop                 (1)
                       inService            (2),
                       outOfService         (3)
                    }
            DESCRIPTION
                 "The only allowed values for this object are 'inService (2)'
                  and 'outOfService (3)'."

        VARIATION   tmnxMcRingInbCtrlDestIp
            SYNTAX  InetAddress (SIZE (0|4))
            DESCRIPTION
                 "tmnxMcRingInbCtrlDestIp supports only InetAddressType values
                  'unknown (0)' and 'ipv4 (1)'."

        VARIATION   tmnxMcRingInbCtrlDestIpType
            SYNTAX  INTEGER {
                       unknown              (0),
                       ipv4                 (1)
                    -- ipv6                 (2)
                    -- ipv4z                (3)
                    -- ipv6z                (4)
                    -- dns                  (16)
                    }
            DESCRIPTION
                 "tmnxMcRingInbCtrlDestIpType supports only InetAddressType
                  values 'unknown (0)' and 'ipv4 (1)'."

        VARIATION   tmnxMcRingInfoInbCtrlSrcIp
            SYNTAX  InetAddress (SIZE (0|4))
            DESCRIPTION
                 "tmnxMcRingInfoInbCtrlSrcIp supports only InetAddressType
                  values 'unknown (0)' and 'ipv4 (1)'."

        VARIATION   tmnxMcRingInfoInbCtrlSrcIpType
            SYNTAX  INTEGER {
                       unknown              (0),
                       ipv4                 (1)
                    -- ipv6                 (2)
                    -- ipv4z                (3)
                    -- ipv6z                (4)
                    -- dns                  (16)
                    }
            DESCRIPTION
                 "tmnxMcRingInfoInbCtrlSrcIpType supports only InetAddressType
                  values 'unknown (0)' and 'ipv4 (1)'."

        VARIATION   tmnxMcRingNodeRncvAdminState
            SYNTAX  INTEGER {
                    -- noop                 (1)
                       inService            (2),
                       outOfService         (3)
                    }
            DESCRIPTION
                 "The only allowed values for this object are 'inService (2)'
                  and 'outOfService (3)'."

        VARIATION   tmnxMcRingNodeRncvDestIp
            SYNTAX  InetAddress (SIZE (0|4))
            DESCRIPTION
                 "tmnxMcRingNodeRncvDestIp supports only InetAddressType values
                  'unknown (0)' and 'ipv4 (1)'."

        VARIATION   tmnxMcRingNodeRncvDestIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvDestIpType supports only InetAddressType
                  values 'unknown (0)' and 'ipv4 (1)'."

        VARIATION   tmnxMcRingNodeRncvSrcIp
            SYNTAX  InetAddress (SIZE (0|4))
            DESCRIPTION
                 "tmnxMcRingNodeRncvSrcIp supports only InetAddressType values
                  'unknown (0)' and 'ipv4 (1)'."

        VARIATION   tmnxMcRingNodeRncvSrcIpType
            SYNTAX  INTEGER {
                       unknown              (0),
                       ipv4                 (1)
                    -- ipv6                 (2)
                    -- ipv4z                (3)
                    -- ipv6z                (4)
                    -- dns                  (16)
                    }
            DESCRIPTION
                 "tmnxMcRingNodeRncvSrcIpType supports only InetAddressType
                  values 'unknown (0)' and 'ipv4 (1)'."

        VARIATION   tmnxMcRingNodeRowStatus
            SYNTAX  INTEGER {
                       active               (1),
                       createAndGo          (4),
                       destroy              (6)
                    }
            DESCRIPTION
                 "tmnxMcRingNodeRowStatus supports only the values 'active (1)',
                  'createAndGo (4)' and 'destroy (6)'."

        VARIATION   tmnxMcRingRowStatus
            SYNTAX  INTEGER {
                       active               (1),
                       createAndGo          (4),
                       destroy              (6)
                    }
            DESCRIPTION
                 "tmnxMcRingRowStatus supports only the values 'active (1)',
                  'createAndGo (4)' and 'destroy (6)'."

        VARIATION   tmnxMcTlsCfgDefGwIp
            SYNTAX  InetAddress (SIZE (0|4))
            DESCRIPTION
                 "tmnxMcTlsCfgDefGwIp supports only InetAddressType values
                  'unknown (0)' and 'ipv4 (1)'."

        VARIATION   tmnxMcTlsCfgDefGwIpType
            SYNTAX  INTEGER {
                       unknown              (0),
                       ipv4                 (1)
                    -- ipv6                 (2)
                    -- ipv4z                (3)
                    -- ipv6z                (4)
                    -- dns                  (16)
                    }
            DESCRIPTION
                 "tmnxMcTlsCfgDefGwIpType supports only InetAddressType values
                  'unknown (0)' and 'ipv4 (1)'."

        VARIATION   tmnxSrrpOperRowStatus
            SYNTAX  INTEGER {
                       active               (1),
                       createAndGo          (4),
                       destroy              (6)
                    }
            DESCRIPTION
                 "tmnxSrrpOperRowStatus supports only the values 'active (1)',
                  'createAndGo (4)' and 'destroy (6)'."

    ::= { tmnxSASMAgentV9v0  30 }

--
-- SAS MPLS CAPABILITIES
--
tmnxSASMplsV9v0                   AGENT-CAPABILITIES
    PRODUCT-RELEASE "Alcatel-Lucent SAS"
    STATUS          current
    DESCRIPTION
         "Implementation of MPLS protocol capabilities for Alcatel-Lucent SAS
          systems release 9.0."

    SUPPORTS        MPLS-LSR-MIB
        INCLUDES {
           mplsInSegmentGroup,
           mplsInterfaceGroup,
           mplsLsrNotificationGroup,
           mplsOutSegmentGroup,
           mplsTrafficParamGroup,
           mplsXCGroup,
           mplsXCIsNotPersistentGroup,
           mplsXCIsPersistentGroup
        }

        VARIATION   mplsInSegmentDiscards
            ACCESS  not-implemented
            DESCRIPTION
                 "Not supported.

                  Not supported."

        VARIATION   mplsInSegmentOctets
            ACCESS  not-implemented
            DESCRIPTION
                 "Not supported.

                  Not supported."

        VARIATION   mplsOutSegmentDiscards
            ACCESS  not-implemented
            DESCRIPTION
                 "Not supported.

                  Not supported."

        VARIATION   mplsOutSegmentErrors
            ACCESS  not-implemented
            DESCRIPTION
                 "Not supported.

                  Not supported."

        VARIATION   mplsOutSegmentNextHopIpv6Addr
            ACCESS  not-implemented
            DESCRIPTION
                 "Not supported. No IPv6.

                  Not supported. No IPv6."

        VARIATION   mplsOutSegmentOctets
            ACCESS  not-implemented
            DESCRIPTION
                 "Not supported.

                  Not supported."

        VARIATION   mplsTrafficParamMaxBurstSize
            ACCESS  read-only
            DESCRIPTION
                 "read-only implementation.

                  read-only implementation."

        VARIATION   mplsTrafficParamMaxRate
            ACCESS  read-only
            DESCRIPTION
                 "read-only implementation.

                  read-only implementation."

        VARIATION   mplsTrafficParamMeanRate
            ACCESS  read-only
            DESCRIPTION
                 "read-only implementation.

                  read-only implementation."

        VARIATION   mplsTrafficParamRowStatus
            ACCESS  read-only
            DESCRIPTION
                 "read-only implementation.

                  read-only implementation."

        VARIATION   mplsTrafficParamStorageType
            ACCESS  read-only
            DESCRIPTION
                 "read-only implementation.

                  read-only implementation."

        VARIATION   mplsXCLspId
            ACCESS  read-only
            DESCRIPTION
                 "read-only implementation.

                  read-only implementation."

        VARIATION   mplsXCTrapEnable
            ACCESS  not-implemented
            DESCRIPTION
                 "Generation of MPLS traps is controled by the TIMETRA-LOG-MIB
                  tmnxEventTable.

                  Generation of MPLS traps is controled by the TIMETRA-LOG-MIB
                  tmnxEventTable."

    SUPPORTS        MPLS-TE-MIB
        INCLUDES {
           mplsTunnelGroup,
           mplsTunnelIsIntfcGroup,
           mplsTunnelIsNotIntfcGroup,
           mplsTunnelManualGroup,
           mplsTunnelOptionalGroup,
           mplsTunnelSignaledGroup
        }

        VARIATION   mplsTunnelARHopIpv6Addr
            ACCESS  not-implemented
            DESCRIPTION
                 "Not supported. No IPv6 MPLS.

                  Not supported. No IPv6 MPLS."

        VARIATION   mplsTunnelARHopIpv6PrefixLen
            ACCESS  not-implemented
            DESCRIPTION
                 "Not supported. No IPv6 MPLS.

                  Not supported. No IPv6 MPLS."

        VARIATION   mplsTunnelEntry
            CREATION-REQUIRES {
                       mplsTunnelRowStatus,
                       mplsTunnelName
                    }
            DESCRIPTION
                 "mplsTunnelName must be set for row creation to succeed. The
                  value of these objects cannot be changed after the row entry
                  has been created: mplsTunnelDescr, mplsTunnelIsIf,
                  mplsTunnelSignallingProto, mplsTunnelSetupPrio,
                  mplsTunnelHoldingPrio, mplsTunnelOwner,
                  mplsTunnelLocalProtectInUse, mplsTunnelResourcePointer,
                  mplsTunnelSessionAttributes, mplsTunnelInstancePriority.

                  mplsTunnelName must be set for row creation to succeed. The
                  value of these objects cannot be changed after the row entry
                  has been created: mplsTunnelDescr, mplsTunnelIsIf,
                  mplsTunnelSignallingProto, mplsTunnelSetupPrio,
                  mplsTunnelHoldingPrio, mplsTunnelOwner,
                  mplsTunnelLocalProtectInUse, mplsTunnelResourcePointer,
                  mplsTunnelSessionAttributes, mplsTunnelInstancePriority."

        VARIATION   mplsTunnelHoldingPrio
            ACCESS  read-only
            DESCRIPTION
                 "read-only implementation.

                  read-only implementation."

        VARIATION   mplsTunnelHopAsNumber
            ACCESS  not-implemented
            DESCRIPTION
                 "Not supported.

                  Not supported."

        VARIATION   mplsTunnelHopIpv6Addr
            ACCESS  not-implemented
            DESCRIPTION
                 "Not supported. No IPv6 MPLS.

                  Not supported. No IPv6 MPLS."

        VARIATION   mplsTunnelHopIpv6PrefixLen
            ACCESS  not-implemented
            DESCRIPTION
                 "Not supported. No IPv6 MPLS.

                  Not supported. No IPv6 MPLS."

        VARIATION   mplsTunnelHopLspId
            ACCESS  not-implemented
            DESCRIPTION
                 "Not supported.

                  Not supported."

        VARIATION   mplsTunnelHopTableIndex
            ACCESS  read-only
            DESCRIPTION
                 "read-only implementation. The value of mplsTunnelHopTableIndex
                  is the same as mplsTunnelIndex.

                  read-only implementation. The value of
                  mplsTunnelHopTableIndex is the same as mplsTunnelIndex."

        VARIATION   mplsTunnelInstancePriority
            ACCESS  read-only
            DESCRIPTION
                 "read-only implementation.

                  read-only implementation."

        VARIATION   mplsTunnelIsIf
            ACCESS  read-only
            DESCRIPTION
                 "read-only implementation.

                  read-only implementation."

        VARIATION   mplsTunnelLocalProtectInUse
            ACCESS  read-only
            DESCRIPTION
                 "read-only implementation.

                  read-only implementation."

        VARIATION   mplsTunnelName
            SYNTAX  DisplayString (SIZE(0..32))
            DESCRIPTION
                 "The maximum length supported for the mplsTunnelName is 32
                  characters.

                  The maximum length supported for the mplsTunnelName is 32
                  characters."

        VARIATION   mplsTunnelOwner
            ACCESS  read-only
            DESCRIPTION
                 "read-only implementation.

                  read-only implementation."

        VARIATION   mplsTunnelResourceIndexNext
            ACCESS  not-implemented
            DESCRIPTION
                 "Not supported.

                  Not supported."

        VARIATION   mplsTunnelResourceMaxBurstSize
            ACCESS  not-implemented
            DESCRIPTION
                 "Not supported.

                  Not supported."

        VARIATION   mplsTunnelResourceMaxRate
            ACCESS  not-implemented
            DESCRIPTION
                 "Not supported.

                  Not supported."

        VARIATION   mplsTunnelResourceMeanRate
            ACCESS  not-implemented
            DESCRIPTION
                 "Not supported.

                  Not supported."

        VARIATION   mplsTunnelResourcePointer
            ACCESS  read-only
            DESCRIPTION
                 "mplsTunnelResourceTable is not implemented and
                  mplsTunnelResourcePointer always returns the null identifier
                  value { ccitt 0 }.

                  mplsTunnelResourceTable is not implemented and
                  mplsTunnelResourcePointer always returns the null identifier
                  value { ccitt 0 }."

        VARIATION   mplsTunnelResourceRowStatus
            ACCESS  not-implemented
            DESCRIPTION
                 "Not supported.

                  Not supported."

        VARIATION   mplsTunnelResourceStorageType
            ACCESS  not-implemented
            DESCRIPTION
                 "Not supported.

                  Not supported."

        VARIATION   mplsTunnelRowStatus
            SYNTAX  INTEGER {
                       active               (1),
                       createAndGo          (4),
                       destroy              (6)
                    }
            DESCRIPTION
                 "mplsTunnelRowStatus supports only the values 'active (1)',
                  'createAndGo (4)' and 'destroy (6)'.

                  mplsTunnelRowStatus supports only the values 'active (1)',
                  'createAndGo (4)' and 'destroy (6)'."

        VARIATION   mplsTunnelSessionAttributes
            ACCESS  read-only
            DESCRIPTION
                 "read-only implementation.

                  read-only implementation."

        VARIATION   mplsTunnelSetupPrio
            ACCESS  read-only
            DESCRIPTION
                 "read-only implementation.

                  read-only implementation."

        VARIATION   mplsTunnelSignallingProto
            ACCESS  read-only
            DESCRIPTION
                 "read-only implementation.

                  read-only implementation."

        VARIATION   mplsTunnelTrapEnable
            ACCESS  not-implemented
            DESCRIPTION
                 "Not supported. Control of MPLS traps is managed using the
                  tmnxEventTable in the TIMETRA-LOG-MIB.

                  Not supported. Control of MPLS traps is managed using the
                  tmnxEventTable in the TIMETRA-LOG-MIB."

    SUPPORTS        TIMETRA-MPLS-MIB
        INCLUDES {
           tmnxMplsAdminGroupGroup,
           tmnxMplsGlobalV6v0Group,
           tmnxMplsGlobalV7v0Group,
           tmnxMplsIfGroup,
           tmnxMplsIfV6v0Group,
           tmnxMplsLabelRangeGroup,
           tmnxMplsLspPathV6v1Group,
           tmnxMplsLspPathV7v0Group,
           tmnxMplsLspV5v0Group,
           tmnxMplsLspV6v0Group,
           tmnxMplsLspV7v0Group,
           tmnxMplsNotificationR2r1Group,
           tmnxMplsNotificationV7v0Group,
           tmnxMplsTunnelARHopGroup,
           tmnxMplsTunnelCHopGroup,
           tmnxMplsXCGroup
        }

        VARIATION   vRtrMplsGenLeastFillReoptiThd
            ACCESS  not-implemented
            DESCRIPTION
                 "Not supported.

                  Not supported."

        VARIATION   vRtrMplsGeneralLeastFillMinThd
            ACCESS  not-implemented
            DESCRIPTION
                 "Not supported.

                  Not supported."

        VARIATION   vRtrMplsGeneralNewP2mpInstIndex
            ACCESS  not-implemented
            DESCRIPTION
                 "Not supported.

                  Not supported.

                  Not supported.

                  Not supported."

        VARIATION   vRtrMplsGeneralOptimizeTimer
            ACCESS  read-only
            DESCRIPTION
                 "read-only implementation.

                  read-only implementation."

        VARIATION   vRtrMplsGeneralP2mpNextResignal
            ACCESS  not-implemented
            DESCRIPTION
                 "Not supported.

                  Not supported.

                  Not supported.

                  Not supported."

        VARIATION   vRtrMplsGeneralP2mpResigTimer
            ACCESS  not-implemented
            DESCRIPTION
                 "Not supported.

                  Not supported.

                  Not supported.

                  Not supported."

        VARIATION   vRtrMplsGeneralPropagateTtl
            ACCESS  read-only
            DESCRIPTION
                 "read-only implementation.

                  read-only implementation."

        VARIATION   vRtrMplsGeneralS2lOriginate
            ACCESS  not-implemented
            DESCRIPTION
                 "Not supported.

                  Not supported.

                  Not supported.

                  Not supported."

        VARIATION   vRtrMplsGeneralS2lTerminate
            ACCESS  not-implemented
            DESCRIPTION
                 "Not supported.

                  Not supported.

                  Not supported.

                  Not supported."

        VARIATION   vRtrMplsGeneralS2lTransit
            ACCESS  not-implemented
            DESCRIPTION
                 "Not supported.

                  Not supported.

                  Not supported.

                  Not supported."

        VARIATION   vRtrMplsGeneralTE
            ACCESS  read-only
            DESCRIPTION
                 "read-only implementation.

                  read-only implementation."

        VARIATION   vRtrMplsInSegmentNumS2ls
            ACCESS  not-implemented
            DESCRIPTION
                 "Not supported.

                  Not supported.

                  Not supported.

                  Not supported."

        VARIATION   vRtrMplsLspBandwidth
            ACCESS  read-only
            DESCRIPTION
                 "read-only implementation.

                  read-only implementation."

        VARIATION   vRtrMplsLspBwProtect
            ACCESS  read-only
            DESCRIPTION
                 "read-only implementation.

                  read-only implementation."

        VARIATION   vRtrMplsLspClassOfService
            ACCESS  read-only
            DESCRIPTION
                 "read-only implementation.

                  read-only implementation."

        VARIATION   vRtrMplsLspClassType
            ACCESS  not-implemented
            DESCRIPTION
                 "Not supported.

                  Not supported."

        VARIATION   vRtrMplsLspConfP2mpInstances
            ACCESS  not-implemented
            DESCRIPTION
                 "Not supported.

                  Not supported.

                  Not supported.

                  Not supported."

        VARIATION   vRtrMplsLspDecrementTtl
            ACCESS  read-only
            DESCRIPTION
                 "read-only implementation.

                  read-only implementation."

        VARIATION   vRtrMplsLspFRObject
            ACCESS  read-only
            DESCRIPTION
                 "read-only implementation.

                  read-only implementation."

        VARIATION   vRtrMplsLspHoldPriority
            ACCESS  read-only
            DESCRIPTION
                 "read-only implementation.

                  read-only implementation."

        VARIATION   vRtrMplsLspLeastFill
            ACCESS  not-implemented
            DESCRIPTION
                 "Not supported.

                  Not supported."

        VARIATION   vRtrMplsLspOctets
            ACCESS  not-implemented
            DESCRIPTION
                 "Not supported.

                  Not supported."

        VARIATION   vRtrMplsLspOptimizeTimer
            ACCESS  read-only
            DESCRIPTION
                 "read-only implementation.

                  read-only implementation."

        VARIATION   vRtrMplsLspP2mpId
            ACCESS  not-implemented
            DESCRIPTION
                 "Not supported.

                  Not supported.

                  Not supported.

                  Not supported."

        VARIATION   vRtrMplsLspPackets
            ACCESS  not-implemented
            DESCRIPTION
                 "Not supported.

                  Not supported."

        VARIATION   vRtrMplsLspPathBwProtect
            ACCESS  read-only
            DESCRIPTION
                 "read-only implementation.

                  read-only implementation."

        VARIATION   vRtrMplsLspPathClassOfService
            ACCESS  read-only
            DESCRIPTION
                 "read-only implementation.

                  read-only implementation."

        VARIATION   vRtrMplsLspPathClassType
            ACCESS  not-implemented
            DESCRIPTION
                 "Not supported.

                  Not supported."

        VARIATION   vRtrMplsLspPathCos
            ACCESS  read-only
            DESCRIPTION
                 "read-only implementation.

                  read-only implementation."

        VARIATION   vRtrMplsLspPathCosSource
            ACCESS  read-only
            DESCRIPTION
                 "read-only implementation.

                  read-only implementation."

        VARIATION   vRtrMplsLspPathOptimizeTimer
            ACCESS  read-only
            DESCRIPTION
                 "read-only implementation.

                  read-only implementation."

        VARIATION   vRtrMplsLspPathPreference
            ACCESS  read-only
            DESCRIPTION
                 "read-only implementation.

                  read-only implementation."

        VARIATION   vRtrMplsLspPathSharing
            ACCESS  read-only
            DESCRIPTION
                 "read-only implementation.

                  read-only implementation."

        VARIATION   vRtrMplsLspPathTableSpinlock
            ACCESS  not-implemented
            DESCRIPTION
                 "vRtrMplsLspPathTableSpinlock was intended to be used for
                  control of changes to inherited attributes. There are no
                  inherited attributes in the base version of MPLS on Nokia
                  SAS-R 7210 systems.

                  vRtrMplsLspPathTableSpinlock was intended to be used for
                  control of changes to inherited attributes. There are no
                  inherited attributes in the base version of MPLS on Nokia
                  SAS-R 7210 systems."

        VARIATION   vRtrMplsLspPreference
            ACCESS  read-only
            DESCRIPTION
                 "read-only implementation.

                  read-only implementation."

        VARIATION   vRtrMplsLspRecord
            ACCESS  read-only
            DESCRIPTION
                 "read-only implementation.

                  read-only implementation."

        VARIATION   vRtrMplsLspSetupPriority
            ACCESS  read-only
            DESCRIPTION
                 "read-only implementation.

                  read-only implementation."

        VARIATION   vRtrMplsLspTemplateAdaptive
            ACCESS  not-implemented
            DESCRIPTION
                 "Not supported.

                  Not supported."

        VARIATION   vRtrMplsLspTemplateAdmGrpExcl
            ACCESS  not-implemented
            DESCRIPTION
                 "Not supported.

                  Not supported."

        VARIATION   vRtrMplsLspTemplateAdmGrpIncl
            ACCESS  not-implemented
            DESCRIPTION
                 "Not supported.

                  Not supported."

        VARIATION   vRtrMplsLspTemplateAdminState
            ACCESS  not-implemented
            DESCRIPTION
                 "Not supported.

                  Not supported."

        VARIATION   vRtrMplsLspTemplateBandwidth
            ACCESS  not-implemented
            DESCRIPTION
                 "Not supported.

                  Not supported."

        VARIATION   vRtrMplsLspTemplateCspf
            ACCESS  not-implemented
            DESCRIPTION
                 "Not supported.

                  Not supported."

        VARIATION   vRtrMplsLspTemplateCspfTeMetric
            ACCESS  not-implemented
            DESCRIPTION
                 "Not supported.

                  Not supported."

        VARIATION   vRtrMplsLspTemplateDefaultPath
            ACCESS  not-implemented
            DESCRIPTION
                 "Not supported.

                  Not supported."

        VARIATION   vRtrMplsLspTemplateFRHopLimit
            ACCESS  not-implemented
            DESCRIPTION
                 "Not supported.

                  Not supported."

        VARIATION   vRtrMplsLspTemplateFRMethod
            ACCESS  not-implemented
            DESCRIPTION
                 "Not supported.

                  Not supported."

        VARIATION   vRtrMplsLspTemplateFastReroute
            ACCESS  not-implemented
            DESCRIPTION
                 "Not supported.

                  Not supported."

        VARIATION   vRtrMplsLspTemplateHopLimit
            ACCESS  not-implemented
            DESCRIPTION
                 "Not supported.

                  Not supported."

        VARIATION   vRtrMplsLspTemplateLastChanged
            ACCESS  not-implemented
            DESCRIPTION
                 "Not supported.

                  Not supported."

        VARIATION   vRtrMplsLspTemplateLspCount
            ACCESS  not-implemented
            DESCRIPTION
                 "Not supported.

                  Not supported."

        VARIATION   vRtrMplsLspTemplateMvpnRefCount
            ACCESS  not-implemented
            DESCRIPTION
                 "Not supported.

                  Not supported."

        VARIATION   vRtrMplsLspTemplateName
            ACCESS  not-implemented
            DESCRIPTION
                 "Not supported.

                  Not supported."

        VARIATION   vRtrMplsLspTemplateRecord
            ACCESS  not-implemented
            DESCRIPTION
                 "Not supported.

                  Not supported."

        VARIATION   vRtrMplsLspTemplateRecordLabel
            ACCESS  not-implemented
            DESCRIPTION
                 "Not supported.

                  Not supported."

        VARIATION   vRtrMplsLspTemplateRetryLimit
            ACCESS  not-implemented
            DESCRIPTION
                 "Not supported.

                  Not supported."

        VARIATION   vRtrMplsLspTemplateRetryTimer
            ACCESS  not-implemented
            DESCRIPTION
                 "Not supported.

                  Not supported."

        VARIATION   vRtrMplsLspTemplateRowStatus
            ACCESS  not-implemented
            DESCRIPTION
                 "Not supported.

                  Not supported."

        VARIATION   vRtrMplsLspTemplateType
            ACCESS  not-implemented
            DESCRIPTION
                 "Not supported.

                  Not supported."

        VARIATION   vRtrMplsOutSegmentNumS2ls
            ACCESS  not-implemented
            DESCRIPTION
                 "Not supported.

                  Not supported.

                  Not supported.

                  Not supported."

    ::= { tmnxSASAgentV9v0  10 }

--
-- SAS MPLS CAPABILITIES
--
tmnxSASMplsV9v0                   AGENT-CAPABILITIES
    PRODUCT-RELEASE "Alcatel-Lucent SAS"
    STATUS          current
    DESCRIPTION
         "Implementation of MPLS protocol capabilities for Alcatel-Lucent SAS
          systems release 9.0."

    SUPPORTS        MPLS-LSR-MIB
        INCLUDES {
           mplsInSegmentGroup,
           mplsInterfaceGroup,
           mplsLsrNotificationGroup,
           mplsOutSegmentGroup,
           mplsTrafficParamGroup,
           mplsXCGroup,
           mplsXCIsNotPersistentGroup,
           mplsXCIsPersistentGroup
        }

        VARIATION   mplsInSegmentDiscards
            ACCESS  not-implemented
            DESCRIPTION
                 "Not supported.

                  Not supported."

        VARIATION   mplsInSegmentOctets
            ACCESS  not-implemented
            DESCRIPTION
                 "Not supported.

                  Not supported."

        VARIATION   mplsOutSegmentDiscards
            ACCESS  not-implemented
            DESCRIPTION
                 "Not supported.

                  Not supported."

        VARIATION   mplsOutSegmentErrors
            ACCESS  not-implemented
            DESCRIPTION
                 "Not supported.

                  Not supported."

        VARIATION   mplsOutSegmentNextHopIpv6Addr
            ACCESS  not-implemented
            DESCRIPTION
                 "Not supported. No IPv6.

                  Not supported. No IPv6."

        VARIATION   mplsOutSegmentOctets
            ACCESS  not-implemented
            DESCRIPTION
                 "Not supported.

                  Not supported."

        VARIATION   mplsTrafficParamMaxBurstSize
            ACCESS  read-only
            DESCRIPTION
                 "read-only implementation.

                  read-only implementation."

        VARIATION   mplsTrafficParamMaxRate
            ACCESS  read-only
            DESCRIPTION
                 "read-only implementation.

                  read-only implementation."

        VARIATION   mplsTrafficParamMeanRate
            ACCESS  read-only
            DESCRIPTION
                 "read-only implementation.

                  read-only implementation."

        VARIATION   mplsTrafficParamRowStatus
            ACCESS  read-only
            DESCRIPTION
                 "read-only implementation.

                  read-only implementation."

        VARIATION   mplsTrafficParamStorageType
            ACCESS  read-only
            DESCRIPTION
                 "read-only implementation.

                  read-only implementation."

        VARIATION   mplsXCLspId
            ACCESS  read-only
            DESCRIPTION
                 "read-only implementation.

                  read-only implementation."

        VARIATION   mplsXCTrapEnable
            ACCESS  not-implemented
            DESCRIPTION
                 "Generation of MPLS traps is controled by the TIMETRA-LOG-MIB
                  tmnxEventTable.

                  Generation of MPLS traps is controled by the TIMETRA-LOG-MIB
                  tmnxEventTable."

    SUPPORTS        MPLS-TE-MIB
        INCLUDES {
           mplsTunnelGroup,
           mplsTunnelIsIntfcGroup,
           mplsTunnelIsNotIntfcGroup,
           mplsTunnelManualGroup,
           mplsTunnelOptionalGroup,
           mplsTunnelSignaledGroup
        }

        VARIATION   mplsTunnelARHopIpv6Addr
            ACCESS  not-implemented
            DESCRIPTION
                 "Not supported. No IPv6 MPLS.

                  Not supported. No IPv6 MPLS."

        VARIATION   mplsTunnelARHopIpv6PrefixLen
            ACCESS  not-implemented
            DESCRIPTION
                 "Not supported. No IPv6 MPLS.

                  Not supported. No IPv6 MPLS."

        VARIATION   mplsTunnelEntry
            CREATION-REQUIRES {
                       mplsTunnelRowStatus,
                       mplsTunnelName
                    }
            DESCRIPTION
                 "mplsTunnelName must be set for row creation to succeed. The
                  value of these objects cannot be changed after the row entry
                  has been created: mplsTunnelDescr, mplsTunnelIsIf,
                  mplsTunnelSignallingProto, mplsTunnelSetupPrio,
                  mplsTunnelHoldingPrio, mplsTunnelOwner,
                  mplsTunnelLocalProtectInUse, mplsTunnelResourcePointer,
                  mplsTunnelSessionAttributes, mplsTunnelInstancePriority.

                  mplsTunnelName must be set for row creation to succeed. The
                  value of these objects cannot be changed after the row entry
                  has been created: mplsTunnelDescr, mplsTunnelIsIf,
                  mplsTunnelSignallingProto, mplsTunnelSetupPrio,
                  mplsTunnelHoldingPrio, mplsTunnelOwner,
                  mplsTunnelLocalProtectInUse, mplsTunnelResourcePointer,
                  mplsTunnelSessionAttributes, mplsTunnelInstancePriority."

        VARIATION   mplsTunnelHoldingPrio
            ACCESS  read-only
            DESCRIPTION
                 "read-only implementation.

                  read-only implementation."

        VARIATION   mplsTunnelHopAsNumber
            ACCESS  not-implemented
            DESCRIPTION
                 "Not supported.

                  Not supported."

        VARIATION   mplsTunnelHopIpv6Addr
            ACCESS  not-implemented
            DESCRIPTION
                 "Not supported. No IPv6 MPLS.

                  Not supported. No IPv6 MPLS."

        VARIATION   mplsTunnelHopIpv6PrefixLen
            ACCESS  not-implemented
            DESCRIPTION
                 "Not supported. No IPv6 MPLS.

                  Not supported. No IPv6 MPLS."

        VARIATION   mplsTunnelHopLspId
            ACCESS  not-implemented
            DESCRIPTION
                 "Not supported.

                  Not supported."

        VARIATION   mplsTunnelHopTableIndex
            ACCESS  read-only
            DESCRIPTION
                 "read-only implementation. The value of mplsTunnelHopTableIndex
                  is the same as mplsTunnelIndex.

                  read-only implementation. The value of
                  mplsTunnelHopTableIndex is the same as mplsTunnelIndex."

        VARIATION   mplsTunnelInstancePriority
            ACCESS  read-only
            DESCRIPTION
                 "read-only implementation.

                  read-only implementation."

        VARIATION   mplsTunnelIsIf
            ACCESS  read-only
            DESCRIPTION
                 "read-only implementation.

                  read-only implementation."

        VARIATION   mplsTunnelLocalProtectInUse
            ACCESS  read-only
            DESCRIPTION
                 "read-only implementation.

                  read-only implementation."

        VARIATION   mplsTunnelName
            SYNTAX  DisplayString (SIZE(0..32))
            DESCRIPTION
                 "The maximum length supported for the mplsTunnelName is 32
                  characters.

                  The maximum length supported for the mplsTunnelName is 32
                  characters."

        VARIATION   mplsTunnelOwner
            ACCESS  read-only
            DESCRIPTION
                 "read-only implementation.

                  read-only implementation."

        VARIATION   mplsTunnelResourceIndexNext
            ACCESS  not-implemented
            DESCRIPTION
                 "Not supported.

                  Not supported."

        VARIATION   mplsTunnelResourceMaxBurstSize
            ACCESS  not-implemented
            DESCRIPTION
                 "Not supported.

                  Not supported."

        VARIATION   mplsTunnelResourceMaxRate
            ACCESS  not-implemented
            DESCRIPTION
                 "Not supported.

                  Not supported."

        VARIATION   mplsTunnelResourceMeanRate
            ACCESS  not-implemented
            DESCRIPTION
                 "Not supported.

                  Not supported."

        VARIATION   mplsTunnelResourcePointer
            ACCESS  read-only
            DESCRIPTION
                 "mplsTunnelResourceTable is not implemented and
                  mplsTunnelResourcePointer always returns the null identifier
                  value { ccitt 0 }.

                  mplsTunnelResourceTable is not implemented and
                  mplsTunnelResourcePointer always returns the null identifier
                  value { ccitt 0 }."

        VARIATION   mplsTunnelResourceRowStatus
            ACCESS  not-implemented
            DESCRIPTION
                 "Not supported.

                  Not supported."

        VARIATION   mplsTunnelResourceStorageType
            ACCESS  not-implemented
            DESCRIPTION
                 "Not supported.

                  Not supported."

        VARIATION   mplsTunnelRowStatus
            SYNTAX  INTEGER {
                       active               (1),
                       createAndGo          (4),
                       destroy              (6)
                    }
            DESCRIPTION
                 "mplsTunnelRowStatus supports only the values 'active (1)',
                  'createAndGo (4)' and 'destroy (6)'.

                  mplsTunnelRowStatus supports only the values 'active (1)',
                  'createAndGo (4)' and 'destroy (6)'."

        VARIATION   mplsTunnelSessionAttributes
            ACCESS  read-only
            DESCRIPTION
                 "read-only implementation.

                  read-only implementation."

        VARIATION   mplsTunnelSetupPrio
            ACCESS  read-only
            DESCRIPTION
                 "read-only implementation.

                  read-only implementation."

        VARIATION   mplsTunnelSignallingProto
            ACCESS  read-only
            DESCRIPTION
                 "read-only implementation.

                  read-only implementation."

        VARIATION   mplsTunnelTrapEnable
            ACCESS  not-implemented
            DESCRIPTION
                 "Not supported. Control of MPLS traps is managed using the
                  tmnxEventTable in the TIMETRA-LOG-MIB.

                  Not supported. Control of MPLS traps is managed using the
                  tmnxEventTable in the TIMETRA-LOG-MIB."

    SUPPORTS        TIMETRA-MPLS-MIB
        INCLUDES {
           tmnxMplsAdminGroupGroup,
           tmnxMplsGlobalV6v0Group,
           tmnxMplsGlobalV7v0Group,
           tmnxMplsIfGroup,
           tmnxMplsIfV6v0Group,
           tmnxMplsLabelRangeGroup,
           tmnxMplsLspPathV6v1Group,
           tmnxMplsLspPathV7v0Group,
           tmnxMplsLspV5v0Group,
           tmnxMplsLspV6v0Group,
           tmnxMplsLspV7v0Group,
           tmnxMplsNotificationR2r1Group,
           tmnxMplsNotificationV7v0Group,
           tmnxMplsTunnelARHopGroup,
           tmnxMplsTunnelCHopGroup,
           tmnxMplsXCGroup
        }

        VARIATION   vRtrMplsGenLeastFillReoptiThd
            ACCESS  not-implemented
            DESCRIPTION
                 "Not supported.

                  Not supported."

        VARIATION   vRtrMplsGeneralLeastFillMinThd
            ACCESS  not-implemented
            DESCRIPTION
                 "Not supported.

                  Not supported."

        VARIATION   vRtrMplsGeneralNewP2mpInstIndex
            ACCESS  not-implemented
            DESCRIPTION
                 "Not supported.

                  Not supported.

                  Not supported.

                  Not supported."

        VARIATION   vRtrMplsGeneralOptimizeTimer
            ACCESS  read-only
            DESCRIPTION
                 "read-only implementation.

                  read-only implementation."

        VARIATION   vRtrMplsGeneralP2mpNextResignal
            ACCESS  not-implemented
            DESCRIPTION
                 "Not supported.

                  Not supported.

                  Not supported.

                  Not supported."

        VARIATION   vRtrMplsGeneralP2mpResigTimer
            ACCESS  not-implemented
            DESCRIPTION
                 "Not supported.

                  Not supported.

                  Not supported.

                  Not supported."

        VARIATION   vRtrMplsGeneralPropagateTtl
            ACCESS  read-only
            DESCRIPTION
                 "read-only implementation.

                  read-only implementation."

        VARIATION   vRtrMplsGeneralS2lOriginate
            ACCESS  not-implemented
            DESCRIPTION
                 "Not supported.

                  Not supported.

                  Not supported.

                  Not supported."

        VARIATION   vRtrMplsGeneralS2lTerminate
            ACCESS  not-implemented
            DESCRIPTION
                 "Not supported.

                  Not supported.

                  Not supported.

                  Not supported."

        VARIATION   vRtrMplsGeneralS2lTransit
            ACCESS  not-implemented
            DESCRIPTION
                 "Not supported.

                  Not supported.

                  Not supported.

                  Not supported."

        VARIATION   vRtrMplsGeneralTE
            ACCESS  read-only
            DESCRIPTION
                 "read-only implementation.

                  read-only implementation."

        VARIATION   vRtrMplsInSegmentNumS2ls
            ACCESS  not-implemented
            DESCRIPTION
                 "Not supported.

                  Not supported.

                  Not supported.

                  Not supported."

        VARIATION   vRtrMplsLspBandwidth
            ACCESS  read-only
            DESCRIPTION
                 "read-only implementation.

                  read-only implementation."

        VARIATION   vRtrMplsLspBwProtect
            ACCESS  read-only
            DESCRIPTION
                 "read-only implementation.

                  read-only implementation."

        VARIATION   vRtrMplsLspClassOfService
            ACCESS  read-only
            DESCRIPTION
                 "read-only implementation.

                  read-only implementation."

        VARIATION   vRtrMplsLspClassType
            ACCESS  not-implemented
            DESCRIPTION
                 "Not supported.

                  Not supported."

        VARIATION   vRtrMplsLspConfP2mpInstances
            ACCESS  not-implemented
            DESCRIPTION
                 "Not supported.

                  Not supported.

                  Not supported.

                  Not supported."

        VARIATION   vRtrMplsLspDecrementTtl
            ACCESS  read-only
            DESCRIPTION
                 "read-only implementation.

                  read-only implementation."

        VARIATION   vRtrMplsLspFRObject
            ACCESS  read-only
            DESCRIPTION
                 "read-only implementation.

                  read-only implementation."

        VARIATION   vRtrMplsLspHoldPriority
            ACCESS  read-only
            DESCRIPTION
                 "read-only implementation.

                  read-only implementation."

        VARIATION   vRtrMplsLspLeastFill
            ACCESS  not-implemented
            DESCRIPTION
                 "Not supported.

                  Not supported."

        VARIATION   vRtrMplsLspOctets
            ACCESS  not-implemented
            DESCRIPTION
                 "Not supported.

                  Not supported."

        VARIATION   vRtrMplsLspOptimizeTimer
            ACCESS  read-only
            DESCRIPTION
                 "read-only implementation.

                  read-only implementation."

        VARIATION   vRtrMplsLspP2mpId
            ACCESS  not-implemented
            DESCRIPTION
                 "Not supported.

                  Not supported.

                  Not supported.

                  Not supported."

        VARIATION   vRtrMplsLspPackets
            ACCESS  not-implemented
            DESCRIPTION
                 "Not supported.

                  Not supported."

        VARIATION   vRtrMplsLspPathBwProtect
            ACCESS  read-only
            DESCRIPTION
                 "read-only implementation.

                  read-only implementation."

        VARIATION   vRtrMplsLspPathClassOfService
            ACCESS  read-only
            DESCRIPTION
                 "read-only implementation.

                  read-only implementation."

        VARIATION   vRtrMplsLspPathClassType
            ACCESS  not-implemented
            DESCRIPTION
                 "Not supported.

                  Not supported."

        VARIATION   vRtrMplsLspPathCos
            ACCESS  read-only
            DESCRIPTION
                 "read-only implementation.

                  read-only implementation."

        VARIATION   vRtrMplsLspPathCosSource
            ACCESS  read-only
            DESCRIPTION
                 "read-only implementation.

                  read-only implementation."

        VARIATION   vRtrMplsLspPathOptimizeTimer
            ACCESS  read-only
            DESCRIPTION
                 "read-only implementation.

                  read-only implementation."

        VARIATION   vRtrMplsLspPathPreference
            ACCESS  read-only
            DESCRIPTION
                 "read-only implementation.

                  read-only implementation."

        VARIATION   vRtrMplsLspPathSharing
            ACCESS  read-only
            DESCRIPTION
                 "read-only implementation.

                  read-only implementation."

        VARIATION   vRtrMplsLspPathTableSpinlock
            ACCESS  not-implemented
            DESCRIPTION
                 "vRtrMplsLspPathTableSpinlock was intended to be used for
                  control of changes to inherited attributes. There are no
                  inherited attributes in the base version of MPLS on Nokia
                  SAS-R 7210 systems.

                  vRtrMplsLspPathTableSpinlock was intended to be used for
                  control of changes to inherited attributes. There are no
                  inherited attributes in the base version of MPLS on Nokia
                  SAS-R 7210 systems."

        VARIATION   vRtrMplsLspPreference
            ACCESS  read-only
            DESCRIPTION
                 "read-only implementation.

                  read-only implementation."

        VARIATION   vRtrMplsLspRecord
            ACCESS  read-only
            DESCRIPTION
                 "read-only implementation.

                  read-only implementation."

        VARIATION   vRtrMplsLspSetupPriority
            ACCESS  read-only
            DESCRIPTION
                 "read-only implementation.

                  read-only implementation."

        VARIATION   vRtrMplsLspTemplateAdaptive
            ACCESS  not-implemented
            DESCRIPTION
                 "Not supported.

                  Not supported."

        VARIATION   vRtrMplsLspTemplateAdmGrpExcl
            ACCESS  not-implemented
            DESCRIPTION
                 "Not supported.

                  Not supported."

        VARIATION   vRtrMplsLspTemplateAdmGrpIncl
            ACCESS  not-implemented
            DESCRIPTION
                 "Not supported.

                  Not supported."

        VARIATION   vRtrMplsLspTemplateAdminState
            ACCESS  not-implemented
            DESCRIPTION
                 "Not supported.

                  Not supported."

        VARIATION   vRtrMplsLspTemplateBandwidth
            ACCESS  not-implemented
            DESCRIPTION
                 "Not supported.

                  Not supported."

        VARIATION   vRtrMplsLspTemplateCspf
            ACCESS  not-implemented
            DESCRIPTION
                 "Not supported.

                  Not supported."

        VARIATION   vRtrMplsLspTemplateCspfTeMetric
            ACCESS  not-implemented
            DESCRIPTION
                 "Not supported.

                  Not supported."

        VARIATION   vRtrMplsLspTemplateDefaultPath
            ACCESS  not-implemented
            DESCRIPTION
                 "Not supported.

                  Not supported."

        VARIATION   vRtrMplsLspTemplateFRHopLimit
            ACCESS  not-implemented
            DESCRIPTION
                 "Not supported.

                  Not supported."

        VARIATION   vRtrMplsLspTemplateFRMethod
            ACCESS  not-implemented
            DESCRIPTION
                 "Not supported.

                  Not supported."

        VARIATION   vRtrMplsLspTemplateFastReroute
            ACCESS  not-implemented
            DESCRIPTION
                 "Not supported.

                  Not supported."

        VARIATION   vRtrMplsLspTemplateHopLimit
            ACCESS  not-implemented
            DESCRIPTION
                 "Not supported.

                  Not supported."

        VARIATION   vRtrMplsLspTemplateLastChanged
            ACCESS  not-implemented
            DESCRIPTION
                 "Not supported.

                  Not supported."

        VARIATION   vRtrMplsLspTemplateLspCount
            ACCESS  not-implemented
            DESCRIPTION
                 "Not supported.

                  Not supported."

        VARIATION   vRtrMplsLspTemplateMvpnRefCount
            ACCESS  not-implemented
            DESCRIPTION
                 "Not supported.

                  Not supported."

        VARIATION   vRtrMplsLspTemplateName
            ACCESS  not-implemented
            DESCRIPTION
                 "Not supported.

                  Not supported."

        VARIATION   vRtrMplsLspTemplateRecord
            ACCESS  not-implemented
            DESCRIPTION
                 "Not supported.

                  Not supported."

        VARIATION   vRtrMplsLspTemplateRecordLabel
            ACCESS  not-implemented
            DESCRIPTION
                 "Not supported.

                  Not supported."

        VARIATION   vRtrMplsLspTemplateRetryLimit
            ACCESS  not-implemented
            DESCRIPTION
                 "Not supported.

                  Not supported."

        VARIATION   vRtrMplsLspTemplateRetryTimer
            ACCESS  not-implemented
            DESCRIPTION
                 "Not supported.

                  Not supported."

        VARIATION   vRtrMplsLspTemplateRowStatus
            ACCESS  not-implemented
            DESCRIPTION
                 "Not supported.

                  Not supported."

        VARIATION   vRtrMplsLspTemplateType
            ACCESS  not-implemented
            DESCRIPTION
                 "Not supported.

                  Not supported."

        VARIATION   vRtrMplsOutSegmentNumS2ls
            ACCESS  not-implemented
            DESCRIPTION
                 "Not supported.

                  Not supported.

                  Not supported.

                  Not supported."

    ::= { tmnxSASAgentV9v0  10 }

--
-- SAS NTP CAPABILITIES
--
tmnxSASNtpV9v0                    AGENT-CAPABILITIES
    PRODUCT-RELEASE "Alcatel-Lucent SAS"
    STATUS          current
    DESCRIPTION
         "Implementation of NTP capabilities for Alcatel-Lucent SAS systems
          release 9.0."

    SUPPORTS        TIMETRA-NTP-MIB
        INCLUDES {
           tmnxNtpAuthKeyGroup,
           tmnxNtpBroadcastGroup,
           tmnxNtpGlobalGroup,
           tmnxNtpNotificationV6v0Group,
           tmnxNtpPeersGroup,
           tmnxNtpServersGroup
        }

        VARIATION   tmnxNtpAuthKeyEntry
            CREATION-REQUIRES {
                       tmnxNtpAuthKeyType
                    }
            DESCRIPTION
                 "A value must be set for tmnxNtpAuthKeyType in order for
                  tmnxNtpAuthKeyEntryStatus to successfully transition to the
                  'active' state.

                  A value must be set for tmnxNtpAuthKeyType in order for
                  tmnxNtpAuthKeyEntryStatus to successfully transition to the
                  'active' state."

        VARIATION   tmnxNtpAuthKeyType
            SYNTAX  INTEGER {
                    -- des                  (1)
                       messageDigest        (2)
                    }
            DESCRIPTION
                 "tmnxNtpAuthKeyType supports only 'messageDigest (2)'.

                  tmnxNtpAuthKeyType supports only 'messageDigest (2)'."

        VARIATION   tmnxNtpMulticastAddress
            SYNTAX  InetAddress (SIZE (4))
            DESCRIPTION
                 "tmnxNtpMulticastAddress supports only InetAddressType 'ipv4'.

                  tmnxNtpMulticastAddress supports only InetAddressType
                  'ipv4'."

        VARIATION   tmnxNtpMulticastAddressType
            SYNTAX  INTEGER {
                    -- unknown              (0)
                       ipv4                 (1)
                    -- ipv6                 (2)
                    -- ipv4z                (3)
                    -- ipv6z                (4)
                    -- dns                  (16)
                    }
            DESCRIPTION
                 "tmnxNtpMulticastAddressType supports only InetAddressType
                  'ipv4'.

                  tmnxNtpMulticastAddressType supports only InetAddressType
                  'ipv4'."

        VARIATION   tmnxNtpPeersAddrType
            SYNTAX  INTEGER {
                    -- unknown              (0)
                       ipv4                 (1)
                    -- ipv6                 (2)
                    -- ipv4z                (3)
                    -- ipv6z                (4)
                    -- dns                  (16)
                    }
            DESCRIPTION
                 "tmnxNtpPeersAddrType supports only InetAddressType 'ipv4'.

                  tmnxNtpPeersAddrType supports only InetAddressType 'ipv4'."

        VARIATION   tmnxNtpPeersAddress
            SYNTAX  InetAddress (SIZE (4))
            DESCRIPTION
                 "tmnxNtpPeersAddress supports only InetAddressType 'ipv4'.

                  tmnxNtpPeersAddress supports only InetAddressType 'ipv4'."

        VARIATION   tmnxNtpPeersPeerAddrType
            SYNTAX  INTEGER {
                    -- unknown              (0)
                       ipv4                 (1)
                    -- ipv6                 (2)
                    -- ipv4z                (3)
                    -- ipv6z                (4)
                    -- dns                  (16)
                    }
            DESCRIPTION
                 "tmnxNtpPeersPeerAddrType supports only InetAddressType 'ipv4'.

                  tmnxNtpPeersPeerAddrType supports only InetAddressType
                  'ipv4'."

        VARIATION   tmnxNtpPeersPeerAddress
            SYNTAX  InetAddress (SIZE (4))
            DESCRIPTION
                 "tmnxNtpPeersPeerAddress supports only InetAddressType 'ipv4'.

                  tmnxNtpPeersPeerAddress supports only InetAddressType
                  'ipv4'."

        VARIATION   tmnxNtpServersAddrType
            SYNTAX  INTEGER {
                    -- unknown              (0)
                       ipv4                 (1)
                    -- ipv6                 (2)
                    -- ipv4z                (3)
                    -- ipv6z                (4)
                    -- dns                  (16)
                    }
            DESCRIPTION
                 "tmnxNtpServersAddrType supports only InetAddressType 'ipv4'.

                  tmnxNtpServersAddrType supports only InetAddressType 'ipv4'."

        VARIATION   tmnxNtpServersAddress
            SYNTAX  InetAddress (SIZE (4))
            DESCRIPTION
                 "tmnxNtpServersAddress supports only InetAddressType 'ipv4'.

                  tmnxNtpServersAddress supports only InetAddressType 'ipv4'."

    ::= { tmnxSASAgentV9v0  20 }

--
-- SAS NTP CAPABILITIES
--
tmnxSASNtpV9v0                    AGENT-CAPABILITIES
    PRODUCT-RELEASE "Alcatel-Lucent SAS"
    STATUS          current
    DESCRIPTION
         "Implementation of NTP capabilities for Alcatel-Lucent SAS systems
          release 9.0."

    SUPPORTS        TIMETRA-NTP-MIB
        INCLUDES {
           tmnxNtpAuthKeyGroup,
           tmnxNtpBroadcastGroup,
           tmnxNtpGlobalGroup,
           tmnxNtpNotificationV6v0Group,
           tmnxNtpPeersGroup,
           tmnxNtpServersGroup
        }

        VARIATION   tmnxNtpAuthKeyEntry
            CREATION-REQUIRES {
                       tmnxNtpAuthKeyType
                    }
            DESCRIPTION
                 "A value must be set for tmnxNtpAuthKeyType in order for
                  tmnxNtpAuthKeyEntryStatus to successfully transition to the
                  'active' state.

                  A value must be set for tmnxNtpAuthKeyType in order for
                  tmnxNtpAuthKeyEntryStatus to successfully transition to the
                  'active' state."

        VARIATION   tmnxNtpAuthKeyType
            SYNTAX  INTEGER {
                    -- des                  (1)
                       messageDigest        (2)
                    }
            DESCRIPTION
                 "tmnxNtpAuthKeyType supports only 'messageDigest (2)'.

                  tmnxNtpAuthKeyType supports only 'messageDigest (2)'."

        VARIATION   tmnxNtpMulticastAddress
            SYNTAX  InetAddress (SIZE (4))
            DESCRIPTION
                 "tmnxNtpMulticastAddress supports only InetAddressType 'ipv4'.

                  tmnxNtpMulticastAddress supports only InetAddressType
                  'ipv4'."

        VARIATION   tmnxNtpMulticastAddressType
            SYNTAX  INTEGER {
                    -- unknown              (0)
                       ipv4                 (1)
                    -- ipv6                 (2)
                    -- ipv4z                (3)
                    -- ipv6z                (4)
                    -- dns                  (16)
                    }
            DESCRIPTION
                 "tmnxNtpMulticastAddressType supports only InetAddressType
                  'ipv4'.

                  tmnxNtpMulticastAddressType supports only InetAddressType
                  'ipv4'."

        VARIATION   tmnxNtpPeersAddrType
            SYNTAX  INTEGER {
                    -- unknown              (0)
                       ipv4                 (1)
                    -- ipv6                 (2)
                    -- ipv4z                (3)
                    -- ipv6z                (4)
                    -- dns                  (16)
                    }
            DESCRIPTION
                 "tmnxNtpPeersAddrType supports only InetAddressType 'ipv4'.

                  tmnxNtpPeersAddrType supports only InetAddressType 'ipv4'."

        VARIATION   tmnxNtpPeersAddress
            SYNTAX  InetAddress (SIZE (4))
            DESCRIPTION
                 "tmnxNtpPeersAddress supports only InetAddressType 'ipv4'.

                  tmnxNtpPeersAddress supports only InetAddressType 'ipv4'."

        VARIATION   tmnxNtpPeersPeerAddrType
            SYNTAX  INTEGER {
                    -- unknown              (0)
                       ipv4                 (1)
                    -- ipv6                 (2)
                    -- ipv4z                (3)
                    -- ipv6z                (4)
                    -- dns                  (16)
                    }
            DESCRIPTION
                 "tmnxNtpPeersPeerAddrType supports only InetAddressType 'ipv4'.

                  tmnxNtpPeersPeerAddrType supports only InetAddressType
                  'ipv4'."

        VARIATION   tmnxNtpPeersPeerAddress
            SYNTAX  InetAddress (SIZE (4))
            DESCRIPTION
                 "tmnxNtpPeersPeerAddress supports only InetAddressType 'ipv4'.

                  tmnxNtpPeersPeerAddress supports only InetAddressType
                  'ipv4'."

        VARIATION   tmnxNtpServersAddrType
            SYNTAX  INTEGER {
                    -- unknown              (0)
                       ipv4                 (1)
                    -- ipv6                 (2)
                    -- ipv4z                (3)
                    -- ipv6z                (4)
                    -- dns                  (16)
                    }
            DESCRIPTION
                 "tmnxNtpServersAddrType supports only InetAddressType 'ipv4'.

                  tmnxNtpServersAddrType supports only InetAddressType 'ipv4'."

        VARIATION   tmnxNtpServersAddress
            SYNTAX  InetAddress (SIZE (4))
            DESCRIPTION
                 "tmnxNtpServersAddress supports only InetAddressType 'ipv4'.

                  tmnxNtpServersAddress supports only InetAddressType 'ipv4'."

    ::= { tmnxSASAgentV9v0  20 }

--
-- SASR OSPF CAPABILITIES
--
tmnxSASROspfV9v0                  AGENT-CAPABILITIES
    PRODUCT-RELEASE "Alcatel-Lucent SAS"
    STATUS          current
    DESCRIPTION
         "Implementation of OSPF protocol capabilities for Alcatel-Lucent SASR
          systems release 9.0."

    SUPPORTS        OSPF-MIB
        INCLUDES {
           ospfAreaAggregateGroup2,
           ospfAreaGroup2,
-- EXCLUDE ospfAreaLsaCountTable
-- EXCLUDE ospfAreaRangeTable
           ospfAsLsdbGroup,
-- EXCLUDE ospfAuthType
           ospfBasicGroup2,
-- EXCLUDE ospfExtLsdbTable
           ospfHostGroup2,
           ospfIfGroup2,
           ospfIfMetricGroup,
           ospfLocalLsdbGroup,
           ospfLsdbGroup,
           ospfNbrGroup2,
           ospfStubAreaGroup,
           ospfVirtIfGroup2,
           ospfVirtLocalLsdbGroup,
           ospfVirtNbrGroup2
        }

        VARIATION   ospfASBdrRtrStatus
            ACCESS  read-only
            DESCRIPTION
                 "read-only implementation."

        VARIATION   ospfAddressLessIf
            ACCESS  read-only
            DESCRIPTION
                 "read-only implementation."

        VARIATION   ospfAdminStat
            ACCESS  read-only
            DESCRIPTION
                 "read-only implementation."

        VARIATION   ospfAreaAggregateAreaID
            ACCESS  read-only
            DESCRIPTION
                 "read-only implementation."

        VARIATION   ospfAreaAggregateEffect
            ACCESS  read-only
            DESCRIPTION
                 "read-only implementation."

        VARIATION   ospfAreaAggregateExtRouteTag
            ACCESS  read-only
            DESCRIPTION
                 "read-only implementation."

        VARIATION   ospfAreaAggregateLsdbType
            ACCESS  read-only
            DESCRIPTION
                 "read-only implementation."

        VARIATION   ospfAreaAggregateMask
            ACCESS  read-only
            DESCRIPTION
                 "read-only implementation."

        VARIATION   ospfAreaAggregateNet
            ACCESS  read-only
            DESCRIPTION
                 "read-only implementation."

        VARIATION   ospfAreaAggregateStatus
            ACCESS  read-only
            DESCRIPTION
                 "read-only implementation."

        VARIATION   ospfAreaBdrRtrCount
            ACCESS  read-only
            DESCRIPTION
                 "read-only implementation."

        VARIATION   ospfAreaBdrRtrStatus
            ACCESS  read-only
            DESCRIPTION
                 "read-only implementation."

        VARIATION   ospfAreaId
            ACCESS  read-only
            DESCRIPTION
                 "read-only implementation."

        VARIATION   ospfAreaLsaCksumSum
            ACCESS  read-only
            DESCRIPTION
                 "read-only implementation."

        VARIATION   ospfAreaLsaCount
            ACCESS  read-only
            DESCRIPTION
                 "read-only implementation."

        VARIATION   ospfAreaLsaCountNumber
            ACCESS  read-only
            DESCRIPTION
                 "read-only implementation."

        VARIATION   ospfAreaNssaTranslatorEvents
            ACCESS  read-only
            DESCRIPTION
                 "read-only implementation."

        VARIATION   ospfAreaNssaTranslatorRole
            ACCESS  read-only
            DESCRIPTION
                 "read-only implementation."

        VARIATION   ospfAreaNssaTranslatorStabilityInterval
            ACCESS  read-only
            DESCRIPTION
                 "read-only implementation."

        VARIATION   ospfAreaNssaTranslatorState
            ACCESS  read-only
            DESCRIPTION
                 "read-only implementation."

        VARIATION   ospfAreaRangeAreaId
            ACCESS  read-only
            DESCRIPTION
                 "read-only implementation."

        VARIATION   ospfAreaRangeEffect
            ACCESS  read-only
            DESCRIPTION
                 "read-only implementation."

        VARIATION   ospfAreaRangeMask
            ACCESS  read-only
            DESCRIPTION
                 "read-only implementation."

        VARIATION   ospfAreaRangeNet
            ACCESS  read-only
            DESCRIPTION
                 "read-only implementation."

        VARIATION   ospfAreaRangeStatus
            ACCESS  read-only
            DESCRIPTION
                 "read-only implementation."

        VARIATION   ospfAreaStatus
            ACCESS  read-only
            DESCRIPTION
                 "read-only implementation."

        VARIATION   ospfAreaSummary
            ACCESS  read-only
            DESCRIPTION
                 "read-only implementation."

        VARIATION   ospfAsBdrRtrCount
            ACCESS  read-only
            DESCRIPTION
                 "read-only implementation."

        VARIATION   ospfAsLsaCksumSum
            ACCESS  read-only
            DESCRIPTION
                 "read-only implementation."

        VARIATION   ospfAsLsaCount
            ACCESS  read-only
            DESCRIPTION
                 "read-only implementation."

        VARIATION   ospfAsLsdbAdvertisement
            ACCESS  read-only
            DESCRIPTION
                 "read-only implementation."

        VARIATION   ospfAsLsdbAge
            ACCESS  read-only
            DESCRIPTION
                 "read-only implementation."

        VARIATION   ospfAsLsdbChecksum
            ACCESS  read-only
            DESCRIPTION
                 "read-only implementation."

        VARIATION   ospfAsLsdbSequence
            ACCESS  read-only
            DESCRIPTION
                 "read-only implementation."

        VARIATION   ospfDemandExtensions
            ACCESS  read-only
            DESCRIPTION
                 "read-only implementation."

        VARIATION   ospfDiscontinuityTime
            ACCESS  read-only
            DESCRIPTION
                 "read-only implementation."

        VARIATION   ospfExitOverflowInterval
            ACCESS  read-only
            DESCRIPTION
                 "read-only implementation."

        VARIATION   ospfExtLsdbAdvertisement
            ACCESS  read-only
            DESCRIPTION
                 "read-only implementation."

        VARIATION   ospfExtLsdbAge
            ACCESS  read-only
            DESCRIPTION
                 "read-only implementation."

        VARIATION   ospfExtLsdbChecksum
            ACCESS  read-only
            DESCRIPTION
                 "read-only implementation."

        VARIATION   ospfExtLsdbLimit
            ACCESS  read-only
            DESCRIPTION
                 "read-only implementation."

        VARIATION   ospfExtLsdbLsid
            ACCESS  read-only
            DESCRIPTION
                 "read-only implementation."

        VARIATION   ospfExtLsdbRouterId
            ACCESS  read-only
            DESCRIPTION
                 "read-only implementation."

        VARIATION   ospfExtLsdbSequence
            ACCESS  read-only
            DESCRIPTION
                 "read-only implementation."

        VARIATION   ospfExtLsdbType
            ACCESS  read-only
            DESCRIPTION
                 "read-only implementation."

        VARIATION   ospfExternLsaCksumSum
            ACCESS  read-only
            DESCRIPTION
                 "read-only implementation."

        VARIATION   ospfExternLsaCount
            ACCESS  read-only
            DESCRIPTION
                 "read-only implementation."

        VARIATION   ospfHostAreaID
            ACCESS  read-only
            DESCRIPTION
                 "read-only implementation."

        VARIATION   ospfHostCfgAreaID
            ACCESS  read-only
            DESCRIPTION
                 "read-only implementation."

        VARIATION   ospfHostIpAddress
            ACCESS  read-only
            DESCRIPTION
                 "read-only implementation."

        VARIATION   ospfHostMetric
            ACCESS  read-only
            DESCRIPTION
                 "read-only implementation."

        VARIATION   ospfHostStatus
            ACCESS  read-only
            DESCRIPTION
                 "read-only implementation."

        VARIATION   ospfHostTOS
            ACCESS  read-only
            DESCRIPTION
                 "read-only implementation."

        VARIATION   ospfIfAdminStat
            ACCESS  read-only
            DESCRIPTION
                 "read-only implementation."

        VARIATION   ospfIfAreaId
            ACCESS  read-only
            DESCRIPTION
                 "read-only implementation."

        VARIATION   ospfIfAuthKey
            ACCESS  read-only
            DESCRIPTION
                 "read-only implementation."

        VARIATION   ospfIfAuthType
            ACCESS  read-only
            DESCRIPTION
                 "read-only implementation."

        VARIATION   ospfIfBackupDesignatedRouter
            ACCESS  read-only
            DESCRIPTION
                 "read-only implementation."

        VARIATION   ospfIfBackupDesignatedRouterId
            ACCESS  read-only
            DESCRIPTION
                 "read-only implementation."

        VARIATION   ospfIfDemand
            ACCESS  read-only
            DESCRIPTION
                 "read-only implementation."

        VARIATION   ospfIfDesignatedRouter
            ACCESS  read-only
            DESCRIPTION
                 "read-only implementation."

        VARIATION   ospfIfDesignatedRouterId
            ACCESS  read-only
            DESCRIPTION
                 "read-only implementation."

        VARIATION   ospfIfEvents
            ACCESS  read-only
            DESCRIPTION
                 "read-only implementation."

        VARIATION   ospfIfHelloInterval
            ACCESS  read-only
            DESCRIPTION
                 "read-only implementation."

        VARIATION   ospfIfIpAddress
            ACCESS  read-only
            DESCRIPTION
                 "read-only implementation."

        VARIATION   ospfIfLsaCksumSum
            ACCESS  read-only
            DESCRIPTION
                 "read-only implementation."

        VARIATION   ospfIfLsaCount
            ACCESS  read-only
            DESCRIPTION
                 "read-only implementation."

        VARIATION   ospfIfMetricAddressLessIf
            ACCESS  read-only
            DESCRIPTION
                 "read-only implementation."

        VARIATION   ospfIfMetricIpAddress
            ACCESS  read-only
            DESCRIPTION
                 "read-only implementation."

        VARIATION   ospfIfMetricStatus
            ACCESS  read-only
            DESCRIPTION
                 "read-only implementation."

        VARIATION   ospfIfMetricTOS
            ACCESS  read-only
            DESCRIPTION
                 "read-only implementation."

        VARIATION   ospfIfMetricValue
            ACCESS  read-only
            DESCRIPTION
                 "read-only implementation."

        VARIATION   ospfIfMulticastForwarding
            ACCESS  read-only
            DESCRIPTION
                 "read-only implementation."

        VARIATION   ospfIfPollInterval
            ACCESS  read-only
            DESCRIPTION
                 "read-only implementation."

        VARIATION   ospfIfRetransInterval
            ACCESS  read-only
            DESCRIPTION
                 "read-only implementation."

        VARIATION   ospfIfRtrDeadInterval
            ACCESS  read-only
            DESCRIPTION
                 "read-only implementation."

        VARIATION   ospfIfRtrPriority
            ACCESS  read-only
            DESCRIPTION
                 "read-only implementation."

        VARIATION   ospfIfState
            ACCESS  read-only
            DESCRIPTION
                 "read-only implementation."

        VARIATION   ospfIfStatus
            ACCESS  read-only
            DESCRIPTION
                 "read-only implementation."

        VARIATION   ospfIfTransitDelay
            ACCESS  read-only
            DESCRIPTION
                 "read-only implementation."

        VARIATION   ospfIfType
            ACCESS  read-only
            DESCRIPTION
                 "read-only implementation."

        VARIATION   ospfImportAsExtern
            ACCESS  read-only
            DESCRIPTION
                 "read-only implementation."

        VARIATION   ospfLocalLsdbAdvertisement
            ACCESS  read-only
            DESCRIPTION
                 "read-only implementation."

        VARIATION   ospfLocalLsdbAge
            ACCESS  read-only
            DESCRIPTION
                 "read-only implementation."

        VARIATION   ospfLocalLsdbChecksum
            ACCESS  read-only
            DESCRIPTION
                 "read-only implementation."

        VARIATION   ospfLocalLsdbSequence
            ACCESS  read-only
            DESCRIPTION
                 "read-only implementation."

        VARIATION   ospfLsdbAdvertisement
            ACCESS  read-only
            DESCRIPTION
                 "read-only implementation."

        VARIATION   ospfLsdbAge
            ACCESS  read-only
            DESCRIPTION
                 "read-only implementation."

        VARIATION   ospfLsdbAreaId
            ACCESS  read-only
            DESCRIPTION
                 "read-only implementation."

        VARIATION   ospfLsdbChecksum
            ACCESS  read-only
            DESCRIPTION
                 "read-only implementation."

        VARIATION   ospfLsdbLsid
            ACCESS  read-only
            DESCRIPTION
                 "read-only implementation."

        VARIATION   ospfLsdbRouterId
            ACCESS  read-only
            DESCRIPTION
                 "read-only implementation."

        VARIATION   ospfLsdbSequence
            ACCESS  read-only
            DESCRIPTION
                 "read-only implementation."

        VARIATION   ospfLsdbType
            ACCESS  read-only
            DESCRIPTION
                 "read-only implementation."

        VARIATION   ospfMulticastExtensions
            ACCESS  read-only
            DESCRIPTION
                 "read-only implementation."

        VARIATION   ospfNbmaNbrPermanence
            ACCESS  read-only
            DESCRIPTION
                 "read-only implementation."

        VARIATION   ospfNbmaNbrStatus
            ACCESS  read-only
            DESCRIPTION
                 "read-only implementation."

        VARIATION   ospfNbrAddressLessIndex
            ACCESS  read-only
            DESCRIPTION
                 "read-only implementation."

        VARIATION   ospfNbrEvents
            ACCESS  read-only
            DESCRIPTION
                 "read-only implementation."

        VARIATION   ospfNbrHelloSuppressed
            ACCESS  read-only
            DESCRIPTION
                 "read-only implementation."

        VARIATION   ospfNbrIpAddr
            ACCESS  read-only
            DESCRIPTION
                 "read-only implementation."

        VARIATION   ospfNbrLsRetransQLen
            ACCESS  read-only
            DESCRIPTION
                 "read-only implementation."

        VARIATION   ospfNbrOptions
            ACCESS  read-only
            DESCRIPTION
                 "read-only implementation."

        VARIATION   ospfNbrPriority
            ACCESS  read-only
            DESCRIPTION
                 "read-only implementation."

        VARIATION   ospfNbrRestartHelperAge
            ACCESS  read-only
            DESCRIPTION
                 "read-only implementation."

        VARIATION   ospfNbrRestartHelperExitReason
            ACCESS  read-only
            DESCRIPTION
                 "read-only implementation."

        VARIATION   ospfNbrRestartHelperStatus
            ACCESS  read-only
            DESCRIPTION
                 "read-only implementation."

        VARIATION   ospfNbrRtrId
            ACCESS  read-only
            DESCRIPTION
                 "read-only implementation."

        VARIATION   ospfNbrState
            ACCESS  read-only
            DESCRIPTION
                 "read-only implementation."

        VARIATION   ospfOpaqueLsaSupport
            ACCESS  read-only
            DESCRIPTION
                 "read-only implementation."

        VARIATION   ospfOriginateNewLsas
            ACCESS  read-only
            DESCRIPTION
                 "read-only implementation."

        VARIATION   ospfRFC1583Compatibility
            ACCESS  read-only
            DESCRIPTION
                 "read-only implementation."

        VARIATION   ospfReferenceBandwidth
            ACCESS  read-only
            DESCRIPTION
                 "read-only implementation."

        VARIATION   ospfRestartAge
            ACCESS  read-only
            DESCRIPTION
                 "read-only implementation."

        VARIATION   ospfRestartExitReason
            ACCESS  read-only
            DESCRIPTION
                 "read-only implementation."

        VARIATION   ospfRestartInterval
            ACCESS  read-only
            DESCRIPTION
                 "read-only implementation."

        VARIATION   ospfRestartStatus
            ACCESS  read-only
            DESCRIPTION
                 "read-only implementation."

        VARIATION   ospfRestartStrictLsaChecking
            ACCESS  read-only
            DESCRIPTION
                 "read-only implementation."

        VARIATION   ospfRestartSupport
            ACCESS  read-only
            DESCRIPTION
                 "read-only implementation."

        VARIATION   ospfRouterId
            ACCESS  read-only
            DESCRIPTION
                 "read-only implementation."

        VARIATION   ospfRxNewLsas
            ACCESS  read-only
            DESCRIPTION
                 "read-only implementation."

        VARIATION   ospfSpfRuns
            ACCESS  read-only
            DESCRIPTION
                 "read-only implementation."

        VARIATION   ospfStubAreaId
            ACCESS  read-only
            DESCRIPTION
                 "read-only implementation."

        VARIATION   ospfStubMetric
            ACCESS  read-only
            DESCRIPTION
                 "read-only implementation."

        VARIATION   ospfStubMetricType
            ACCESS  read-only
            DESCRIPTION
                 "read-only implementation."

        VARIATION   ospfStubRouterAdvertisement
            ACCESS  read-only
            DESCRIPTION
                 "read-only implementation."

        VARIATION   ospfStubRouterSupport
            ACCESS  read-only
            DESCRIPTION
                 "read-only implementation."

        VARIATION   ospfStubStatus
            ACCESS  read-only
            DESCRIPTION
                 "read-only implementation."

        VARIATION   ospfStubTOS
            ACCESS  read-only
            DESCRIPTION
                 "read-only implementation."

        VARIATION   ospfTOSSupport
            ACCESS  read-only
            DESCRIPTION
                 "read-only implementation."

        VARIATION   ospfVersionNumber
            ACCESS  read-only
            DESCRIPTION
                 "read-only implementation."

        VARIATION   ospfVirtIfAreaId
            ACCESS  read-only
            DESCRIPTION
                 "read-only implementation."

        VARIATION   ospfVirtIfAuthKey
            ACCESS  read-only
            DESCRIPTION
                 "read-only implementation."

        VARIATION   ospfVirtIfAuthType
            ACCESS  read-only
            DESCRIPTION
                 "read-only implementation."

        VARIATION   ospfVirtIfEvents
            ACCESS  read-only
            DESCRIPTION
                 "read-only implementation."

        VARIATION   ospfVirtIfHelloInterval
            ACCESS  read-only
            DESCRIPTION
                 "read-only implementation."

        VARIATION   ospfVirtIfLsaCksumSum
            ACCESS  read-only
            DESCRIPTION
                 "read-only implementation."

        VARIATION   ospfVirtIfLsaCount
            ACCESS  read-only
            DESCRIPTION
                 "read-only implementation."

        VARIATION   ospfVirtIfNeighbor
            ACCESS  read-only
            DESCRIPTION
                 "read-only implementation."

        VARIATION   ospfVirtIfRetransInterval
            ACCESS  read-only
            DESCRIPTION
                 "read-only implementation."

        VARIATION   ospfVirtIfRtrDeadInterval
            ACCESS  read-only
            DESCRIPTION
                 "read-only implementation."

        VARIATION   ospfVirtIfState
            ACCESS  read-only
            DESCRIPTION
                 "read-only implementation."

        VARIATION   ospfVirtIfStatus
            ACCESS  read-only
            DESCRIPTION
                 "read-only implementation."

        VARIATION   ospfVirtIfTransitDelay
            ACCESS  read-only
            DESCRIPTION
                 "read-only implementation."

        VARIATION   ospfVirtLocalLsdbAdvertisement
            ACCESS  read-only
            DESCRIPTION
                 "read-only implementation."

        VARIATION   ospfVirtLocalLsdbAge
            ACCESS  read-only
            DESCRIPTION
                 "read-only implementation."

        VARIATION   ospfVirtLocalLsdbChecksum
            ACCESS  read-only
            DESCRIPTION
                 "read-only implementation."

        VARIATION   ospfVirtLocalLsdbSequence
            ACCESS  read-only
            DESCRIPTION
                 "read-only implementation."

        VARIATION   ospfVirtNbrArea
            ACCESS  read-only
            DESCRIPTION
                 "read-only implementation."

        VARIATION   ospfVirtNbrEvents
            ACCESS  read-only
            DESCRIPTION
                 "read-only implementation."

        VARIATION   ospfVirtNbrHelloSuppressed
            ACCESS  read-only
            DESCRIPTION
                 "read-only implementation."

        VARIATION   ospfVirtNbrIpAddr
            ACCESS  read-only
            DESCRIPTION
                 "read-only implementation."

        VARIATION   ospfVirtNbrLsRetransQLen
            ACCESS  read-only
            DESCRIPTION
                 "read-only implementation."

        VARIATION   ospfVirtNbrOptions
            ACCESS  read-only
            DESCRIPTION
                 "read-only implementation."

        VARIATION   ospfVirtNbrRestartHelperAge
            ACCESS  read-only
            DESCRIPTION
                 "read-only implementation."

        VARIATION   ospfVirtNbrRestartHelperExitReason
            ACCESS  read-only
            DESCRIPTION
                 "read-only implementation."

        VARIATION   ospfVirtNbrRestartHelperStatus
            ACCESS  read-only
            DESCRIPTION
                 "read-only implementation."

        VARIATION   ospfVirtNbrRtrId
            ACCESS  read-only
            DESCRIPTION
                 "read-only implementation."

        VARIATION   ospfVirtNbrState
            ACCESS  read-only
            DESCRIPTION
                 "read-only implementation."

    SUPPORTS        OSPF-TRAP-MIB
        INCLUDES {
           ospfTrapControlGroup,
           ospfTrapEventGroup
        }

        VARIATION   ospfSetTrap
            ACCESS  read-only
            DESCRIPTION
                 "ospfSetTrap is implemented as read-only. The generation of
                  OSPF notifications is controled by tmnxEventTable in the
                  TIMETRA-LOG-MIB."

    SUPPORTS        TIMETRA-OSPF-NG-MIB
        INCLUDES {
           tmnxOspfAreaAggrGroup,
           tmnxOspfAreaGroup,
           tmnxOspfGeneralV5v0Group,
           tmnxOspfGeneralV6v0Group,
           tmnxOspfGeneralV6v1Group,
           tmnxOspfHostGroup,
           tmnxOspfIfV5v0Group,
           tmnxOspfIfV6v0Group,
           tmnxOspfMD5KeyGroup,
           tmnxOspfNbrGroup,
           tmnxOspfNotificationGroup,
           tmnxOspfNotificationV6v0Group,
           tmnxOspfNotifyObjsGroup,
           tmnxOspfVirtIfGroup,
           tmnxOspfVirtNbrGroup
        }

        VARIATION   tmnxOspfAdvertiseTunnelLink
            ACCESS  not-implemented
            DESCRIPTION
                 "Not supported."

        VARIATION   tmnxOspfAreaAggrRouteTag
            ACCESS  read-only
            DESCRIPTION
                 "read-only implementation."

        VARIATION   tmnxOspfAreaNssaTranslatorRole
            ACCESS  read-only
            DESCRIPTION
                 "read-only implementation."

        VARIATION   tmnxOspfAreaNssaTranslatorStabInt
            ACCESS  read-only
            DESCRIPTION
                 "read-only implementation."

        VARIATION   tmnxOspfAreaStubMetricType
            ACCESS  read-only
            DESCRIPTION
                 "read-only implementation."

        VARIATION   tmnxOspfBootOverloadAdmState
            SYNTAX  INTEGER {
                       disabled             (1),
                       enabled              (2)
                    -- enabledWaitForBgp    (3)
                    }
            DESCRIPTION
                 "tmnxOspfBootOverloadAdmState only supports 'disabled (1)' and
                  'enabled (2)'. 'enabledWaitForBgp (3) is not implemented."

        VARIATION   tmnxOspfDemandExtensions
            ACCESS  read-only
            DESCRIPTION
                 "read-only implementation."

        VARIATION   tmnxOspfIfAdvtSubnet
            ACCESS  not-implemented
            DESCRIPTION
                 "Obsolete object."

        VARIATION   tmnxOspfIfDemand
            ACCESS  read-only
            DESCRIPTION
                 "read-only implementation."

        VARIATION   tmnxOspfIfMulticastForwarding
            ACCESS  not-implemented
            DESCRIPTION
                 "Not supported."

        VARIATION   tmnxOspfMulticastExtensions
            ACCESS  not-implemented
            DESCRIPTION
                 "Not supported."

        VARIATION   tmnxOspfMulticastImport
            ACCESS  not-implemented
            DESCRIPTION
                 "Not supported."

        VARIATION   tmnxOspfNbrBfdTracking
            ACCESS  not-implemented
            DESCRIPTION
                 "Not supported."

        VARIATION   tmnxOspfRestartInterval
            ACCESS  read-only
            DESCRIPTION
                 "read-only implementation."

        VARIATION   tmnxOspfRestartSupport
            ACCESS  read-only
            DESCRIPTION
                 "read-only implementation."

        VARIATION   tmnxOspfRsvpShortcut
            ACCESS  not-implemented
            DESCRIPTION
                 "Not supported."

        VARIATION   tmnxOspfStrictLsaChecking
            ACCESS  read-only
            DESCRIPTION
                 "read-only implementation."

        VARIATION   tmnxOspfUnicastImport
            ACCESS  not-implemented
            DESCRIPTION
                 "Not supported."

    ::= { tmnxSASRAgentV9v0  12 }

--
-- SASX OSPF CAPABILITIES
--
tmnxSASXOspfV9v0                  AGENT-CAPABILITIES
    PRODUCT-RELEASE "Alcatel-Lucent SAS"
    STATUS          current
    DESCRIPTION
         "Implementation of OSPF protocol capabilities for Alcatel-Lucent SASX
          systems release 9.0."

    SUPPORTS        OSPF-MIB
        INCLUDES {
           ospfAreaAggregateGroup2,
           ospfAreaGroup2,
-- EXCLUDE ospfAreaLsaCountTable
-- EXCLUDE ospfAreaRangeTable
           ospfAsLsdbGroup,
-- EXCLUDE ospfAuthType
           ospfBasicGroup2,
-- EXCLUDE ospfExtLsdbTable
           ospfHostGroup2,
           ospfIfGroup2,
           ospfIfMetricGroup,
           ospfLocalLsdbGroup,
           ospfLsdbGroup,
           ospfNbrGroup2,
           ospfStubAreaGroup,
           ospfVirtIfGroup2,
           ospfVirtLocalLsdbGroup,
           ospfVirtNbrGroup2
        }

        VARIATION   ospfASBdrRtrStatus
            ACCESS  read-only
            DESCRIPTION
                 "read-only implementation."

        VARIATION   ospfAddressLessIf
            ACCESS  read-only
            DESCRIPTION
                 "read-only implementation."

        VARIATION   ospfAdminStat
            ACCESS  read-only
            DESCRIPTION
                 "read-only implementation."

        VARIATION   ospfAreaAggregateAreaID
            ACCESS  read-only
            DESCRIPTION
                 "read-only implementation."

        VARIATION   ospfAreaAggregateEffect
            ACCESS  read-only
            DESCRIPTION
                 "read-only implementation."

        VARIATION   ospfAreaAggregateExtRouteTag
            ACCESS  read-only
            DESCRIPTION
                 "read-only implementation."

        VARIATION   ospfAreaAggregateLsdbType
            ACCESS  read-only
            DESCRIPTION
                 "read-only implementation."

        VARIATION   ospfAreaAggregateMask
            ACCESS  read-only
            DESCRIPTION
                 "read-only implementation."

        VARIATION   ospfAreaAggregateNet
            ACCESS  read-only
            DESCRIPTION
                 "read-only implementation."

        VARIATION   ospfAreaAggregateStatus
            ACCESS  read-only
            DESCRIPTION
                 "read-only implementation."

        VARIATION   ospfAreaBdrRtrCount
            ACCESS  read-only
            DESCRIPTION
                 "read-only implementation."

        VARIATION   ospfAreaBdrRtrStatus
            ACCESS  read-only
            DESCRIPTION
                 "read-only implementation."

        VARIATION   ospfAreaId
            ACCESS  read-only
            DESCRIPTION
                 "read-only implementation."

        VARIATION   ospfAreaLsaCksumSum
            ACCESS  read-only
            DESCRIPTION
                 "read-only implementation."

        VARIATION   ospfAreaLsaCount
            ACCESS  read-only
            DESCRIPTION
                 "read-only implementation."

        VARIATION   ospfAreaLsaCountNumber
            ACCESS  read-only
            DESCRIPTION
                 "read-only implementation."

        VARIATION   ospfAreaNssaTranslatorEvents
            ACCESS  read-only
            DESCRIPTION
                 "read-only implementation."

        VARIATION   ospfAreaNssaTranslatorRole
            ACCESS  read-only
            DESCRIPTION
                 "read-only implementation."

        VARIATION   ospfAreaNssaTranslatorStabilityInterval
            ACCESS  read-only
            DESCRIPTION
                 "read-only implementation."

        VARIATION   ospfAreaNssaTranslatorState
            ACCESS  read-only
            DESCRIPTION
                 "read-only implementation."

        VARIATION   ospfAreaRangeAreaId
            ACCESS  read-only
            DESCRIPTION
                 "read-only implementation."

        VARIATION   ospfAreaRangeEffect
            ACCESS  read-only
            DESCRIPTION
                 "read-only implementation."

        VARIATION   ospfAreaRangeMask
            ACCESS  read-only
            DESCRIPTION
                 "read-only implementation."

        VARIATION   ospfAreaRangeNet
            ACCESS  read-only
            DESCRIPTION
                 "read-only implementation."

        VARIATION   ospfAreaRangeStatus
            ACCESS  read-only
            DESCRIPTION
                 "read-only implementation."

        VARIATION   ospfAreaStatus
            ACCESS  read-only
            DESCRIPTION
                 "read-only implementation."

        VARIATION   ospfAreaSummary
            ACCESS  read-only
            DESCRIPTION
                 "read-only implementation."

        VARIATION   ospfAsBdrRtrCount
            ACCESS  read-only
            DESCRIPTION
                 "read-only implementation."

        VARIATION   ospfAsLsaCksumSum
            ACCESS  read-only
            DESCRIPTION
                 "read-only implementation."

        VARIATION   ospfAsLsaCount
            ACCESS  read-only
            DESCRIPTION
                 "read-only implementation."

        VARIATION   ospfAsLsdbAdvertisement
            ACCESS  read-only
            DESCRIPTION
                 "read-only implementation."

        VARIATION   ospfAsLsdbAge
            ACCESS  read-only
            DESCRIPTION
                 "read-only implementation."

        VARIATION   ospfAsLsdbChecksum
            ACCESS  read-only
            DESCRIPTION
                 "read-only implementation."

        VARIATION   ospfAsLsdbSequence
            ACCESS  read-only
            DESCRIPTION
                 "read-only implementation."

        VARIATION   ospfDemandExtensions
            ACCESS  read-only
            DESCRIPTION
                 "read-only implementation."

        VARIATION   ospfDiscontinuityTime
            ACCESS  read-only
            DESCRIPTION
                 "read-only implementation."

        VARIATION   ospfExitOverflowInterval
            ACCESS  read-only
            DESCRIPTION
                 "read-only implementation."

        VARIATION   ospfExtLsdbAdvertisement
            ACCESS  read-only
            DESCRIPTION
                 "read-only implementation."

        VARIATION   ospfExtLsdbAge
            ACCESS  read-only
            DESCRIPTION
                 "read-only implementation."

        VARIATION   ospfExtLsdbChecksum
            ACCESS  read-only
            DESCRIPTION
                 "read-only implementation."

        VARIATION   ospfExtLsdbLimit
            ACCESS  read-only
            DESCRIPTION
                 "read-only implementation."

        VARIATION   ospfExtLsdbLsid
            ACCESS  read-only
            DESCRIPTION
                 "read-only implementation."

        VARIATION   ospfExtLsdbRouterId
            ACCESS  read-only
            DESCRIPTION
                 "read-only implementation."

        VARIATION   ospfExtLsdbSequence
            ACCESS  read-only
            DESCRIPTION
                 "read-only implementation."

        VARIATION   ospfExtLsdbType
            ACCESS  read-only
            DESCRIPTION
                 "read-only implementation."

        VARIATION   ospfExternLsaCksumSum
            ACCESS  read-only
            DESCRIPTION
                 "read-only implementation."

        VARIATION   ospfExternLsaCount
            ACCESS  read-only
            DESCRIPTION
                 "read-only implementation."

        VARIATION   ospfHostAreaID
            ACCESS  read-only
            DESCRIPTION
                 "read-only implementation."

        VARIATION   ospfHostCfgAreaID
            ACCESS  read-only
            DESCRIPTION
                 "read-only implementation."

        VARIATION   ospfHostIpAddress
            ACCESS  read-only
            DESCRIPTION
                 "read-only implementation."

        VARIATION   ospfHostMetric
            ACCESS  read-only
            DESCRIPTION
                 "read-only implementation."

        VARIATION   ospfHostStatus
            ACCESS  read-only
            DESCRIPTION
                 "read-only implementation."

        VARIATION   ospfHostTOS
            ACCESS  read-only
            DESCRIPTION
                 "read-only implementation."

        VARIATION   ospfIfAdminStat
            ACCESS  read-only
            DESCRIPTION
                 "read-only implementation."

        VARIATION   ospfIfAreaId
            ACCESS  read-only
            DESCRIPTION
                 "read-only implementation."

        VARIATION   ospfIfAuthKey
            ACCESS  read-only
            DESCRIPTION
                 "read-only implementation."

        VARIATION   ospfIfAuthType
            ACCESS  read-only
            DESCRIPTION
                 "read-only implementation."

        VARIATION   ospfIfBackupDesignatedRouter
            ACCESS  read-only
            DESCRIPTION
                 "read-only implementation."

        VARIATION   ospfIfBackupDesignatedRouterId
            ACCESS  read-only
            DESCRIPTION
                 "read-only implementation."

        VARIATION   ospfIfDemand
            ACCESS  read-only
            DESCRIPTION
                 "read-only implementation."

        VARIATION   ospfIfDesignatedRouter
            ACCESS  read-only
            DESCRIPTION
                 "read-only implementation."

        VARIATION   ospfIfDesignatedRouterId
            ACCESS  read-only
            DESCRIPTION
                 "read-only implementation."

        VARIATION   ospfIfEvents
            ACCESS  read-only
            DESCRIPTION
                 "read-only implementation."

        VARIATION   ospfIfHelloInterval
            ACCESS  read-only
            DESCRIPTION
                 "read-only implementation."

        VARIATION   ospfIfIpAddress
            ACCESS  read-only
            DESCRIPTION
                 "read-only implementation."

        VARIATION   ospfIfLsaCksumSum
            ACCESS  read-only
            DESCRIPTION
                 "read-only implementation."

        VARIATION   ospfIfLsaCount
            ACCESS  read-only
            DESCRIPTION
                 "read-only implementation."

        VARIATION   ospfIfMetricAddressLessIf
            ACCESS  read-only
            DESCRIPTION
                 "read-only implementation."

        VARIATION   ospfIfMetricIpAddress
            ACCESS  read-only
            DESCRIPTION
                 "read-only implementation."

        VARIATION   ospfIfMetricStatus
            ACCESS  read-only
            DESCRIPTION
                 "read-only implementation."

        VARIATION   ospfIfMetricTOS
            ACCESS  read-only
            DESCRIPTION
                 "read-only implementation."

        VARIATION   ospfIfMetricValue
            ACCESS  read-only
            DESCRIPTION
                 "read-only implementation."

        VARIATION   ospfIfMulticastForwarding
            ACCESS  read-only
            DESCRIPTION
                 "read-only implementation."

        VARIATION   ospfIfPollInterval
            ACCESS  read-only
            DESCRIPTION
                 "read-only implementation."

        VARIATION   ospfIfRetransInterval
            ACCESS  read-only
            DESCRIPTION
                 "read-only implementation."

        VARIATION   ospfIfRtrDeadInterval
            ACCESS  read-only
            DESCRIPTION
                 "read-only implementation."

        VARIATION   ospfIfRtrPriority
            ACCESS  read-only
            DESCRIPTION
                 "read-only implementation."

        VARIATION   ospfIfState
            ACCESS  read-only
            DESCRIPTION
                 "read-only implementation."

        VARIATION   ospfIfStatus
            ACCESS  read-only
            DESCRIPTION
                 "read-only implementation."

        VARIATION   ospfIfTransitDelay
            ACCESS  read-only
            DESCRIPTION
                 "read-only implementation."

        VARIATION   ospfIfType
            ACCESS  read-only
            DESCRIPTION
                 "read-only implementation."

        VARIATION   ospfImportAsExtern
            ACCESS  read-only
            DESCRIPTION
                 "read-only implementation."

        VARIATION   ospfLocalLsdbAdvertisement
            ACCESS  read-only
            DESCRIPTION
                 "read-only implementation."

        VARIATION   ospfLocalLsdbAge
            ACCESS  read-only
            DESCRIPTION
                 "read-only implementation."

        VARIATION   ospfLocalLsdbChecksum
            ACCESS  read-only
            DESCRIPTION
                 "read-only implementation."

        VARIATION   ospfLocalLsdbSequence
            ACCESS  read-only
            DESCRIPTION
                 "read-only implementation."

        VARIATION   ospfLsdbAdvertisement
            ACCESS  read-only
            DESCRIPTION
                 "read-only implementation."

        VARIATION   ospfLsdbAge
            ACCESS  read-only
            DESCRIPTION
                 "read-only implementation."

        VARIATION   ospfLsdbAreaId
            ACCESS  read-only
            DESCRIPTION
                 "read-only implementation."

        VARIATION   ospfLsdbChecksum
            ACCESS  read-only
            DESCRIPTION
                 "read-only implementation."

        VARIATION   ospfLsdbLsid
            ACCESS  read-only
            DESCRIPTION
                 "read-only implementation."

        VARIATION   ospfLsdbRouterId
            ACCESS  read-only
            DESCRIPTION
                 "read-only implementation."

        VARIATION   ospfLsdbSequence
            ACCESS  read-only
            DESCRIPTION
                 "read-only implementation."

        VARIATION   ospfLsdbType
            ACCESS  read-only
            DESCRIPTION
                 "read-only implementation."

        VARIATION   ospfMulticastExtensions
            ACCESS  read-only
            DESCRIPTION
                 "read-only implementation."

        VARIATION   ospfNbmaNbrPermanence
            ACCESS  read-only
            DESCRIPTION
                 "read-only implementation."

        VARIATION   ospfNbmaNbrStatus
            ACCESS  read-only
            DESCRIPTION
                 "read-only implementation."

        VARIATION   ospfNbrAddressLessIndex
            ACCESS  read-only
            DESCRIPTION
                 "read-only implementation."

        VARIATION   ospfNbrEvents
            ACCESS  read-only
            DESCRIPTION
                 "read-only implementation."

        VARIATION   ospfNbrHelloSuppressed
            ACCESS  read-only
            DESCRIPTION
                 "read-only implementation."

        VARIATION   ospfNbrIpAddr
            ACCESS  read-only
            DESCRIPTION
                 "read-only implementation."

        VARIATION   ospfNbrLsRetransQLen
            ACCESS  read-only
            DESCRIPTION
                 "read-only implementation."

        VARIATION   ospfNbrOptions
            ACCESS  read-only
            DESCRIPTION
                 "read-only implementation."

        VARIATION   ospfNbrPriority
            ACCESS  read-only
            DESCRIPTION
                 "read-only implementation."

        VARIATION   ospfNbrRestartHelperAge
            ACCESS  read-only
            DESCRIPTION
                 "read-only implementation."

        VARIATION   ospfNbrRestartHelperExitReason
            ACCESS  read-only
            DESCRIPTION
                 "read-only implementation."

        VARIATION   ospfNbrRestartHelperStatus
            ACCESS  read-only
            DESCRIPTION
                 "read-only implementation."

        VARIATION   ospfNbrRtrId
            ACCESS  read-only
            DESCRIPTION
                 "read-only implementation."

        VARIATION   ospfNbrState
            ACCESS  read-only
            DESCRIPTION
                 "read-only implementation."

        VARIATION   ospfOpaqueLsaSupport
            ACCESS  read-only
            DESCRIPTION
                 "read-only implementation."

        VARIATION   ospfOriginateNewLsas
            ACCESS  read-only
            DESCRIPTION
                 "read-only implementation."

        VARIATION   ospfRFC1583Compatibility
            ACCESS  read-only
            DESCRIPTION
                 "read-only implementation."

        VARIATION   ospfReferenceBandwidth
            ACCESS  read-only
            DESCRIPTION
                 "read-only implementation."

        VARIATION   ospfRestartAge
            ACCESS  read-only
            DESCRIPTION
                 "read-only implementation."

        VARIATION   ospfRestartExitReason
            ACCESS  read-only
            DESCRIPTION
                 "read-only implementation."

        VARIATION   ospfRestartInterval
            ACCESS  read-only
            DESCRIPTION
                 "read-only implementation."

        VARIATION   ospfRestartStatus
            ACCESS  read-only
            DESCRIPTION
                 "read-only implementation."

        VARIATION   ospfRestartStrictLsaChecking
            ACCESS  read-only
            DESCRIPTION
                 "read-only implementation."

        VARIATION   ospfRestartSupport
            ACCESS  read-only
            DESCRIPTION
                 "read-only implementation."

        VARIATION   ospfRouterId
            ACCESS  read-only
            DESCRIPTION
                 "read-only implementation."

        VARIATION   ospfRxNewLsas
            ACCESS  read-only
            DESCRIPTION
                 "read-only implementation."

        VARIATION   ospfSpfRuns
            ACCESS  read-only
            DESCRIPTION
                 "read-only implementation."

        VARIATION   ospfStubAreaId
            ACCESS  read-only
            DESCRIPTION
                 "read-only implementation."

        VARIATION   ospfStubMetric
            ACCESS  read-only
            DESCRIPTION
                 "read-only implementation."

        VARIATION   ospfStubMetricType
            ACCESS  read-only
            DESCRIPTION
                 "read-only implementation."

        VARIATION   ospfStubRouterAdvertisement
            ACCESS  read-only
            DESCRIPTION
                 "read-only implementation."

        VARIATION   ospfStubRouterSupport
            ACCESS  read-only
            DESCRIPTION
                 "read-only implementation."

        VARIATION   ospfStubStatus
            ACCESS  read-only
            DESCRIPTION
                 "read-only implementation."

        VARIATION   ospfStubTOS
            ACCESS  read-only
            DESCRIPTION
                 "read-only implementation."

        VARIATION   ospfTOSSupport
            ACCESS  read-only
            DESCRIPTION
                 "read-only implementation."

        VARIATION   ospfVersionNumber
            ACCESS  read-only
            DESCRIPTION
                 "read-only implementation."

        VARIATION   ospfVirtIfAreaId
            ACCESS  read-only
            DESCRIPTION
                 "read-only implementation."

        VARIATION   ospfVirtIfAuthKey
            ACCESS  read-only
            DESCRIPTION
                 "read-only implementation."

        VARIATION   ospfVirtIfAuthType
            ACCESS  read-only
            DESCRIPTION
                 "read-only implementation."

        VARIATION   ospfVirtIfEvents
            ACCESS  read-only
            DESCRIPTION
                 "read-only implementation."

        VARIATION   ospfVirtIfHelloInterval
            ACCESS  read-only
            DESCRIPTION
                 "read-only implementation."

        VARIATION   ospfVirtIfLsaCksumSum
            ACCESS  read-only
            DESCRIPTION
                 "read-only implementation."

        VARIATION   ospfVirtIfLsaCount
            ACCESS  read-only
            DESCRIPTION
                 "read-only implementation."

        VARIATION   ospfVirtIfNeighbor
            ACCESS  read-only
            DESCRIPTION
                 "read-only implementation."

        VARIATION   ospfVirtIfRetransInterval
            ACCESS  read-only
            DESCRIPTION
                 "read-only implementation."

        VARIATION   ospfVirtIfRtrDeadInterval
            ACCESS  read-only
            DESCRIPTION
                 "read-only implementation."

        VARIATION   ospfVirtIfState
            ACCESS  read-only
            DESCRIPTION
                 "read-only implementation."

        VARIATION   ospfVirtIfStatus
            ACCESS  read-only
            DESCRIPTION
                 "read-only implementation."

        VARIATION   ospfVirtIfTransitDelay
            ACCESS  read-only
            DESCRIPTION
                 "read-only implementation."

        VARIATION   ospfVirtLocalLsdbAdvertisement
            ACCESS  read-only
            DESCRIPTION
                 "read-only implementation."

        VARIATION   ospfVirtLocalLsdbAge
            ACCESS  read-only
            DESCRIPTION
                 "read-only implementation."

        VARIATION   ospfVirtLocalLsdbChecksum
            ACCESS  read-only
            DESCRIPTION
                 "read-only implementation."

        VARIATION   ospfVirtLocalLsdbSequence
            ACCESS  read-only
            DESCRIPTION
                 "read-only implementation."

        VARIATION   ospfVirtNbrArea
            ACCESS  read-only
            DESCRIPTION
                 "read-only implementation."

        VARIATION   ospfVirtNbrEvents
            ACCESS  read-only
            DESCRIPTION
                 "read-only implementation."

        VARIATION   ospfVirtNbrHelloSuppressed
            ACCESS  read-only
            DESCRIPTION
                 "read-only implementation."

        VARIATION   ospfVirtNbrIpAddr
            ACCESS  read-only
            DESCRIPTION
                 "read-only implementation."

        VARIATION   ospfVirtNbrLsRetransQLen
            ACCESS  read-only
            DESCRIPTION
                 "read-only implementation."

        VARIATION   ospfVirtNbrOptions
            ACCESS  read-only
            DESCRIPTION
                 "read-only implementation."

        VARIATION   ospfVirtNbrRestartHelperAge
            ACCESS  read-only
            DESCRIPTION
                 "read-only implementation."

        VARIATION   ospfVirtNbrRestartHelperExitReason
            ACCESS  read-only
            DESCRIPTION
                 "read-only implementation."

        VARIATION   ospfVirtNbrRestartHelperStatus
            ACCESS  read-only
            DESCRIPTION
                 "read-only implementation."

        VARIATION   ospfVirtNbrRtrId
            ACCESS  read-only
            DESCRIPTION
                 "read-only implementation."

        VARIATION   ospfVirtNbrState
            ACCESS  read-only
            DESCRIPTION
                 "read-only implementation."

    SUPPORTS        OSPF-TRAP-MIB
        INCLUDES {
           ospfTrapControlGroup,
           ospfTrapEventGroup
        }

        VARIATION   ospfSetTrap
            ACCESS  read-only
            DESCRIPTION
                 "ospfSetTrap is implemented as read-only. The generation of
                  OSPF notifications is controled by tmnxEventTable in the
                  TIMETRA-LOG-MIB."

    SUPPORTS        TIMETRA-OSPF-NG-MIB
        INCLUDES {
           tmnxOspfAreaAggrGroup,
           tmnxOspfAreaGroup,
           tmnxOspfGeneralV5v0Group,
           tmnxOspfGeneralV6v0Group,
           tmnxOspfGeneralV6v1Group,
           tmnxOspfHostGroup,
           tmnxOspfIfV5v0Group,
           tmnxOspfIfV6v0Group,
           tmnxOspfMD5KeyGroup,
           tmnxOspfNbrGroup,
           tmnxOspfNotificationGroup,
           tmnxOspfNotificationV6v0Group,
           tmnxOspfNotifyObjsGroup,
           tmnxOspfVirtIfGroup,
           tmnxOspfVirtNbrGroup
        }

        VARIATION   tmnxOspfAdvertiseTunnelLink
            ACCESS  not-implemented
            DESCRIPTION
                 "Not supported."

        VARIATION   tmnxOspfAreaAggrRouteTag
            ACCESS  read-only
            DESCRIPTION
                 "read-only implementation."

        VARIATION   tmnxOspfAreaNssaTranslatorRole
            ACCESS  read-only
            DESCRIPTION
                 "read-only implementation."

        VARIATION   tmnxOspfAreaNssaTranslatorStabInt
            ACCESS  read-only
            DESCRIPTION
                 "read-only implementation."

        VARIATION   tmnxOspfAreaStubMetricType
            ACCESS  read-only
            DESCRIPTION
                 "read-only implementation."

        VARIATION   tmnxOspfBootOverloadAdmState
            SYNTAX  INTEGER {
                       disabled             (1),
                       enabled              (2)
                    -- enabledWaitForBgp    (3)
                    }
            DESCRIPTION
                 "tmnxOspfBootOverloadAdmState only supports 'disabled (1)' and
                  'enabled (2)'. 'enabledWaitForBgp (3) is not implemented."

        VARIATION   tmnxOspfDemandExtensions
            ACCESS  read-only
            DESCRIPTION
                 "read-only implementation."

        VARIATION   tmnxOspfIfAdvtSubnet
            ACCESS  not-implemented
            DESCRIPTION
                 "Obsolete object."

        VARIATION   tmnxOspfIfDemand
            ACCESS  read-only
            DESCRIPTION
                 "read-only implementation."

        VARIATION   tmnxOspfIfMulticastForwarding
            ACCESS  not-implemented
            DESCRIPTION
                 "Not supported."

        VARIATION   tmnxOspfMulticastExtensions
            ACCESS  not-implemented
            DESCRIPTION
                 "Not supported."

        VARIATION   tmnxOspfMulticastImport
            ACCESS  not-implemented
            DESCRIPTION
                 "Not supported."

        VARIATION   tmnxOspfNbrBfdTracking
            ACCESS  not-implemented
            DESCRIPTION
                 "Not supported."

        VARIATION   tmnxOspfRestartInterval
            ACCESS  read-only
            DESCRIPTION
                 "read-only implementation."

        VARIATION   tmnxOspfRestartSupport
            ACCESS  read-only
            DESCRIPTION
                 "read-only implementation."

        VARIATION   tmnxOspfRsvpShortcut
            ACCESS  not-implemented
            DESCRIPTION
                 "Not supported."

        VARIATION   tmnxOspfStrictLsaChecking
            ACCESS  read-only
            DESCRIPTION
                 "read-only implementation."

        VARIATION   tmnxOspfUnicastImport
            ACCESS  not-implemented
            DESCRIPTION
                 "Not supported."

    ::= { tmnxSASXAgentV9v0  12 }

--
-- SASM OSPF CAPABILITIES
--
tmnxSASMOspfV9v0                  AGENT-CAPABILITIES
    PRODUCT-RELEASE "Alcatel-Lucent SAS"
    STATUS          current
    DESCRIPTION
         "Implementation of OSPF protocol capabilities for Alcatel-Lucent SASM
          systems release 9.0."

    SUPPORTS        OSPF-MIB
        INCLUDES {
           ospfAreaAggregateGroup2,
           ospfAreaGroup2,
-- EXCLUDE ospfAreaLsaCountTable
-- EXCLUDE ospfAreaRangeTable
           ospfAsLsdbGroup,
-- EXCLUDE ospfAuthType
           ospfBasicGroup2,
-- EXCLUDE ospfExtLsdbTable
           ospfHostGroup2,
           ospfIfGroup2,
           ospfIfMetricGroup,
           ospfLocalLsdbGroup,
           ospfLsdbGroup,
           ospfNbrGroup2,
           ospfStubAreaGroup,
           ospfVirtIfGroup2,
           ospfVirtLocalLsdbGroup,
           ospfVirtNbrGroup2
        }

        VARIATION   ospfASBdrRtrStatus
            ACCESS  read-only
            DESCRIPTION
                 "read-only implementation."

        VARIATION   ospfAddressLessIf
            ACCESS  read-only
            DESCRIPTION
                 "read-only implementation."

        VARIATION   ospfAdminStat
            ACCESS  read-only
            DESCRIPTION
                 "read-only implementation."

        VARIATION   ospfAreaAggregateAreaID
            ACCESS  read-only
            DESCRIPTION
                 "read-only implementation."

        VARIATION   ospfAreaAggregateEffect
            ACCESS  read-only
            DESCRIPTION
                 "read-only implementation."

        VARIATION   ospfAreaAggregateExtRouteTag
            ACCESS  read-only
            DESCRIPTION
                 "read-only implementation."

        VARIATION   ospfAreaAggregateLsdbType
            ACCESS  read-only
            DESCRIPTION
                 "read-only implementation."

        VARIATION   ospfAreaAggregateMask
            ACCESS  read-only
            DESCRIPTION
                 "read-only implementation."

        VARIATION   ospfAreaAggregateNet
            ACCESS  read-only
            DESCRIPTION
                 "read-only implementation."

        VARIATION   ospfAreaAggregateStatus
            ACCESS  read-only
            DESCRIPTION
                 "read-only implementation."

        VARIATION   ospfAreaBdrRtrCount
            ACCESS  read-only
            DESCRIPTION
                 "read-only implementation."

        VARIATION   ospfAreaBdrRtrStatus
            ACCESS  read-only
            DESCRIPTION
                 "read-only implementation."

        VARIATION   ospfAreaId
            ACCESS  read-only
            DESCRIPTION
                 "read-only implementation."

        VARIATION   ospfAreaLsaCksumSum
            ACCESS  read-only
            DESCRIPTION
                 "read-only implementation."

        VARIATION   ospfAreaLsaCount
            ACCESS  read-only
            DESCRIPTION
                 "read-only implementation."

        VARIATION   ospfAreaLsaCountNumber
            ACCESS  read-only
            DESCRIPTION
                 "read-only implementation."

        VARIATION   ospfAreaNssaTranslatorEvents
            ACCESS  read-only
            DESCRIPTION
                 "read-only implementation."

        VARIATION   ospfAreaNssaTranslatorRole
            ACCESS  read-only
            DESCRIPTION
                 "read-only implementation."

        VARIATION   ospfAreaNssaTranslatorStabilityInterval
            ACCESS  read-only
            DESCRIPTION
                 "read-only implementation."

        VARIATION   ospfAreaNssaTranslatorState
            ACCESS  read-only
            DESCRIPTION
                 "read-only implementation."

        VARIATION   ospfAreaRangeAreaId
            ACCESS  read-only
            DESCRIPTION
                 "read-only implementation."

        VARIATION   ospfAreaRangeEffect
            ACCESS  read-only
            DESCRIPTION
                 "read-only implementation."

        VARIATION   ospfAreaRangeMask
            ACCESS  read-only
            DESCRIPTION
                 "read-only implementation."

        VARIATION   ospfAreaRangeNet
            ACCESS  read-only
            DESCRIPTION
                 "read-only implementation."

        VARIATION   ospfAreaRangeStatus
            ACCESS  read-only
            DESCRIPTION
                 "read-only implementation."

        VARIATION   ospfAreaStatus
            ACCESS  read-only
            DESCRIPTION
                 "read-only implementation."

        VARIATION   ospfAreaSummary
            ACCESS  read-only
            DESCRIPTION
                 "read-only implementation."

        VARIATION   ospfAsBdrRtrCount
            ACCESS  read-only
            DESCRIPTION
                 "read-only implementation."

        VARIATION   ospfAsLsaCksumSum
            ACCESS  read-only
            DESCRIPTION
                 "read-only implementation."

        VARIATION   ospfAsLsaCount
            ACCESS  read-only
            DESCRIPTION
                 "read-only implementation."

        VARIATION   ospfAsLsdbAdvertisement
            ACCESS  read-only
            DESCRIPTION
                 "read-only implementation."

        VARIATION   ospfAsLsdbAge
            ACCESS  read-only
            DESCRIPTION
                 "read-only implementation."

        VARIATION   ospfAsLsdbChecksum
            ACCESS  read-only
            DESCRIPTION
                 "read-only implementation."

        VARIATION   ospfAsLsdbSequence
            ACCESS  read-only
            DESCRIPTION
                 "read-only implementation."

        VARIATION   ospfDemandExtensions
            ACCESS  read-only
            DESCRIPTION
                 "read-only implementation."

        VARIATION   ospfDiscontinuityTime
            ACCESS  read-only
            DESCRIPTION
                 "read-only implementation."

        VARIATION   ospfExitOverflowInterval
            ACCESS  read-only
            DESCRIPTION
                 "read-only implementation."

        VARIATION   ospfExtLsdbAdvertisement
            ACCESS  read-only
            DESCRIPTION
                 "read-only implementation."

        VARIATION   ospfExtLsdbAge
            ACCESS  read-only
            DESCRIPTION
                 "read-only implementation."

        VARIATION   ospfExtLsdbChecksum
            ACCESS  read-only
            DESCRIPTION
                 "read-only implementation."

        VARIATION   ospfExtLsdbLimit
            ACCESS  read-only
            DESCRIPTION
                 "read-only implementation."

        VARIATION   ospfExtLsdbLsid
            ACCESS  read-only
            DESCRIPTION
                 "read-only implementation."

        VARIATION   ospfExtLsdbRouterId
            ACCESS  read-only
            DESCRIPTION
                 "read-only implementation."

        VARIATION   ospfExtLsdbSequence
            ACCESS  read-only
            DESCRIPTION
                 "read-only implementation."

        VARIATION   ospfExtLsdbType
            ACCESS  read-only
            DESCRIPTION
                 "read-only implementation."

        VARIATION   ospfExternLsaCksumSum
            ACCESS  read-only
            DESCRIPTION
                 "read-only implementation."

        VARIATION   ospfExternLsaCount
            ACCESS  read-only
            DESCRIPTION
                 "read-only implementation."

        VARIATION   ospfHostAreaID
            ACCESS  read-only
            DESCRIPTION
                 "read-only implementation."

        VARIATION   ospfHostCfgAreaID
            ACCESS  read-only
            DESCRIPTION
                 "read-only implementation."

        VARIATION   ospfHostIpAddress
            ACCESS  read-only
            DESCRIPTION
                 "read-only implementation."

        VARIATION   ospfHostMetric
            ACCESS  read-only
            DESCRIPTION
                 "read-only implementation."

        VARIATION   ospfHostStatus
            ACCESS  read-only
            DESCRIPTION
                 "read-only implementation."

        VARIATION   ospfHostTOS
            ACCESS  read-only
            DESCRIPTION
                 "read-only implementation."

        VARIATION   ospfIfAdminStat
            ACCESS  read-only
            DESCRIPTION
                 "read-only implementation."

        VARIATION   ospfIfAreaId
            ACCESS  read-only
            DESCRIPTION
                 "read-only implementation."

        VARIATION   ospfIfAuthKey
            ACCESS  read-only
            DESCRIPTION
                 "read-only implementation."

        VARIATION   ospfIfAuthType
            ACCESS  read-only
            DESCRIPTION
                 "read-only implementation."

        VARIATION   ospfIfBackupDesignatedRouter
            ACCESS  read-only
            DESCRIPTION
                 "read-only implementation."

        VARIATION   ospfIfBackupDesignatedRouterId
            ACCESS  read-only
            DESCRIPTION
                 "read-only implementation."

        VARIATION   ospfIfDemand
            ACCESS  read-only
            DESCRIPTION
                 "read-only implementation."

        VARIATION   ospfIfDesignatedRouter
            ACCESS  read-only
            DESCRIPTION
                 "read-only implementation."

        VARIATION   ospfIfDesignatedRouterId
            ACCESS  read-only
            DESCRIPTION
                 "read-only implementation."

        VARIATION   ospfIfEvents
            ACCESS  read-only
            DESCRIPTION
                 "read-only implementation."

        VARIATION   ospfIfHelloInterval
            ACCESS  read-only
            DESCRIPTION
                 "read-only implementation."

        VARIATION   ospfIfIpAddress
            ACCESS  read-only
            DESCRIPTION
                 "read-only implementation."

        VARIATION   ospfIfLsaCksumSum
            ACCESS  read-only
            DESCRIPTION
                 "read-only implementation."

        VARIATION   ospfIfLsaCount
            ACCESS  read-only
            DESCRIPTION
                 "read-only implementation."

        VARIATION   ospfIfMetricAddressLessIf
            ACCESS  read-only
            DESCRIPTION
                 "read-only implementation."

        VARIATION   ospfIfMetricIpAddress
            ACCESS  read-only
            DESCRIPTION
                 "read-only implementation."

        VARIATION   ospfIfMetricStatus
            ACCESS  read-only
            DESCRIPTION
                 "read-only implementation."

        VARIATION   ospfIfMetricTOS
            ACCESS  read-only
            DESCRIPTION
                 "read-only implementation."

        VARIATION   ospfIfMetricValue
            ACCESS  read-only
            DESCRIPTION
                 "read-only implementation."

        VARIATION   ospfIfMulticastForwarding
            ACCESS  read-only
            DESCRIPTION
                 "read-only implementation."

        VARIATION   ospfIfPollInterval
            ACCESS  read-only
            DESCRIPTION
                 "read-only implementation."

        VARIATION   ospfIfRetransInterval
            ACCESS  read-only
            DESCRIPTION
                 "read-only implementation."

        VARIATION   ospfIfRtrDeadInterval
            ACCESS  read-only
            DESCRIPTION
                 "read-only implementation."

        VARIATION   ospfIfRtrPriority
            ACCESS  read-only
            DESCRIPTION
                 "read-only implementation."

        VARIATION   ospfIfState
            ACCESS  read-only
            DESCRIPTION
                 "read-only implementation."

        VARIATION   ospfIfStatus
            ACCESS  read-only
            DESCRIPTION
                 "read-only implementation."

        VARIATION   ospfIfTransitDelay
            ACCESS  read-only
            DESCRIPTION
                 "read-only implementation."

        VARIATION   ospfIfType
            ACCESS  read-only
            DESCRIPTION
                 "read-only implementation."

        VARIATION   ospfImportAsExtern
            ACCESS  read-only
            DESCRIPTION
                 "read-only implementation."

        VARIATION   ospfLocalLsdbAdvertisement
            ACCESS  read-only
            DESCRIPTION
                 "read-only implementation."

        VARIATION   ospfLocalLsdbAge
            ACCESS  read-only
            DESCRIPTION
                 "read-only implementation."

        VARIATION   ospfLocalLsdbChecksum
            ACCESS  read-only
            DESCRIPTION
                 "read-only implementation."

        VARIATION   ospfLocalLsdbSequence
            ACCESS  read-only
            DESCRIPTION
                 "read-only implementation."

        VARIATION   ospfLsdbAdvertisement
            ACCESS  read-only
            DESCRIPTION
                 "read-only implementation."

        VARIATION   ospfLsdbAge
            ACCESS  read-only
            DESCRIPTION
                 "read-only implementation."

        VARIATION   ospfLsdbAreaId
            ACCESS  read-only
            DESCRIPTION
                 "read-only implementation."

        VARIATION   ospfLsdbChecksum
            ACCESS  read-only
            DESCRIPTION
                 "read-only implementation."

        VARIATION   ospfLsdbLsid
            ACCESS  read-only
            DESCRIPTION
                 "read-only implementation."

        VARIATION   ospfLsdbRouterId
            ACCESS  read-only
            DESCRIPTION
                 "read-only implementation."

        VARIATION   ospfLsdbSequence
            ACCESS  read-only
            DESCRIPTION
                 "read-only implementation."

        VARIATION   ospfLsdbType
            ACCESS  read-only
            DESCRIPTION
                 "read-only implementation."

        VARIATION   ospfMulticastExtensions
            ACCESS  read-only
            DESCRIPTION
                 "read-only implementation."

        VARIATION   ospfNbmaNbrPermanence
            ACCESS  read-only
            DESCRIPTION
                 "read-only implementation."

        VARIATION   ospfNbmaNbrStatus
            ACCESS  read-only
            DESCRIPTION
                 "read-only implementation."

        VARIATION   ospfNbrAddressLessIndex
            ACCESS  read-only
            DESCRIPTION
                 "read-only implementation."

        VARIATION   ospfNbrEvents
            ACCESS  read-only
            DESCRIPTION
                 "read-only implementation."

        VARIATION   ospfNbrHelloSuppressed
            ACCESS  read-only
            DESCRIPTION
                 "read-only implementation."

        VARIATION   ospfNbrIpAddr
            ACCESS  read-only
            DESCRIPTION
                 "read-only implementation."

        VARIATION   ospfNbrLsRetransQLen
            ACCESS  read-only
            DESCRIPTION
                 "read-only implementation."

        VARIATION   ospfNbrOptions
            ACCESS  read-only
            DESCRIPTION
                 "read-only implementation."

        VARIATION   ospfNbrPriority
            ACCESS  read-only
            DESCRIPTION
                 "read-only implementation."

        VARIATION   ospfNbrRestartHelperAge
            ACCESS  read-only
            DESCRIPTION
                 "read-only implementation."

        VARIATION   ospfNbrRestartHelperExitReason
            ACCESS  read-only
            DESCRIPTION
                 "read-only implementation."

        VARIATION   ospfNbrRestartHelperStatus
            ACCESS  read-only
            DESCRIPTION
                 "read-only implementation."

        VARIATION   ospfNbrRtrId
            ACCESS  read-only
            DESCRIPTION
                 "read-only implementation."

        VARIATION   ospfNbrState
            ACCESS  read-only
            DESCRIPTION
                 "read-only implementation."

        VARIATION   ospfOpaqueLsaSupport
            ACCESS  read-only
            DESCRIPTION
                 "read-only implementation."

        VARIATION   ospfOriginateNewLsas
            ACCESS  read-only
            DESCRIPTION
                 "read-only implementation."

        VARIATION   ospfRFC1583Compatibility
            ACCESS  read-only
            DESCRIPTION
                 "read-only implementation."

        VARIATION   ospfReferenceBandwidth
            ACCESS  read-only
            DESCRIPTION
                 "read-only implementation."

        VARIATION   ospfRestartAge
            ACCESS  read-only
            DESCRIPTION
                 "read-only implementation."

        VARIATION   ospfRestartExitReason
            ACCESS  read-only
            DESCRIPTION
                 "read-only implementation."

        VARIATION   ospfRestartInterval
            ACCESS  read-only
            DESCRIPTION
                 "read-only implementation."

        VARIATION   ospfRestartStatus
            ACCESS  read-only
            DESCRIPTION
                 "read-only implementation."

        VARIATION   ospfRestartStrictLsaChecking
            ACCESS  read-only
            DESCRIPTION
                 "read-only implementation."

        VARIATION   ospfRestartSupport
            ACCESS  read-only
            DESCRIPTION
                 "read-only implementation."

        VARIATION   ospfRouterId
            ACCESS  read-only
            DESCRIPTION
                 "read-only implementation."

        VARIATION   ospfRxNewLsas
            ACCESS  read-only
            DESCRIPTION
                 "read-only implementation."

        VARIATION   ospfSpfRuns
            ACCESS  read-only
            DESCRIPTION
                 "read-only implementation."

        VARIATION   ospfStubAreaId
            ACCESS  read-only
            DESCRIPTION
                 "read-only implementation."

        VARIATION   ospfStubMetric
            ACCESS  read-only
            DESCRIPTION
                 "read-only implementation."

        VARIATION   ospfStubMetricType
            ACCESS  read-only
            DESCRIPTION
                 "read-only implementation."

        VARIATION   ospfStubRouterAdvertisement
            ACCESS  read-only
            DESCRIPTION
                 "read-only implementation."

        VARIATION   ospfStubRouterSupport
            ACCESS  read-only
            DESCRIPTION
                 "read-only implementation."

        VARIATION   ospfStubStatus
            ACCESS  read-only
            DESCRIPTION
                 "read-only implementation."

        VARIATION   ospfStubTOS
            ACCESS  read-only
            DESCRIPTION
                 "read-only implementation."

        VARIATION   ospfTOSSupport
            ACCESS  read-only
            DESCRIPTION
                 "read-only implementation."

        VARIATION   ospfVersionNumber
            ACCESS  read-only
            DESCRIPTION
                 "read-only implementation."

        VARIATION   ospfVirtIfAreaId
            ACCESS  read-only
            DESCRIPTION
                 "read-only implementation."

        VARIATION   ospfVirtIfAuthKey
            ACCESS  read-only
            DESCRIPTION
                 "read-only implementation."

        VARIATION   ospfVirtIfAuthType
            ACCESS  read-only
            DESCRIPTION
                 "read-only implementation."

        VARIATION   ospfVirtIfEvents
            ACCESS  read-only
            DESCRIPTION
                 "read-only implementation."

        VARIATION   ospfVirtIfHelloInterval
            ACCESS  read-only
            DESCRIPTION
                 "read-only implementation."

        VARIATION   ospfVirtIfLsaCksumSum
            ACCESS  read-only
            DESCRIPTION
                 "read-only implementation."

        VARIATION   ospfVirtIfLsaCount
            ACCESS  read-only
            DESCRIPTION
                 "read-only implementation."

        VARIATION   ospfVirtIfNeighbor
            ACCESS  read-only
            DESCRIPTION
                 "read-only implementation."

        VARIATION   ospfVirtIfRetransInterval
            ACCESS  read-only
            DESCRIPTION
                 "read-only implementation."

        VARIATION   ospfVirtIfRtrDeadInterval
            ACCESS  read-only
            DESCRIPTION
                 "read-only implementation."

        VARIATION   ospfVirtIfState
            ACCESS  read-only
            DESCRIPTION
                 "read-only implementation."

        VARIATION   ospfVirtIfStatus
            ACCESS  read-only
            DESCRIPTION
                 "read-only implementation."

        VARIATION   ospfVirtIfTransitDelay
            ACCESS  read-only
            DESCRIPTION
                 "read-only implementation."

        VARIATION   ospfVirtLocalLsdbAdvertisement
            ACCESS  read-only
            DESCRIPTION
                 "read-only implementation."

        VARIATION   ospfVirtLocalLsdbAge
            ACCESS  read-only
            DESCRIPTION
                 "read-only implementation."

        VARIATION   ospfVirtLocalLsdbChecksum
            ACCESS  read-only
            DESCRIPTION
                 "read-only implementation."

        VARIATION   ospfVirtLocalLsdbSequence
            ACCESS  read-only
            DESCRIPTION
                 "read-only implementation."

        VARIATION   ospfVirtNbrArea
            ACCESS  read-only
            DESCRIPTION
                 "read-only implementation."

        VARIATION   ospfVirtNbrEvents
            ACCESS  read-only
            DESCRIPTION
                 "read-only implementation."

        VARIATION   ospfVirtNbrHelloSuppressed
            ACCESS  read-only
            DESCRIPTION
                 "read-only implementation."

        VARIATION   ospfVirtNbrIpAddr
            ACCESS  read-only
            DESCRIPTION
                 "read-only implementation."

        VARIATION   ospfVirtNbrLsRetransQLen
            ACCESS  read-only
            DESCRIPTION
                 "read-only implementation."

        VARIATION   ospfVirtNbrOptions
            ACCESS  read-only
            DESCRIPTION
                 "read-only implementation."

        VARIATION   ospfVirtNbrRestartHelperAge
            ACCESS  read-only
            DESCRIPTION
                 "read-only implementation."

        VARIATION   ospfVirtNbrRestartHelperExitReason
            ACCESS  read-only
            DESCRIPTION
                 "read-only implementation."

        VARIATION   ospfVirtNbrRestartHelperStatus
            ACCESS  read-only
            DESCRIPTION
                 "read-only implementation."

        VARIATION   ospfVirtNbrRtrId
            ACCESS  read-only
            DESCRIPTION
                 "read-only implementation."

        VARIATION   ospfVirtNbrState
            ACCESS  read-only
            DESCRIPTION
                 "read-only implementation."

    SUPPORTS        OSPF-TRAP-MIB
        INCLUDES {
           ospfTrapControlGroup,
           ospfTrapEventGroup
        }

        VARIATION   ospfSetTrap
            ACCESS  read-only
            DESCRIPTION
                 "ospfSetTrap is implemented as read-only. The generation of
                  OSPF notifications is controled by tmnxEventTable in the
                  TIMETRA-LOG-MIB."

    SUPPORTS        TIMETRA-OSPF-NG-MIB
        INCLUDES {
           tmnxOspfAreaAggrGroup,
           tmnxOspfAreaGroup,
           tmnxOspfGeneralV5v0Group,
           tmnxOspfGeneralV6v0Group,
           tmnxOspfGeneralV6v1Group,
           tmnxOspfHostGroup,
           tmnxOspfIfV5v0Group,
           tmnxOspfIfV6v0Group,
           tmnxOspfMD5KeyGroup,
           tmnxOspfNbrGroup,
           tmnxOspfNotificationGroup,
           tmnxOspfNotificationV6v0Group,
           tmnxOspfNotifyObjsGroup,
           tmnxOspfVirtIfGroup,
           tmnxOspfVirtNbrGroup
        }

        VARIATION   tmnxOspfAdvertiseTunnelLink
            ACCESS  not-implemented
            DESCRIPTION
                 "Not supported."

        VARIATION   tmnxOspfAreaAggrRouteTag
            ACCESS  read-only
            DESCRIPTION
                 "read-only implementation."

        VARIATION   tmnxOspfAreaNssaTranslatorRole
            ACCESS  read-only
            DESCRIPTION
                 "read-only implementation."

        VARIATION   tmnxOspfAreaNssaTranslatorStabInt
            ACCESS  read-only
            DESCRIPTION
                 "read-only implementation."

        VARIATION   tmnxOspfAreaStubMetricType
            ACCESS  read-only
            DESCRIPTION
                 "read-only implementation."

        VARIATION   tmnxOspfBootOverloadAdmState
            SYNTAX  INTEGER {
                       disabled             (1),
                       enabled              (2)
                    -- enabledWaitForBgp    (3)
                    }
            DESCRIPTION
                 "tmnxOspfBootOverloadAdmState only supports 'disabled (1)' and
                  'enabled (2)'. 'enabledWaitForBgp (3) is not implemented."

        VARIATION   tmnxOspfDemandExtensions
            ACCESS  read-only
            DESCRIPTION
                 "read-only implementation."

        VARIATION   tmnxOspfIfAdvtSubnet
            ACCESS  not-implemented
            DESCRIPTION
                 "Obsolete object."

        VARIATION   tmnxOspfIfDemand
            ACCESS  read-only
            DESCRIPTION
                 "read-only implementation."

        VARIATION   tmnxOspfIfMulticastForwarding
            ACCESS  not-implemented
            DESCRIPTION
                 "Not supported."

        VARIATION   tmnxOspfMulticastExtensions
            ACCESS  not-implemented
            DESCRIPTION
                 "Not supported."

        VARIATION   tmnxOspfMulticastImport
            ACCESS  not-implemented
            DESCRIPTION
                 "Not supported."

        VARIATION   tmnxOspfNbrBfdTracking
            ACCESS  not-implemented
            DESCRIPTION
                 "Not supported."

        VARIATION   tmnxOspfRestartInterval
            ACCESS  read-only
            DESCRIPTION
                 "read-only implementation."

        VARIATION   tmnxOspfRestartSupport
            ACCESS  read-only
            DESCRIPTION
                 "read-only implementation."

        VARIATION   tmnxOspfRsvpShortcut
            ACCESS  not-implemented
            DESCRIPTION
                 "Not supported."

        VARIATION   tmnxOspfStrictLsaChecking
            ACCESS  read-only
            DESCRIPTION
                 "read-only implementation."

        VARIATION   tmnxOspfUnicastImport
            ACCESS  not-implemented
            DESCRIPTION
                 "Not supported."

    ::= { tmnxSASMAgentV9v0  12 }

--
-- SASMxp OSPF CAPABILITIES
--
tmnxSASMxpOspfV9v0                AGENT-CAPABILITIES
    PRODUCT-RELEASE "Alcatel-Lucent SAS"
    STATUS          current
    DESCRIPTION
         "Implementation of OSPF protocol capabilities for Alcatel-Lucent SASM
          xp systems release 9.0."

    SUPPORTS        OSPF-MIB
        INCLUDES {
           ospfAreaAggregateGroup2,
           ospfAreaGroup2,
-- EXCLUDE ospfAreaLsaCountTable
-- EXCLUDE ospfAreaRangeTable
           ospfAsLsdbGroup,
-- EXCLUDE ospfAuthType
           ospfBasicGroup2,
-- EXCLUDE ospfExtLsdbTable
           ospfHostGroup2,
           ospfIfGroup2,
           ospfIfMetricGroup,
           ospfLocalLsdbGroup,
           ospfLsdbGroup,
           ospfNbrGroup2,
           ospfStubAreaGroup,
           ospfVirtIfGroup2,
           ospfVirtLocalLsdbGroup,
           ospfVirtNbrGroup2
        }

        VARIATION   ospfASBdrRtrStatus
            ACCESS  read-only
            DESCRIPTION
                 "read-only implementation."

        VARIATION   ospfAddressLessIf
            ACCESS  read-only
            DESCRIPTION
                 "read-only implementation."

        VARIATION   ospfAdminStat
            ACCESS  read-only
            DESCRIPTION
                 "read-only implementation."

        VARIATION   ospfAreaAggregateAreaID
            ACCESS  read-only
            DESCRIPTION
                 "read-only implementation."

        VARIATION   ospfAreaAggregateEffect
            ACCESS  read-only
            DESCRIPTION
                 "read-only implementation."

        VARIATION   ospfAreaAggregateExtRouteTag
            ACCESS  read-only
            DESCRIPTION
                 "read-only implementation."

        VARIATION   ospfAreaAggregateLsdbType
            ACCESS  read-only
            DESCRIPTION
                 "read-only implementation."

        VARIATION   ospfAreaAggregateMask
            ACCESS  read-only
            DESCRIPTION
                 "read-only implementation."

        VARIATION   ospfAreaAggregateNet
            ACCESS  read-only
            DESCRIPTION
                 "read-only implementation."

        VARIATION   ospfAreaAggregateStatus
            ACCESS  read-only
            DESCRIPTION
                 "read-only implementation."

        VARIATION   ospfAreaBdrRtrCount
            ACCESS  read-only
            DESCRIPTION
                 "read-only implementation."

        VARIATION   ospfAreaBdrRtrStatus
            ACCESS  read-only
            DESCRIPTION
                 "read-only implementation."

        VARIATION   ospfAreaId
            ACCESS  read-only
            DESCRIPTION
                 "read-only implementation."

        VARIATION   ospfAreaLsaCksumSum
            ACCESS  read-only
            DESCRIPTION
                 "read-only implementation."

        VARIATION   ospfAreaLsaCount
            ACCESS  read-only
            DESCRIPTION
                 "read-only implementation."

        VARIATION   ospfAreaLsaCountNumber
            ACCESS  read-only
            DESCRIPTION
                 "read-only implementation."

        VARIATION   ospfAreaNssaTranslatorEvents
            ACCESS  read-only
            DESCRIPTION
                 "read-only implementation."

        VARIATION   ospfAreaNssaTranslatorRole
            ACCESS  read-only
            DESCRIPTION
                 "read-only implementation."

        VARIATION   ospfAreaNssaTranslatorStabilityInterval
            ACCESS  read-only
            DESCRIPTION
                 "read-only implementation."

        VARIATION   ospfAreaNssaTranslatorState
            ACCESS  read-only
            DESCRIPTION
                 "read-only implementation."

        VARIATION   ospfAreaRangeAreaId
            ACCESS  read-only
            DESCRIPTION
                 "read-only implementation."

        VARIATION   ospfAreaRangeEffect
            ACCESS  read-only
            DESCRIPTION
                 "read-only implementation."

        VARIATION   ospfAreaRangeMask
            ACCESS  read-only
            DESCRIPTION
                 "read-only implementation."

        VARIATION   ospfAreaRangeNet
            ACCESS  read-only
            DESCRIPTION
                 "read-only implementation."

        VARIATION   ospfAreaRangeStatus
            ACCESS  read-only
            DESCRIPTION
                 "read-only implementation."

        VARIATION   ospfAreaStatus
            ACCESS  read-only
            DESCRIPTION
                 "read-only implementation."

        VARIATION   ospfAreaSummary
            ACCESS  read-only
            DESCRIPTION
                 "read-only implementation."

        VARIATION   ospfAsBdrRtrCount
            ACCESS  read-only
            DESCRIPTION
                 "read-only implementation."

        VARIATION   ospfAsLsaCksumSum
            ACCESS  read-only
            DESCRIPTION
                 "read-only implementation."

        VARIATION   ospfAsLsaCount
            ACCESS  read-only
            DESCRIPTION
                 "read-only implementation."

        VARIATION   ospfAsLsdbAdvertisement
            ACCESS  read-only
            DESCRIPTION
                 "read-only implementation."

        VARIATION   ospfAsLsdbAge
            ACCESS  read-only
            DESCRIPTION
                 "read-only implementation."

        VARIATION   ospfAsLsdbChecksum
            ACCESS  read-only
            DESCRIPTION
                 "read-only implementation."

        VARIATION   ospfAsLsdbSequence
            ACCESS  read-only
            DESCRIPTION
                 "read-only implementation."

        VARIATION   ospfDemandExtensions
            ACCESS  read-only
            DESCRIPTION
                 "read-only implementation."

        VARIATION   ospfDiscontinuityTime
            ACCESS  read-only
            DESCRIPTION
                 "read-only implementation."

        VARIATION   ospfExitOverflowInterval
            ACCESS  read-only
            DESCRIPTION
                 "read-only implementation."

        VARIATION   ospfExtLsdbAdvertisement
            ACCESS  read-only
            DESCRIPTION
                 "read-only implementation."

        VARIATION   ospfExtLsdbAge
            ACCESS  read-only
            DESCRIPTION
                 "read-only implementation."

        VARIATION   ospfExtLsdbChecksum
            ACCESS  read-only
            DESCRIPTION
                 "read-only implementation."

        VARIATION   ospfExtLsdbLimit
            ACCESS  read-only
            DESCRIPTION
                 "read-only implementation."

        VARIATION   ospfExtLsdbLsid
            ACCESS  read-only
            DESCRIPTION
                 "read-only implementation."

        VARIATION   ospfExtLsdbRouterId
            ACCESS  read-only
            DESCRIPTION
                 "read-only implementation."

        VARIATION   ospfExtLsdbSequence
            ACCESS  read-only
            DESCRIPTION
                 "read-only implementation."

        VARIATION   ospfExtLsdbType
            ACCESS  read-only
            DESCRIPTION
                 "read-only implementation."

        VARIATION   ospfExternLsaCksumSum
            ACCESS  read-only
            DESCRIPTION
                 "read-only implementation."

        VARIATION   ospfExternLsaCount
            ACCESS  read-only
            DESCRIPTION
                 "read-only implementation."

        VARIATION   ospfHostAreaID
            ACCESS  read-only
            DESCRIPTION
                 "read-only implementation."

        VARIATION   ospfHostCfgAreaID
            ACCESS  read-only
            DESCRIPTION
                 "read-only implementation."

        VARIATION   ospfHostIpAddress
            ACCESS  read-only
            DESCRIPTION
                 "read-only implementation."

        VARIATION   ospfHostMetric
            ACCESS  read-only
            DESCRIPTION
                 "read-only implementation."

        VARIATION   ospfHostStatus
            ACCESS  read-only
            DESCRIPTION
                 "read-only implementation."

        VARIATION   ospfHostTOS
            ACCESS  read-only
            DESCRIPTION
                 "read-only implementation."

        VARIATION   ospfIfAdminStat
            ACCESS  read-only
            DESCRIPTION
                 "read-only implementation."

        VARIATION   ospfIfAreaId
            ACCESS  read-only
            DESCRIPTION
                 "read-only implementation."

        VARIATION   ospfIfAuthKey
            ACCESS  read-only
            DESCRIPTION
                 "read-only implementation."

        VARIATION   ospfIfAuthType
            ACCESS  read-only
            DESCRIPTION
                 "read-only implementation."

        VARIATION   ospfIfBackupDesignatedRouter
            ACCESS  read-only
            DESCRIPTION
                 "read-only implementation."

        VARIATION   ospfIfBackupDesignatedRouterId
            ACCESS  read-only
            DESCRIPTION
                 "read-only implementation."

        VARIATION   ospfIfDemand
            ACCESS  read-only
            DESCRIPTION
                 "read-only implementation."

        VARIATION   ospfIfDesignatedRouter
            ACCESS  read-only
            DESCRIPTION
                 "read-only implementation."

        VARIATION   ospfIfDesignatedRouterId
            ACCESS  read-only
            DESCRIPTION
                 "read-only implementation."

        VARIATION   ospfIfEvents
            ACCESS  read-only
            DESCRIPTION
                 "read-only implementation."

        VARIATION   ospfIfHelloInterval
            ACCESS  read-only
            DESCRIPTION
                 "read-only implementation."

        VARIATION   ospfIfIpAddress
            ACCESS  read-only
            DESCRIPTION
                 "read-only implementation."

        VARIATION   ospfIfLsaCksumSum
            ACCESS  read-only
            DESCRIPTION
                 "read-only implementation."

        VARIATION   ospfIfLsaCount
            ACCESS  read-only
            DESCRIPTION
                 "read-only implementation."

        VARIATION   ospfIfMetricAddressLessIf
            ACCESS  read-only
            DESCRIPTION
                 "read-only implementation."

        VARIATION   ospfIfMetricIpAddress
            ACCESS  read-only
            DESCRIPTION
                 "read-only implementation."

        VARIATION   ospfIfMetricStatus
            ACCESS  read-only
            DESCRIPTION
                 "read-only implementation."

        VARIATION   ospfIfMetricTOS
            ACCESS  read-only
            DESCRIPTION
                 "read-only implementation."

        VARIATION   ospfIfMetricValue
            ACCESS  read-only
            DESCRIPTION
                 "read-only implementation."

        VARIATION   ospfIfMulticastForwarding
            ACCESS  read-only
            DESCRIPTION
                 "read-only implementation."

        VARIATION   ospfIfPollInterval
            ACCESS  read-only
            DESCRIPTION
                 "read-only implementation."

        VARIATION   ospfIfRetransInterval
            ACCESS  read-only
            DESCRIPTION
                 "read-only implementation."

        VARIATION   ospfIfRtrDeadInterval
            ACCESS  read-only
            DESCRIPTION
                 "read-only implementation."

        VARIATION   ospfIfRtrPriority
            ACCESS  read-only
            DESCRIPTION
                 "read-only implementation."

        VARIATION   ospfIfState
            ACCESS  read-only
            DESCRIPTION
                 "read-only implementation."

        VARIATION   ospfIfStatus
            ACCESS  read-only
            DESCRIPTION
                 "read-only implementation."

        VARIATION   ospfIfTransitDelay
            ACCESS  read-only
            DESCRIPTION
                 "read-only implementation."

        VARIATION   ospfIfType
            ACCESS  read-only
            DESCRIPTION
                 "read-only implementation."

        VARIATION   ospfImportAsExtern
            ACCESS  read-only
            DESCRIPTION
                 "read-only implementation."

        VARIATION   ospfLocalLsdbAdvertisement
            ACCESS  read-only
            DESCRIPTION
                 "read-only implementation."

        VARIATION   ospfLocalLsdbAge
            ACCESS  read-only
            DESCRIPTION
                 "read-only implementation."

        VARIATION   ospfLocalLsdbChecksum
            ACCESS  read-only
            DESCRIPTION
                 "read-only implementation."

        VARIATION   ospfLocalLsdbSequence
            ACCESS  read-only
            DESCRIPTION
                 "read-only implementation."

        VARIATION   ospfLsdbAdvertisement
            ACCESS  read-only
            DESCRIPTION
                 "read-only implementation."

        VARIATION   ospfLsdbAge
            ACCESS  read-only
            DESCRIPTION
                 "read-only implementation."

        VARIATION   ospfLsdbAreaId
            ACCESS  read-only
            DESCRIPTION
                 "read-only implementation."

        VARIATION   ospfLsdbChecksum
            ACCESS  read-only
            DESCRIPTION
                 "read-only implementation."

        VARIATION   ospfLsdbLsid
            ACCESS  read-only
            DESCRIPTION
                 "read-only implementation."

        VARIATION   ospfLsdbRouterId
            ACCESS  read-only
            DESCRIPTION
                 "read-only implementation."

        VARIATION   ospfLsdbSequence
            ACCESS  read-only
            DESCRIPTION
                 "read-only implementation."

        VARIATION   ospfLsdbType
            ACCESS  read-only
            DESCRIPTION
                 "read-only implementation."

        VARIATION   ospfMulticastExtensions
            ACCESS  read-only
            DESCRIPTION
                 "read-only implementation."

        VARIATION   ospfNbmaNbrPermanence
            ACCESS  read-only
            DESCRIPTION
                 "read-only implementation."

        VARIATION   ospfNbmaNbrStatus
            ACCESS  read-only
            DESCRIPTION
                 "read-only implementation."

        VARIATION   ospfNbrAddressLessIndex
            ACCESS  read-only
            DESCRIPTION
                 "read-only implementation."

        VARIATION   ospfNbrEvents
            ACCESS  read-only
            DESCRIPTION
                 "read-only implementation."

        VARIATION   ospfNbrHelloSuppressed
            ACCESS  read-only
            DESCRIPTION
                 "read-only implementation."

        VARIATION   ospfNbrIpAddr
            ACCESS  read-only
            DESCRIPTION
                 "read-only implementation."

        VARIATION   ospfNbrLsRetransQLen
            ACCESS  read-only
            DESCRIPTION
                 "read-only implementation."

        VARIATION   ospfNbrOptions
            ACCESS  read-only
            DESCRIPTION
                 "read-only implementation."

        VARIATION   ospfNbrPriority
            ACCESS  read-only
            DESCRIPTION
                 "read-only implementation."

        VARIATION   ospfNbrRestartHelperAge
            ACCESS  read-only
            DESCRIPTION
                 "read-only implementation."

        VARIATION   ospfNbrRestartHelperExitReason
            ACCESS  read-only
            DESCRIPTION
                 "read-only implementation."

        VARIATION   ospfNbrRestartHelperStatus
            ACCESS  read-only
            DESCRIPTION
                 "read-only implementation."

        VARIATION   ospfNbrRtrId
            ACCESS  read-only
            DESCRIPTION
                 "read-only implementation."

        VARIATION   ospfNbrState
            ACCESS  read-only
            DESCRIPTION
                 "read-only implementation."

        VARIATION   ospfOpaqueLsaSupport
            ACCESS  read-only
            DESCRIPTION
                 "read-only implementation."

        VARIATION   ospfOriginateNewLsas
            ACCESS  read-only
            DESCRIPTION
                 "read-only implementation."

        VARIATION   ospfRFC1583Compatibility
            ACCESS  read-only
            DESCRIPTION
                 "read-only implementation."

        VARIATION   ospfReferenceBandwidth
            ACCESS  read-only
            DESCRIPTION
                 "read-only implementation."

        VARIATION   ospfRestartAge
            ACCESS  read-only
            DESCRIPTION
                 "read-only implementation."

        VARIATION   ospfRestartExitReason
            ACCESS  read-only
            DESCRIPTION
                 "read-only implementation."

        VARIATION   ospfRestartInterval
            ACCESS  read-only
            DESCRIPTION
                 "read-only implementation."

        VARIATION   ospfRestartStatus
            ACCESS  read-only
            DESCRIPTION
                 "read-only implementation."

        VARIATION   ospfRestartStrictLsaChecking
            ACCESS  read-only
            DESCRIPTION
                 "read-only implementation."

        VARIATION   ospfRestartSupport
            ACCESS  read-only
            DESCRIPTION
                 "read-only implementation."

        VARIATION   ospfRouterId
            ACCESS  read-only
            DESCRIPTION
                 "read-only implementation."

        VARIATION   ospfRxNewLsas
            ACCESS  read-only
            DESCRIPTION
                 "read-only implementation."

        VARIATION   ospfSpfRuns
            ACCESS  read-only
            DESCRIPTION
                 "read-only implementation."

        VARIATION   ospfStubAreaId
            ACCESS  read-only
            DESCRIPTION
                 "read-only implementation."

        VARIATION   ospfStubMetric
            ACCESS  read-only
            DESCRIPTION
                 "read-only implementation."

        VARIATION   ospfStubMetricType
            ACCESS  read-only
            DESCRIPTION
                 "read-only implementation."

        VARIATION   ospfStubRouterAdvertisement
            ACCESS  read-only
            DESCRIPTION
                 "read-only implementation."

        VARIATION   ospfStubRouterSupport
            ACCESS  read-only
            DESCRIPTION
                 "read-only implementation."

        VARIATION   ospfStubStatus
            ACCESS  read-only
            DESCRIPTION
                 "read-only implementation."

        VARIATION   ospfStubTOS
            ACCESS  read-only
            DESCRIPTION
                 "read-only implementation."

        VARIATION   ospfTOSSupport
            ACCESS  read-only
            DESCRIPTION
                 "read-only implementation."

        VARIATION   ospfVersionNumber
            ACCESS  read-only
            DESCRIPTION
                 "read-only implementation."

        VARIATION   ospfVirtIfAreaId
            ACCESS  read-only
            DESCRIPTION
                 "read-only implementation."

        VARIATION   ospfVirtIfAuthKey
            ACCESS  read-only
            DESCRIPTION
                 "read-only implementation."

        VARIATION   ospfVirtIfAuthType
            ACCESS  read-only
            DESCRIPTION
                 "read-only implementation."

        VARIATION   ospfVirtIfEvents
            ACCESS  read-only
            DESCRIPTION
                 "read-only implementation."

        VARIATION   ospfVirtIfHelloInterval
            ACCESS  read-only
            DESCRIPTION
                 "read-only implementation."

        VARIATION   ospfVirtIfLsaCksumSum
            ACCESS  read-only
            DESCRIPTION
                 "read-only implementation."

        VARIATION   ospfVirtIfLsaCount
            ACCESS  read-only
            DESCRIPTION
                 "read-only implementation."

        VARIATION   ospfVirtIfNeighbor
            ACCESS  read-only
            DESCRIPTION
                 "read-only implementation."

        VARIATION   ospfVirtIfRetransInterval
            ACCESS  read-only
            DESCRIPTION
                 "read-only implementation."

        VARIATION   ospfVirtIfRtrDeadInterval
            ACCESS  read-only
            DESCRIPTION
                 "read-only implementation."

        VARIATION   ospfVirtIfState
            ACCESS  read-only
            DESCRIPTION
                 "read-only implementation."

        VARIATION   ospfVirtIfStatus
            ACCESS  read-only
            DESCRIPTION
                 "read-only implementation."

        VARIATION   ospfVirtIfTransitDelay
            ACCESS  read-only
            DESCRIPTION
                 "read-only implementation."

        VARIATION   ospfVirtLocalLsdbAdvertisement
            ACCESS  read-only
            DESCRIPTION
                 "read-only implementation."

        VARIATION   ospfVirtLocalLsdbAge
            ACCESS  read-only
            DESCRIPTION
                 "read-only implementation."

        VARIATION   ospfVirtLocalLsdbChecksum
            ACCESS  read-only
            DESCRIPTION
                 "read-only implementation."

        VARIATION   ospfVirtLocalLsdbSequence
            ACCESS  read-only
            DESCRIPTION
                 "read-only implementation."

        VARIATION   ospfVirtNbrArea
            ACCESS  read-only
            DESCRIPTION
                 "read-only implementation."

        VARIATION   ospfVirtNbrEvents
            ACCESS  read-only
            DESCRIPTION
                 "read-only implementation."

        VARIATION   ospfVirtNbrHelloSuppressed
            ACCESS  read-only
            DESCRIPTION
                 "read-only implementation."

        VARIATION   ospfVirtNbrIpAddr
            ACCESS  read-only
            DESCRIPTION
                 "read-only implementation."

        VARIATION   ospfVirtNbrLsRetransQLen
            ACCESS  read-only
            DESCRIPTION
                 "read-only implementation."

        VARIATION   ospfVirtNbrOptions
            ACCESS  read-only
            DESCRIPTION
                 "read-only implementation."

        VARIATION   ospfVirtNbrRestartHelperAge
            ACCESS  read-only
            DESCRIPTION
                 "read-only implementation."

        VARIATION   ospfVirtNbrRestartHelperExitReason
            ACCESS  read-only
            DESCRIPTION
                 "read-only implementation."

        VARIATION   ospfVirtNbrRestartHelperStatus
            ACCESS  read-only
            DESCRIPTION
                 "read-only implementation."

        VARIATION   ospfVirtNbrRtrId
            ACCESS  read-only
            DESCRIPTION
                 "read-only implementation."

        VARIATION   ospfVirtNbrState
            ACCESS  read-only
            DESCRIPTION
                 "read-only implementation."

    SUPPORTS        OSPF-TRAP-MIB
        INCLUDES {
           ospfTrapControlGroup,
           ospfTrapEventGroup
        }

        VARIATION   ospfSetTrap
            ACCESS  read-only
            DESCRIPTION
                 "ospfSetTrap is implemented as read-only. The generation of
                  OSPF notifications is controled by tmnxEventTable in the
                  TIMETRA-LOG-MIB."

    SUPPORTS        TIMETRA-OSPF-NG-MIB
        INCLUDES {
           tmnxOspfAreaAggrGroup,
           tmnxOspfAreaGroup,
           tmnxOspfGeneralV5v0Group,
           tmnxOspfGeneralV6v0Group,
           tmnxOspfGeneralV6v1Group,
           tmnxOspfHostGroup,
           tmnxOspfIfV5v0Group,
           tmnxOspfIfV6v0Group,
           tmnxOspfMD5KeyGroup,
           tmnxOspfNbrGroup,
           tmnxOspfNotificationGroup,
           tmnxOspfNotificationV6v0Group,
           tmnxOspfNotifyObjsGroup,
           tmnxOspfVirtIfGroup,
           tmnxOspfVirtNbrGroup
        }

        VARIATION   tmnxOspfAdvertiseTunnelLink
            ACCESS  not-implemented
            DESCRIPTION
                 "Not supported."

        VARIATION   tmnxOspfAreaAggrRouteTag
            ACCESS  read-only
            DESCRIPTION
                 "read-only implementation."

        VARIATION   tmnxOspfAreaNssaTranslatorRole
            ACCESS  read-only
            DESCRIPTION
                 "read-only implementation."

        VARIATION   tmnxOspfAreaNssaTranslatorStabInt
            ACCESS  read-only
            DESCRIPTION
                 "read-only implementation."

        VARIATION   tmnxOspfAreaStubMetricType
            ACCESS  read-only
            DESCRIPTION
                 "read-only implementation."

        VARIATION   tmnxOspfBootOverloadAdmState
            SYNTAX  INTEGER {
                       disabled             (1),
                       enabled              (2)
                    -- enabledWaitForBgp    (3)
                    }
            DESCRIPTION
                 "tmnxOspfBootOverloadAdmState only supports 'disabled (1)' and
                  'enabled (2)'. 'enabledWaitForBgp (3) is not implemented."

        VARIATION   tmnxOspfDemandExtensions
            ACCESS  read-only
            DESCRIPTION
                 "read-only implementation."

        VARIATION   tmnxOspfIfAdvtSubnet
            ACCESS  not-implemented
            DESCRIPTION
                 "Obsolete object."

        VARIATION   tmnxOspfIfDemand
            ACCESS  read-only
            DESCRIPTION
                 "read-only implementation."

        VARIATION   tmnxOspfIfMulticastForwarding
            ACCESS  not-implemented
            DESCRIPTION
                 "Not supported."

        VARIATION   tmnxOspfMulticastExtensions
            ACCESS  not-implemented
            DESCRIPTION
                 "Not supported."

        VARIATION   tmnxOspfMulticastImport
            ACCESS  not-implemented
            DESCRIPTION
                 "Not supported."

        VARIATION   tmnxOspfNbrBfdTracking
            ACCESS  not-implemented
            DESCRIPTION
                 "Not supported."

        VARIATION   tmnxOspfRestartInterval
            ACCESS  read-only
            DESCRIPTION
                 "read-only implementation."

        VARIATION   tmnxOspfRestartSupport
            ACCESS  read-only
            DESCRIPTION
                 "read-only implementation."

        VARIATION   tmnxOspfRsvpShortcut
            ACCESS  not-implemented
            DESCRIPTION
                 "Not supported."

        VARIATION   tmnxOspfStrictLsaChecking
            ACCESS  read-only
            DESCRIPTION
                 "read-only implementation."

        VARIATION   tmnxOspfUnicastImport
            ACCESS  not-implemented
            DESCRIPTION
                 "Not supported."

    ::= { tmnxSASMxpAgentV9v0  12 }

--
-- SASR PIM CAPABILITIES
--
tmnxSASRPimV9v0                   AGENT-CAPABILITIES
    PRODUCT-RELEASE "Alcatel-Lucent SAS"
    STATUS          current
    DESCRIPTION
         "Implementation of PIM protocol capabilities for Alcatel-Lucent SASR
          systems release 9.0."

    SUPPORTS        TIMETRA-PIM-NG-MIB
        INCLUDES {
           tmnxPimIfSecNbrV6v0Group,
           tmnxPimNgEchoGroup,
           tmnxPimNgEmbeddedRPV7v0Group,
           tmnxPimNgGlobalGroupV10v0,
           tmnxPimNgGlobalGroupV8v0,
           tmnxPimNgGlobalGrpSrcV10v0Group,
           tmnxPimNgGlobalGrpSrcV9v0Group,
           tmnxPimNgGlobalSSMV6v1Group,
           tmnxPimNgIfGroup,
           tmnxPimNgIfIPMSIV9v0Group,
           tmnxPimNgIfIpv6BfdV9v0Group,
           tmnxPimNgIfStatsV10v0Group,
           tmnxPimNgIfStatsV7v0Group,
           tmnxPimNgIfStatsV9v0Group,
           tmnxPimNgIfV10v0Group,
           tmnxPimNgIfV8v0Group,
           tmnxPimNgLdpEntryV10v0Group,
           tmnxPimNgMvpnExtranetGroupV10v0,
           tmnxPimNgMvpnV8v0Group,
           tmnxPimNgMvpnV9v0Group,
           tmnxPimNgMvpnV9v0R4Group,
           tmnxPimNgNotificationGroup,
           tmnxPimNgNotificationV7v0Group,
           tmnxPimNgNotifyObjsV7v0Group,
           tmnxPimNgNotifyObjsV8v0Group,
           tmnxPimNgNotifyObjsV9v0Group,
           tmnxPimNgV7v0Group
        }

        VARIATION   vRtrPimNgAFGenMvpnUMHSelection
            SYNTAX  INTEGER {
                       highestip            (0),
                       hashbased            (1)
                    -- tunnelstatus         (2)
                    }
            DESCRIPTION
                 "vRtrPimNgAFGenMvpnUMHSelection does not support the value
                  'tunnelStatus (2)' for version 7.0R1 on Nokia SROS series
                  systems."

        VARIATION   vRtrPimNgAfGenAutoRPDiscovery
            ACCESS  not-implemented
            DESCRIPTION
                 "Not supported."

        VARIATION   vRtrPimNgGenEnableMdtSpt
            ACCESS  not-implemented
            DESCRIPTION
                 "Not supported."

        VARIATION   vRtrPimNgGenLagUsageOptimize
            ACCESS  not-implemented
            DESCRIPTION
                 "Not supported."

        VARIATION   vRtrPimNgIfP2mpLdpTreeJoin
            ACCESS  not-implemented
            DESCRIPTION
                 "Not supported."

        VARIATION   vRtrPimNgMvpnUMHPEStandbyAddr
            SYNTAX  InetAddress (SIZE (4))
            DESCRIPTION
                 "vRtrPimNgMvpnUMHPEStandbyAddr supports only InetAddressType
                  'ipv4'."

        VARIATION   vRtrPimNgMvpnUMHPEStandbyAdrTyp
            SYNTAX  INTEGER {
                    -- unknown              (0)
                       ipv4                 (1)
                    -- ipv6                 (2)
                    -- ipv4z                (3)
                    -- ipv6z                (4)
                    -- dns                  (16)
                    }
            DESCRIPTION
                 "vRtrPimNgMvpnUMHPEStandbyAdrTyp supports only InetAddressType
                  'ipv4'."

        VARIATION   vRtrPimNgRsvpIfSenderAddr
            SYNTAX  InetAddress (SIZE (4))
            DESCRIPTION
                 "vRtrPimNgRsvpIfSenderAddr supports only InetAddressType
                  'ipv4'."

        VARIATION   vRtrPimNgRsvpIfSenderAddrType
            SYNTAX  INTEGER {
                    -- unknown              (0)
                       ipv4                 (1)
                    -- ipv6                 (2)
                    -- ipv4z                (3)
                    -- ipv6z                (4)
                    -- dns                  (16)
                    }
            DESCRIPTION
                 "vRtrPimNgRsvpIfSenderAddrType supports only InetAddressType
                  'ipv4'."

    ::= { tmnxSASRAgentV9v0  33 }

--
-- SASX PIM CAPABILITIES
--
tmnxSASXPimV9v0                   AGENT-CAPABILITIES
    PRODUCT-RELEASE "Alcatel-Lucent SAS"
    STATUS          current
    DESCRIPTION
         "Implementation of PIM protocol capabilities for Alcatel-Lucent SASX
          systems release 9.0."

    SUPPORTS        TIMETRA-PIM-NG-MIB
        INCLUDES {
           tmnxPimIfSecNbrV6v0Group,
           tmnxPimNgEchoGroup,
           tmnxPimNgEmbeddedRPV7v0Group,
           tmnxPimNgGlobalGroupV10v0,
           tmnxPimNgGlobalGroupV8v0,
           tmnxPimNgGlobalGrpSrcV10v0Group,
           tmnxPimNgGlobalGrpSrcV9v0Group,
           tmnxPimNgGlobalSSMV6v1Group,
           tmnxPimNgIfGroup,
           tmnxPimNgIfIPMSIV9v0Group,
           tmnxPimNgIfIpv6BfdV9v0Group,
           tmnxPimNgIfStatsV10v0Group,
           tmnxPimNgIfStatsV7v0Group,
           tmnxPimNgIfStatsV9v0Group,
           tmnxPimNgIfV10v0Group,
           tmnxPimNgIfV8v0Group,
           tmnxPimNgLdpEntryV10v0Group,
           tmnxPimNgMvpnExtranetGroupV10v0,
           tmnxPimNgMvpnV8v0Group,
           tmnxPimNgMvpnV9v0Group,
           tmnxPimNgMvpnV9v0R4Group,
           tmnxPimNgNotificationGroup,
           tmnxPimNgNotificationV7v0Group,
           tmnxPimNgNotifyObjsV7v0Group,
           tmnxPimNgNotifyObjsV8v0Group,
           tmnxPimNgNotifyObjsV9v0Group,
           tmnxPimNgV7v0Group
        }

        VARIATION   vRtrPimNgAFGenMvpnUMHSelection
            SYNTAX  INTEGER {
                       highestip            (0),
                       hashbased            (1)
                    -- tunnelstatus         (2)
                    }
            DESCRIPTION
                 "vRtrPimNgAFGenMvpnUMHSelection does not support the value
                  'tunnelStatus (2)' for version 7.0R1 on Nokia SROS series
                  systems."

        VARIATION   vRtrPimNgAfGenAutoRPDiscovery
            ACCESS  not-implemented
            DESCRIPTION
                 "Not supported."

        VARIATION   vRtrPimNgGenEnableMdtSpt
            ACCESS  not-implemented
            DESCRIPTION
                 "Not supported."

        VARIATION   vRtrPimNgGenLagUsageOptimize
            ACCESS  not-implemented
            DESCRIPTION
                 "Not supported."

        VARIATION   vRtrPimNgIfP2mpLdpTreeJoin
            ACCESS  not-implemented
            DESCRIPTION
                 "Not supported."

        VARIATION   vRtrPimNgMvpnUMHPEStandbyAddr
            SYNTAX  InetAddress (SIZE (4))
            DESCRIPTION
                 "vRtrPimNgMvpnUMHPEStandbyAddr supports only InetAddressType
                  'ipv4'."

        VARIATION   vRtrPimNgMvpnUMHPEStandbyAdrTyp
            SYNTAX  INTEGER {
                    -- unknown              (0)
                       ipv4                 (1)
                    -- ipv6                 (2)
                    -- ipv4z                (3)
                    -- ipv6z                (4)
                    -- dns                  (16)
                    }
            DESCRIPTION
                 "vRtrPimNgMvpnUMHPEStandbyAdrTyp supports only InetAddressType
                  'ipv4'."

        VARIATION   vRtrPimNgRsvpIfSenderAddr
            SYNTAX  InetAddress (SIZE (4))
            DESCRIPTION
                 "vRtrPimNgRsvpIfSenderAddr supports only InetAddressType
                  'ipv4'."

        VARIATION   vRtrPimNgRsvpIfSenderAddrType
            SYNTAX  INTEGER {
                    -- unknown              (0)
                       ipv4                 (1)
                    -- ipv6                 (2)
                    -- ipv4z                (3)
                    -- ipv6z                (4)
                    -- dns                  (16)
                    }
            DESCRIPTION
                 "vRtrPimNgRsvpIfSenderAddrType supports only InetAddressType
                  'ipv4'."

    ::= { tmnxSASXAgentV9v0  33 }

--
-- SASM PIM CAPABILITIES
--
tmnxSASMPimV9v0                   AGENT-CAPABILITIES
    PRODUCT-RELEASE "Alcatel-Lucent SAS"
    STATUS          current
    DESCRIPTION
         "Implementation of PIM protocol capabilities for Alcatel-Lucent SASM
          systems release 9.0."

    SUPPORTS        TIMETRA-PIM-NG-MIB
        INCLUDES {
           tmnxPimIfSecNbrV6v0Group,
           tmnxPimNgEchoGroup,
           tmnxPimNgEmbeddedRPV7v0Group,
           tmnxPimNgGlobalGroupV10v0,
           tmnxPimNgGlobalGroupV8v0,
           tmnxPimNgGlobalGrpSrcV10v0Group,
           tmnxPimNgGlobalGrpSrcV9v0Group,
           tmnxPimNgGlobalSSMV6v1Group,
           tmnxPimNgIfGroup,
           tmnxPimNgIfIPMSIV9v0Group,
           tmnxPimNgIfIpv6BfdV9v0Group,
           tmnxPimNgIfStatsV10v0Group,
           tmnxPimNgIfStatsV7v0Group,
           tmnxPimNgIfStatsV9v0Group,
           tmnxPimNgIfV10v0Group,
           tmnxPimNgIfV8v0Group,
           tmnxPimNgLdpEntryV10v0Group,
           tmnxPimNgMvpnExtranetGroupV10v0,
           tmnxPimNgMvpnV8v0Group,
           tmnxPimNgMvpnV9v0Group,
           tmnxPimNgMvpnV9v0R4Group,
           tmnxPimNgNotificationGroup,
           tmnxPimNgNotificationV7v0Group,
           tmnxPimNgNotifyObjsV7v0Group,
           tmnxPimNgNotifyObjsV8v0Group,
           tmnxPimNgNotifyObjsV9v0Group,
           tmnxPimNgV7v0Group
        }

        VARIATION   vRtrPimNgAFGenMvpnUMHSelection
            SYNTAX  INTEGER {
                       highestip            (0),
                       hashbased            (1)
                    -- tunnelstatus         (2)
                    }
            DESCRIPTION
                 "vRtrPimNgAFGenMvpnUMHSelection does not support the value
                  'tunnelStatus (2)' for version 7.0R1 on Nokia SROS series
                  systems."

        VARIATION   vRtrPimNgAfGenAutoRPDiscovery
            ACCESS  not-implemented
            DESCRIPTION
                 "Not supported."

        VARIATION   vRtrPimNgGenEnableMdtSpt
            ACCESS  not-implemented
            DESCRIPTION
                 "Not supported."

        VARIATION   vRtrPimNgGenLagUsageOptimize
            ACCESS  not-implemented
            DESCRIPTION
                 "Not supported."

        VARIATION   vRtrPimNgIfP2mpLdpTreeJoin
            ACCESS  not-implemented
            DESCRIPTION
                 "Not supported."

        VARIATION   vRtrPimNgMvpnUMHPEStandbyAddr
            SYNTAX  InetAddress (SIZE (4))
            DESCRIPTION
                 "vRtrPimNgMvpnUMHPEStandbyAddr supports only InetAddressType
                  'ipv4'."

        VARIATION   vRtrPimNgMvpnUMHPEStandbyAdrTyp
            SYNTAX  INTEGER {
                    -- unknown              (0)
                       ipv4                 (1)
                    -- ipv6                 (2)
                    -- ipv4z                (3)
                    -- ipv6z                (4)
                    -- dns                  (16)
                    }
            DESCRIPTION
                 "vRtrPimNgMvpnUMHPEStandbyAdrTyp supports only InetAddressType
                  'ipv4'."

        VARIATION   vRtrPimNgRsvpIfSenderAddr
            SYNTAX  InetAddress (SIZE (4))
            DESCRIPTION
                 "vRtrPimNgRsvpIfSenderAddr supports only InetAddressType
                  'ipv4'."

        VARIATION   vRtrPimNgRsvpIfSenderAddrType
            SYNTAX  INTEGER {
                    -- unknown              (0)
                       ipv4                 (1)
                    -- ipv6                 (2)
                    -- ipv4z                (3)
                    -- ipv6z                (4)
                    -- dns                  (16)
                    }
            DESCRIPTION
                 "vRtrPimNgRsvpIfSenderAddrType supports only InetAddressType
                  'ipv4'."

    ::= { tmnxSASMAgentV9v0  33 }

--
-- SAS RMON CAPABILITIES
--
tmnxSASRmonV9v0                   AGENT-CAPABILITIES
    PRODUCT-RELEASE "Alcatel-Lucent SAS"
    STATUS          current
    DESCRIPTION
         "Implementation of Remote Monitoring, RMON, capabilities for
          Alcatel-Lucent SAS systems release 9.0."

    SUPPORTS        HC-RMON-MIB
        INCLUDES {
           etherHistoryHighCapacityGroup,
           etherStatsHighCapacityGroup,
           hcRMONInformationGroup,
           mediaIndependentGroup
        }

        VARIATION   mediaIndependentDataSource
            ACCESS  read-only
            DESCRIPTION
                 "mediaIndependentTable is read-only on SAS-X 7210. The agent
                  creates a row entry in the mediaIndependentTable for each
                  physical port in the system, indexed by the port-id.

                  mediaIndependentTable is read-only on SAS-X 7210. The agent
                  creates a row entry in the mediaIndependentTable for each
                  physical port in the system, indexed by the port-id."

        VARIATION   mediaIndependentIndex
            SYNTAX  InterfaceIndex
            DESCRIPTION
                 "The agent creates a row entry in the mediaIndependentTable for
                  each physical port in the system, indexed by the port-id which
                  is also the ifIndex which has a larger value range than that
                  specified for mediaIndependentIndex in the HC-RMON-MIB.

                  The agent creates a row entry in the mediaIndependentTable
                  for each physical port in the system, indexed by the port-id
                  which is also the ifIndex which has a larger value range than
                  that specified for mediaIndependentIndex in the HC-RMON-MIB."

        VARIATION   mediaIndependentOwner
            ACCESS  read-only
            DESCRIPTION
                 "read-only implementation.

                  read-only implementation."

        VARIATION   mediaIndependentStatus
            ACCESS  read-only
            DESCRIPTION
                 "mediaIndependentTable is read-only on SAS-X 7210. Rows cannot
                  be created in the table by SNMP SET requests. The agent
                  creates a row entry in the mediaIndependentTable for each
                  physical port in the system, indexed by the port-id.

                  mediaIndependentTable is read-only on SAS-X 7210. Rows cannot
                  be created in the table by SNMP SET requests. The agent
                  creates a row entry in the mediaIndependentTable for each
                  physical port in the system, indexed by the port-id."

    SUPPORTS        RMON-MIB
        INCLUDES {
           rmonAlarmGroup,
           rmonEtherStatsGroup,
           rmonEthernetHistoryGroup,
           rmonEventGroup,
           rmonHistoryControlGroup
        }

        VARIATION   etherStatsDataSource
            ACCESS  read-only
            DESCRIPTION
                 "read-only implementation. The agent creates a row entry in the
                  etherStatsTable for each ethernet port in the system, indexed
                  by the port-id.

                  read-only implementation. The agent creates a row entry in
                  the etherStatsTable for each ethernet port in the system,
                  indexed by the port-id."

        VARIATION   etherStatsIndex
            SYNTAX  InterfaceIndex
            DESCRIPTION
                 "The agent creates a row entry in the etherStatsTable for each
                  ethernet port in the system that is indexed by the port-id or
                  ifIndex value which has a larger value range than that
                  specified for etherStatsIndex in the RMON-MIB.

                  The agent creates a row entry in the etherStatsTable for each
                  ethernet port in the system that is indexed by the port-id or
                  ifIndex value which has a larger value range than that
                  specified for etherStatsIndex in the RMON-MIB."

        VARIATION   etherStatsOversizePkts
            DESCRIPTION
                 "etherStatsOversizePkts indicates the total number of packets
                  received that were longer than the maximum frame size for the
                  particular media, usually 12287 octets (excluding framing
                  bits, but including FCS octets), and were otherwise well
                  formed.

                  TIMETRA-PORT-MIB::tmnxPortEtherPkts1519toMax,
                  TIMETRA-PORT-MIB::tmnxPortEtherHCOverPkts1519toMax and
                  TIMETRA-PORT-MIB::tmnxPortEtherHCPkts1519toMax are used to
                  indicate the total number of packets received that were longer
                  than 1518 octets but less than the maximum frame size for the
                  particular media, usually 12287 octets (excluding framing
                  bits, but including FCS octets).

                  etherStatsOversizePkts indicates the total number of packets
                  received that were longer than the maximum frame size for the
                  particular media, usually 12287 octets (excluding framing
                  bits, but including FCS octets), and were otherwise well
                  formed.

                  TIMETRA-PORT-MIB::tmnxPortEtherPkts1519toMax,
                  TIMETRA-PORT-MIB::tmnxPortEtherHCOverPkts1519toMax and
                  TIMETRA-PORT-MIB::tmnxPortEtherHCPkts1519toMax are used to
                  indicate the total number of packets received that were longer
                  than 1518 octets but less than the maximum frame size for the
                  particular media, usually 12287 octets (excluding framing
                  bits, but including FCS octets)."

        VARIATION   etherStatsOwner
            ACCESS  read-only
            DESCRIPTION
                 "read-only implementation.

                  read-only implementation."

        VARIATION   etherStatsStatus
            ACCESS  read-only
            DESCRIPTION
                 "etherStatsTable is read-only on SAS-R 7210. Rows cannot be
                  created by SNMP SET requests. The agent creates a row entry in
                  the etherStatsTable for each ethernet port in the system,
                  indexed by the port-id.

                  etherStatsTable is read-only on SAS-R 7210. Rows cannot be
                  created by SNMP SET requests. The agent creates a row entry in
                  the etherStatsTable for each ethernet port in the system,
                  indexed by the port-id."

    ::= { tmnxSASAgentV9v0   4 }

--
-- SAS RMON CAPABILITIES
--
tmnxSASRmonV9v0                   AGENT-CAPABILITIES
    PRODUCT-RELEASE "Alcatel-Lucent SAS"
    STATUS          current
    DESCRIPTION
         "Implementation of Remote Monitoring, RMON, capabilities for
          Alcatel-Lucent SAS systems release 9.0."

    SUPPORTS        HC-RMON-MIB
        INCLUDES {
           etherHistoryHighCapacityGroup,
           etherStatsHighCapacityGroup,
           hcRMONInformationGroup,
           mediaIndependentGroup
        }

        VARIATION   mediaIndependentDataSource
            ACCESS  read-only
            DESCRIPTION
                 "mediaIndependentTable is read-only on SAS-X 7210. The agent
                  creates a row entry in the mediaIndependentTable for each
                  physical port in the system, indexed by the port-id.

                  mediaIndependentTable is read-only on SAS-X 7210. The agent
                  creates a row entry in the mediaIndependentTable for each
                  physical port in the system, indexed by the port-id."

        VARIATION   mediaIndependentIndex
            SYNTAX  InterfaceIndex
            DESCRIPTION
                 "The agent creates a row entry in the mediaIndependentTable for
                  each physical port in the system, indexed by the port-id which
                  is also the ifIndex which has a larger value range than that
                  specified for mediaIndependentIndex in the HC-RMON-MIB.

                  The agent creates a row entry in the mediaIndependentTable
                  for each physical port in the system, indexed by the port-id
                  which is also the ifIndex which has a larger value range than
                  that specified for mediaIndependentIndex in the HC-RMON-MIB."

        VARIATION   mediaIndependentOwner
            ACCESS  read-only
            DESCRIPTION
                 "read-only implementation.

                  read-only implementation."

        VARIATION   mediaIndependentStatus
            ACCESS  read-only
            DESCRIPTION
                 "mediaIndependentTable is read-only on SAS-X 7210. Rows cannot
                  be created in the table by SNMP SET requests. The agent
                  creates a row entry in the mediaIndependentTable for each
                  physical port in the system, indexed by the port-id.

                  mediaIndependentTable is read-only on SAS-X 7210. Rows cannot
                  be created in the table by SNMP SET requests. The agent
                  creates a row entry in the mediaIndependentTable for each
                  physical port in the system, indexed by the port-id."

    SUPPORTS        RMON-MIB
        INCLUDES {
           rmonAlarmGroup,
           rmonEtherStatsGroup,
           rmonEthernetHistoryGroup,
           rmonEventGroup,
           rmonHistoryControlGroup
        }

        VARIATION   etherStatsDataSource
            ACCESS  read-only
            DESCRIPTION
                 "read-only implementation. The agent creates a row entry in the
                  etherStatsTable for each ethernet port in the system, indexed
                  by the port-id.

                  read-only implementation. The agent creates a row entry in
                  the etherStatsTable for each ethernet port in the system,
                  indexed by the port-id."

        VARIATION   etherStatsIndex
            SYNTAX  InterfaceIndex
            DESCRIPTION
                 "The agent creates a row entry in the etherStatsTable for each
                  ethernet port in the system that is indexed by the port-id or
                  ifIndex value which has a larger value range than that
                  specified for etherStatsIndex in the RMON-MIB.

                  The agent creates a row entry in the etherStatsTable for each
                  ethernet port in the system that is indexed by the port-id or
                  ifIndex value which has a larger value range than that
                  specified for etherStatsIndex in the RMON-MIB."

        VARIATION   etherStatsOversizePkts
            DESCRIPTION
                 "etherStatsOversizePkts indicates the total number of packets
                  received that were longer than the maximum frame size for the
                  particular media, usually 12287 octets (excluding framing
                  bits, but including FCS octets), and were otherwise well
                  formed.

                  TIMETRA-PORT-MIB::tmnxPortEtherPkts1519toMax,
                  TIMETRA-PORT-MIB::tmnxPortEtherHCOverPkts1519toMax and
                  TIMETRA-PORT-MIB::tmnxPortEtherHCPkts1519toMax are used to
                  indicate the total number of packets received that were longer
                  than 1518 octets but less than the maximum frame size for the
                  particular media, usually 12287 octets (excluding framing
                  bits, but including FCS octets).

                  etherStatsOversizePkts indicates the total number of packets
                  received that were longer than the maximum frame size for the
                  particular media, usually 12287 octets (excluding framing
                  bits, but including FCS octets), and were otherwise well
                  formed.

                  TIMETRA-PORT-MIB::tmnxPortEtherPkts1519toMax,
                  TIMETRA-PORT-MIB::tmnxPortEtherHCOverPkts1519toMax and
                  TIMETRA-PORT-MIB::tmnxPortEtherHCPkts1519toMax are used to
                  indicate the total number of packets received that were longer
                  than 1518 octets but less than the maximum frame size for the
                  particular media, usually 12287 octets (excluding framing
                  bits, but including FCS octets)."

        VARIATION   etherStatsOwner
            ACCESS  read-only
            DESCRIPTION
                 "read-only implementation.

                  read-only implementation."

        VARIATION   etherStatsStatus
            ACCESS  read-only
            DESCRIPTION
                 "etherStatsTable is read-only on SAS-R 7210. Rows cannot be
                  created by SNMP SET requests. The agent creates a row entry in
                  the etherStatsTable for each ethernet port in the system,
                  indexed by the port-id.

                  etherStatsTable is read-only on SAS-R 7210. Rows cannot be
                  created by SNMP SET requests. The agent creates a row entry in
                  the etherStatsTable for each ethernet port in the system,
                  indexed by the port-id."

    ::= { tmnxSASAgentV9v0   4 }

--
-- SAS RSVP CAPABILITIES
--
tmnxSASRsvpV9v0                   AGENT-CAPABILITIES
    PRODUCT-RELEASE "Alcatel-Lucent SAS"
    STATUS          current
    DESCRIPTION
         "Implementation of RSVP protocol capabilities for Alcatel-Lucent SAS
          systems release 9.0."

    SUPPORTS        RSVP-MIB
        INCLUDES {
-- EXCLUDE rsvpGenObjects
           rsvpIfGroup,
           rsvpNbrGroup,
           rsvpNotificationGroup
-- EXCLUDE rsvpResvFwdTable
-- EXCLUDE rsvpResvTable
-- EXCLUDE rsvpSenderOutInterfaceTable
-- EXCLUDE rsvpSenderTable
-- EXCLUDE rsvpSessionTable
        }

        VARIATION   lostFlow
            ACCESS  not-implemented
            DESCRIPTION
                 "Not supported.

                  Not supported."

        VARIATION   newFlow
            ACCESS  not-implemented
            DESCRIPTION
                 "Not supported.

                  Not supported."

        VARIATION   rsvpNbrProtocol
            ACCESS  read-only
            DESCRIPTION
                 "read-only implementation.

                  read-only implementation."

        VARIATION   rsvpNbrStatus
            ACCESS  read-only
            DESCRIPTION
                 "rsvpNbrTable is implemented as read-only. Row entries cannot
                  be created by SNMP SET requests.

                  rsvpNbrTable is implemented as read-only. Row entries cannot
                  be created by SNMP SET requests."

    SUPPORTS        TIMETRA-RSVP-MIB
        INCLUDES {
           tmnxRsvpGeneralGroup,
           tmnxRsvpGeneralV6v0Group,
           tmnxRsvpGeneralV6v1Group,
           tmnxRsvpGeneralV7v0Group,
           tmnxRsvpIfV5v0Group,
           tmnxRsvpIfV6v0Group,
           tmnxRsvpNbrV6v0Group,
           tmnxRsvpNotificationGroup,
           tmnxRsvpSessionGroup,
           tmnxRsvpSessionV5v0Group,
           tmnxRsvpSessionV6v0Group
        }

        VARIATION   vRtrRsvpDSTEAdmCtlModel
            SYNTAX  INTEGER {
                       basic                (0),
                       mam                  (1)
                    -- rdm                  (2)
                    }
            DESCRIPTION
                 "vRtrRsvpDSTEAdmCtlModel does not support the value 'rdm'.

                  vRtrRsvpDSTEAdmCtlModel does not support the value 'rdm'."

        VARIATION   vRtrRsvpGeneralRefreshBypass
            ACCESS  not-implemented
            DESCRIPTION
                 "Not supported.

                  Not supported."

        VARIATION   vRtrRsvpIfAggregate
            ACCESS  read-only
            DESCRIPTION
                 "read-only implementation.

                  read-only implementation."

        VARIATION   vRtrRsvpIfAuthChallenge
            ACCESS  not-implemented
            DESCRIPTION
                 "vRtrRsvpIfAuthChallenge is not supported.

                  vRtrRsvpIfAuthChallenge is not supported."

        VARIATION   vRtrRsvpIfKeepMultiplier
            ACCESS  not-implemented
            DESCRIPTION
                 "vRtrRsvpIfKeepMultiplier is obsolete.

                  vRtrRsvpIfKeepMultiplier is obsolete."

        VARIATION   vRtrRsvpIfRefreshTime
            ACCESS  not-implemented
            DESCRIPTION
                 "vRtrRsvpIfRefreshTime is obsolete.

                  vRtrRsvpIfRefreshTime is obsolete."

    ::= { tmnxSASAgentV9v0  13 }

--
-- SAS RSVP CAPABILITIES
--
tmnxSASRsvpV9v0                   AGENT-CAPABILITIES
    PRODUCT-RELEASE "Alcatel-Lucent SAS"
    STATUS          current
    DESCRIPTION
         "Implementation of RSVP protocol capabilities for Alcatel-Lucent SAS
          systems release 9.0."

    SUPPORTS        RSVP-MIB
        INCLUDES {
-- EXCLUDE rsvpGenObjects
           rsvpIfGroup,
           rsvpNbrGroup,
           rsvpNotificationGroup
-- EXCLUDE rsvpResvFwdTable
-- EXCLUDE rsvpResvTable
-- EXCLUDE rsvpSenderOutInterfaceTable
-- EXCLUDE rsvpSenderTable
-- EXCLUDE rsvpSessionTable
        }

        VARIATION   lostFlow
            ACCESS  not-implemented
            DESCRIPTION
                 "Not supported.

                  Not supported."

        VARIATION   newFlow
            ACCESS  not-implemented
            DESCRIPTION
                 "Not supported.

                  Not supported."

        VARIATION   rsvpNbrProtocol
            ACCESS  read-only
            DESCRIPTION
                 "read-only implementation.

                  read-only implementation."

        VARIATION   rsvpNbrStatus
            ACCESS  read-only
            DESCRIPTION
                 "rsvpNbrTable is implemented as read-only. Row entries cannot
                  be created by SNMP SET requests.

                  rsvpNbrTable is implemented as read-only. Row entries cannot
                  be created by SNMP SET requests."

    SUPPORTS        TIMETRA-RSVP-MIB
        INCLUDES {
           tmnxRsvpGeneralGroup,
           tmnxRsvpGeneralV6v0Group,
           tmnxRsvpGeneralV6v1Group,
           tmnxRsvpGeneralV7v0Group,
           tmnxRsvpIfV5v0Group,
           tmnxRsvpIfV6v0Group,
           tmnxRsvpNbrV6v0Group,
           tmnxRsvpNotificationGroup,
           tmnxRsvpSessionGroup,
           tmnxRsvpSessionV5v0Group,
           tmnxRsvpSessionV6v0Group
        }

        VARIATION   vRtrRsvpDSTEAdmCtlModel
            SYNTAX  INTEGER {
                       basic                (0),
                       mam                  (1)
                    -- rdm                  (2)
                    }
            DESCRIPTION
                 "vRtrRsvpDSTEAdmCtlModel does not support the value 'rdm'.

                  vRtrRsvpDSTEAdmCtlModel does not support the value 'rdm'."

        VARIATION   vRtrRsvpGeneralRefreshBypass
            ACCESS  not-implemented
            DESCRIPTION
                 "Not supported.

                  Not supported."

        VARIATION   vRtrRsvpIfAggregate
            ACCESS  read-only
            DESCRIPTION
                 "read-only implementation.

                  read-only implementation."

        VARIATION   vRtrRsvpIfAuthChallenge
            ACCESS  not-implemented
            DESCRIPTION
                 "vRtrRsvpIfAuthChallenge is not supported.

                  vRtrRsvpIfAuthChallenge is not supported."

        VARIATION   vRtrRsvpIfKeepMultiplier
            ACCESS  not-implemented
            DESCRIPTION
                 "vRtrRsvpIfKeepMultiplier is obsolete.

                  vRtrRsvpIfKeepMultiplier is obsolete."

        VARIATION   vRtrRsvpIfRefreshTime
            ACCESS  not-implemented
            DESCRIPTION
                 "vRtrRsvpIfRefreshTime is obsolete.

                  vRtrRsvpIfRefreshTime is obsolete."

    ::= { tmnxSASAgentV9v0  13 }

--
-- SASK RSVP CAPABILITIES
--
tmnxSASKRsvpV9v0                  AGENT-CAPABILITIES
    PRODUCT-RELEASE "Alcatel-Lucent SAS"
    STATUS          current
    DESCRIPTION
         "Implementation of RSVP protocol capabilities for Alcatel-Lucent SASK
          systems release 9.0."

--    SUPPORTS        RSVP-MIB
--        INCLUDES {
--        }

--    SUPPORTS        TIMETRA-RSVP-MIB
--        INCLUDES {
--        }

    ::= { tmnxSASKAgentV9v0  13 }

--
-- SAS SAP CAPABILITIES
--
tmnxSASSapV9v0                    AGENT-CAPABILITIES
    PRODUCT-RELEASE "Alcatel-Lucent SAS"
    STATUS          current
    DESCRIPTION
         "Implementation of SAP capabilities for Alcatel-Lucent SAS systems
          release 9.0."

    SUPPORTS        TIMETRA-SAP-MIB
        INCLUDES {
           tmnxSapArpHostGroup,
           tmnxSapBaseV6v0Group,
           tmnxSapCemNotificationV6v0Group,
           tmnxSapCemV6v0Group,
           tmnxSapDhcpV8v0Group,
           tmnxSapL2ptV6v0Group,
           tmnxSapMstiV6v0Group,
           tmnxSapNotifyGroup,
           tmnxSapPolicyV6v0Group,
           tmnxSapTlsV6v1Group,
           tmnxSapTlsV8v0Group,
           tmnxSapV10v0Group,
           tmnxSapV7v0Group
        }

        VARIATION   msapTlsPlcyArpHostMaxNumHosts
            ACCESS  not-implemented
            DESCRIPTION
                 "Not supported.

                  Not supported."

        VARIATION   msapTlsPlcyArpHostMinAuthIntvl
            ACCESS  not-implemented
            DESCRIPTION
                 "Not supported.

                  Not supported."

        VARIATION   sapAntiSpoofing
            ACCESS  not-implemented
            DESCRIPTION
                 "Not supported.

                  Not supported."

        VARIATION   sapBaseStatsAuthenticationPktsDiscarded
            ACCESS  not-implemented
            DESCRIPTION
                 "Not supported.

                  Not supported.

                  Not supported.

                  Not supported."

        VARIATION   sapBaseStatsAuthenticationPktsSuccess
            ACCESS  not-implemented
            DESCRIPTION
                 "Not supported.

                  Not supported.

                  Not supported.

                  Not supported."

        VARIATION   sapBaseStatsEgressQchipDroppedInProfOctets
            ACCESS  not-implemented
            DESCRIPTION
                 "Not supported.

                  Not supported."

        VARIATION   sapBaseStatsEgressQchipDroppedInProfPackets
            ACCESS  not-implemented
            DESCRIPTION
                 "Not supported.

                  Not supported."

        VARIATION   sapBaseStatsEgressQchipDroppedOutProfOctets
            ACCESS  not-implemented
            DESCRIPTION
                 "Not supported.

                  Not supported."

        VARIATION   sapBaseStatsEgressQchipDroppedOutProfPackets
            ACCESS  not-implemented
            DESCRIPTION
                 "Not supported.

                  Not supported."

        VARIATION   sapBaseStatsEgressQchipForwardedInProfOctets
            ACCESS  not-implemented
            DESCRIPTION
                 "Not supported.

                  Not supported."

        VARIATION   sapBaseStatsEgressQchipForwardedInProfPackets
            ACCESS  not-implemented
            DESCRIPTION
                 "Not supported.

                  Not supported."

        VARIATION   sapBaseStatsEgressQchipForwardedOutProfOctets
            ACCESS  not-implemented
            DESCRIPTION
                 "Not supported.

                  Not supported."

        VARIATION   sapBaseStatsEgressQchipForwardedOutProfPackets
            ACCESS  not-implemented
            DESCRIPTION
                 "Not supported.

                  Not supported."

        VARIATION   sapBaseStatsIngressPchipDroppedOctets
            ACCESS  not-implemented
            DESCRIPTION
                 "Not supported.

                  Not supported."

        VARIATION   sapBaseStatsIngressPchipDroppedPackets
            ACCESS  not-implemented
            DESCRIPTION
                 "Not supported.

                  Not supported."

        VARIATION   sapBaseStatsIngressPchipOfferedHiPrioOctets
            ACCESS  not-implemented
            DESCRIPTION
                 "Not supported.

                  Not supported."

        VARIATION   sapBaseStatsIngressPchipOfferedHiPrioPackets
            ACCESS  not-implemented
            DESCRIPTION
                 "Not supported.

                  Not supported."

        VARIATION   sapBaseStatsIngressPchipOfferedLoPrioOctets
            ACCESS  not-implemented
            DESCRIPTION
                 "Not supported.

                  Not supported."

        VARIATION   sapBaseStatsIngressPchipOfferedLoPrioPackets
            ACCESS  not-implemented
            DESCRIPTION
                 "Not supported.

                  Not supported."

        VARIATION   sapBaseStatsIngressPchipOfferedUncoloredOctets
            ACCESS  not-implemented
            DESCRIPTION
                 "Not supported.

                  Not supported."

        VARIATION   sapBaseStatsIngressPchipOfferedUncoloredPackets
            ACCESS  not-implemented
            DESCRIPTION
                 "Not supported.

                  Not supported."

        VARIATION   sapBaseStatsIngressQchipDroppedHiPrioOctets
            ACCESS  not-implemented
            DESCRIPTION
                 "Not supported.

                  Not supported."

        VARIATION   sapBaseStatsIngressQchipDroppedHiPrioPackets
            ACCESS  not-implemented
            DESCRIPTION
                 "Not supported.

                  Not supported."

        VARIATION   sapBaseStatsIngressQchipDroppedLoPrioOctets
            ACCESS  not-implemented
            DESCRIPTION
                 "Not supported.

                  Not supported."

        VARIATION   sapBaseStatsIngressQchipDroppedLoPrioPackets
            ACCESS  not-implemented
            DESCRIPTION
                 "Not supported.

                  Not supported."

        VARIATION   sapBaseStatsIngressQchipForwardedInProfOctets
            ACCESS  not-implemented
            DESCRIPTION
                 "Not supported.

                  Not supported."

        VARIATION   sapBaseStatsIngressQchipForwardedInProfPackets
            ACCESS  not-implemented
            DESCRIPTION
                 "Not supported.

                  Not supported."

        VARIATION   sapBaseStatsIngressQchipForwardedOutProfOctets
            ACCESS  not-implemented
            DESCRIPTION
                 "Not supported.

                  Not supported."

        VARIATION   sapBaseStatsIngressQchipForwardedOutProfPackets
            ACCESS  not-implemented
            DESCRIPTION
                 "Not supported.

                  Not supported."

        VARIATION   sapCemDifferential
            ACCESS  not-implemented
            DESCRIPTION
                 "Not supported.

                  Not supported."

        VARIATION   sapCemLocalEcid
            ACCESS  not-implemented
            DESCRIPTION
                 "Not supported.

                  Not supported."

        VARIATION   sapCemRemoteEcid
            ACCESS  not-implemented
            DESCRIPTION
                 "Not supported.

                  Not supported."

        VARIATION   sapCemRemoteMacAddr
            ACCESS  not-implemented
            DESCRIPTION
                 "Not supported.

                  Not supported."

        VARIATION   sapCemTimestampFreq
            ACCESS  not-implemented
            DESCRIPTION
                 "Not supported.

                  Not supported."

        VARIATION   sapCustMultSvcSite
            ACCESS  not-implemented
            DESCRIPTION
                 "Not supported.

                  Not supported."

        VARIATION   sapEgressFrameBasedAccounting
            ACCESS  not-implemented
            DESCRIPTION
                 "Not supported.

                  Not supported."

        VARIATION   sapEgressQinQMarkTopOnly
            ACCESS  not-implemented
            DESCRIPTION
                 "Not supported.

                  Not supported."

        VARIATION   sapIngUseMultipointShared
            ACCESS  not-implemented
            DESCRIPTION
                 "Not supported.

                  Not supported."

        VARIATION   sapIngressMatchQinQDot1PBits
            ACCESS  not-implemented
            DESCRIPTION
                 "Not supported.

                  Not supported."

        VARIATION   sapIngressSharedQueuePolicy
            ACCESS  not-implemented
            DESCRIPTION
                 "Not supported.

                  Not supported."

        VARIATION   sapIngressVlanTranslation
            ACCESS  not-implemented
            DESCRIPTION
                 "Not supported.

                  Not supported."

        VARIATION   sapIngressVlanTranslationId
            ACCESS  not-implemented
            DESCRIPTION
                 "Not supported.

                  Not supported."

        VARIATION   sapStaticHostMRtLastMgmtChange
            ACCESS  not-implemented
            DESCRIPTION
                 "Not supported (No Routed Subscriber Host feature).

                  Not supported (No Routed Subscriber Host feature)."

        VARIATION   sapStaticHostMRtRowStatus
            ACCESS  not-implemented
            DESCRIPTION
                 "Not supported (No Routed Subscriber Host feature).

                  Not supported (No Routed Subscriber Host feature)."

        VARIATION   sapStaticHostMRtStatus
            ACCESS  not-implemented
            DESCRIPTION
                 "Not supported (No Routed Subscriber Host feature).

                  Not supported (No Routed Subscriber Host feature)."

        VARIATION   sapStaticHostMRtTblLastChgd
            ACCESS  not-implemented
            DESCRIPTION
                 "Not supported (No Routed Subscriber Host feature).

                  Not supported (No Routed Subscriber Host feature)."

        VARIATION   sapTlsArpReplyAgent
            ACCESS  not-implemented
            DESCRIPTION
                 "Not supported.

                  Not supported."

        VARIATION   sapTlsAuthenticationPolicy
            ACCESS  not-implemented
            DESCRIPTION
                 "Not supported.

                  Not supported."

        VARIATION   sapTlsDhcpLeasePopulate
            ACCESS  not-implemented
            DESCRIPTION
                 "Not supported.

                  Not supported."

        VARIATION   sapTlsDhcpOperLeasePopulate
            ACCESS  not-implemented
            DESCRIPTION
                 "Not supported.

                  Not supported."

        VARIATION   sapTlsDhcpProxyAdminState
            ACCESS  not-implemented
            DESCRIPTION
                 "Not supported.

                  Not supported."

        VARIATION   sapTlsDhcpProxyLTRadiusOverride
            ACCESS  not-implemented
            DESCRIPTION
                 "Not supported.

                  Not supported."

        VARIATION   sapTlsDhcpProxyLeaseTime
            ACCESS  not-implemented
            DESCRIPTION
                 "Not supported.

                  Not supported."

        VARIATION   sapTlsDhcpProxyServerAddr
            ACCESS  not-implemented
            DESCRIPTION
                 "Not supported.

                  Not supported."

        VARIATION   sapTlsDhcpUserDb
            ACCESS  not-implemented
            DESCRIPTION
                 "Not supported.

                  Not supported."

        VARIATION   sapTlsEgressMcastGroup
            ACCESS  not-implemented
            DESCRIPTION
                 "Not supported.

                  Not supported."

        VARIATION   sapTlsL2ptForceBoundary
            ACCESS  not-implemented
            DESCRIPTION
                 "Not supported.

                  Not supported."

        VARIATION   sapTlsL2ptForceProtocols
            ACCESS  not-implemented
            DESCRIPTION
                 "Not supported.

                  Not supported."

        VARIATION   sapTlsMvplsMgmtMsti
            ACCESS  not-implemented
            DESCRIPTION
                 "Not supported.

                  Not supported."

        VARIATION   sapTlsRestProtSrcMac
            ACCESS  not-implemented
            DESCRIPTION
                 "Not supported.

                  Not supported."

        VARIATION   sapTlsRestProtSrcMacAction
            ACCESS  not-implemented
            DESCRIPTION
                 "Not supported.

                  Not supported."

        VARIATION   sapTlsRestUnprotDstMac
            ACCESS  not-implemented
            DESCRIPTION
                 "Not supported.

                  Not supported."

        VARIATION   sapTlsShcvAction
            ACCESS  not-implemented
            DESCRIPTION
                 "Not supported.

                  Not supported."

        VARIATION   sapTlsShcvInterval
            ACCESS  not-implemented
            DESCRIPTION
                 "Not supported.

                  Not supported."

        VARIATION   sapTlsShcvSrcIp
            ACCESS  not-implemented
            DESCRIPTION
                 "Not supported.

                  Not supported."

        VARIATION   sapTlsShcvSrcMac
            ACCESS  not-implemented
            DESCRIPTION
                 "Not supported.

                  Not supported."

        VARIATION   sapTlsStpBpduEncap
            SYNTAX  INTEGER {
                       dynamic              (1)
                    }
            DESCRIPTION
                 "The only value that can be assigned to sapTlsStpBpduEncap is
                  'dynamic (1)'. Additional values may be supported in a later
                  release.

                  The only value that can be assigned to sapTlsStpBpduEncap is
                  'dynamic (1)'. Additional values may be supported in a later
                  release."

        VARIATION   sapTlsStpInMstBpdus
            ACCESS  not-implemented
            DESCRIPTION
                 "Not supported.

                  Not supported."

        VARIATION   sapTlsStpInsideRegion
            ACCESS  not-implemented
            DESCRIPTION
                 "Not supported.

                  Not supported."

        VARIATION   sapTlsStpOutMstBpdus
            ACCESS  not-implemented
            DESCRIPTION
                 "Not supported.

                  Not supported."

    ::= { tmnxSASAgentV9v0  24 }

--
-- SAS SAP CAPABILITIES
--
tmnxSASSapV9v0                    AGENT-CAPABILITIES
    PRODUCT-RELEASE "Alcatel-Lucent SAS"
    STATUS          current
    DESCRIPTION
         "Implementation of SAP capabilities for Alcatel-Lucent SAS systems
          release 9.0."

    SUPPORTS        TIMETRA-SAP-MIB
        INCLUDES {
           tmnxSapArpHostGroup,
           tmnxSapBaseV6v0Group,
           tmnxSapCemNotificationV6v0Group,
           tmnxSapCemV6v0Group,
           tmnxSapDhcpV8v0Group,
           tmnxSapL2ptV6v0Group,
           tmnxSapMstiV6v0Group,
           tmnxSapNotifyGroup,
           tmnxSapPolicyV6v0Group,
           tmnxSapTlsV6v1Group,
           tmnxSapTlsV8v0Group,
           tmnxSapV10v0Group,
           tmnxSapV7v0Group
        }

        VARIATION   msapTlsPlcyArpHostMaxNumHosts
            ACCESS  not-implemented
            DESCRIPTION
                 "Not supported.

                  Not supported."

        VARIATION   msapTlsPlcyArpHostMinAuthIntvl
            ACCESS  not-implemented
            DESCRIPTION
                 "Not supported.

                  Not supported."

        VARIATION   sapAntiSpoofing
            ACCESS  not-implemented
            DESCRIPTION
                 "Not supported.

                  Not supported."

        VARIATION   sapBaseStatsAuthenticationPktsDiscarded
            ACCESS  not-implemented
            DESCRIPTION
                 "Not supported.

                  Not supported.

                  Not supported.

                  Not supported."

        VARIATION   sapBaseStatsAuthenticationPktsSuccess
            ACCESS  not-implemented
            DESCRIPTION
                 "Not supported.

                  Not supported.

                  Not supported.

                  Not supported."

        VARIATION   sapBaseStatsEgressQchipDroppedInProfOctets
            ACCESS  not-implemented
            DESCRIPTION
                 "Not supported.

                  Not supported."

        VARIATION   sapBaseStatsEgressQchipDroppedInProfPackets
            ACCESS  not-implemented
            DESCRIPTION
                 "Not supported.

                  Not supported."

        VARIATION   sapBaseStatsEgressQchipDroppedOutProfOctets
            ACCESS  not-implemented
            DESCRIPTION
                 "Not supported.

                  Not supported."

        VARIATION   sapBaseStatsEgressQchipDroppedOutProfPackets
            ACCESS  not-implemented
            DESCRIPTION
                 "Not supported.

                  Not supported."

        VARIATION   sapBaseStatsEgressQchipForwardedInProfOctets
            ACCESS  not-implemented
            DESCRIPTION
                 "Not supported.

                  Not supported."

        VARIATION   sapBaseStatsEgressQchipForwardedInProfPackets
            ACCESS  not-implemented
            DESCRIPTION
                 "Not supported.

                  Not supported."

        VARIATION   sapBaseStatsEgressQchipForwardedOutProfOctets
            ACCESS  not-implemented
            DESCRIPTION
                 "Not supported.

                  Not supported."

        VARIATION   sapBaseStatsEgressQchipForwardedOutProfPackets
            ACCESS  not-implemented
            DESCRIPTION
                 "Not supported.

                  Not supported."

        VARIATION   sapBaseStatsIngressPchipDroppedOctets
            ACCESS  not-implemented
            DESCRIPTION
                 "Not supported.

                  Not supported."

        VARIATION   sapBaseStatsIngressPchipDroppedPackets
            ACCESS  not-implemented
            DESCRIPTION
                 "Not supported.

                  Not supported."

        VARIATION   sapBaseStatsIngressPchipOfferedHiPrioOctets
            ACCESS  not-implemented
            DESCRIPTION
                 "Not supported.

                  Not supported."

        VARIATION   sapBaseStatsIngressPchipOfferedHiPrioPackets
            ACCESS  not-implemented
            DESCRIPTION
                 "Not supported.

                  Not supported."

        VARIATION   sapBaseStatsIngressPchipOfferedLoPrioOctets
            ACCESS  not-implemented
            DESCRIPTION
                 "Not supported.

                  Not supported."

        VARIATION   sapBaseStatsIngressPchipOfferedLoPrioPackets
            ACCESS  not-implemented
            DESCRIPTION
                 "Not supported.

                  Not supported."

        VARIATION   sapBaseStatsIngressPchipOfferedUncoloredOctets
            ACCESS  not-implemented
            DESCRIPTION
                 "Not supported.

                  Not supported."

        VARIATION   sapBaseStatsIngressPchipOfferedUncoloredPackets
            ACCESS  not-implemented
            DESCRIPTION
                 "Not supported.

                  Not supported."

        VARIATION   sapBaseStatsIngressQchipDroppedHiPrioOctets
            ACCESS  not-implemented
            DESCRIPTION
                 "Not supported.

                  Not supported."

        VARIATION   sapBaseStatsIngressQchipDroppedHiPrioPackets
            ACCESS  not-implemented
            DESCRIPTION
                 "Not supported.

                  Not supported."

        VARIATION   sapBaseStatsIngressQchipDroppedLoPrioOctets
            ACCESS  not-implemented
            DESCRIPTION
                 "Not supported.

                  Not supported."

        VARIATION   sapBaseStatsIngressQchipDroppedLoPrioPackets
            ACCESS  not-implemented
            DESCRIPTION
                 "Not supported.

                  Not supported."

        VARIATION   sapBaseStatsIngressQchipForwardedInProfOctets
            ACCESS  not-implemented
            DESCRIPTION
                 "Not supported.

                  Not supported."

        VARIATION   sapBaseStatsIngressQchipForwardedInProfPackets
            ACCESS  not-implemented
            DESCRIPTION
                 "Not supported.

                  Not supported."

        VARIATION   sapBaseStatsIngressQchipForwardedOutProfOctets
            ACCESS  not-implemented
            DESCRIPTION
                 "Not supported.

                  Not supported."

        VARIATION   sapBaseStatsIngressQchipForwardedOutProfPackets
            ACCESS  not-implemented
            DESCRIPTION
                 "Not supported.

                  Not supported."

        VARIATION   sapCemDifferential
            ACCESS  not-implemented
            DESCRIPTION
                 "Not supported.

                  Not supported."

        VARIATION   sapCemLocalEcid
            ACCESS  not-implemented
            DESCRIPTION
                 "Not supported.

                  Not supported."

        VARIATION   sapCemRemoteEcid
            ACCESS  not-implemented
            DESCRIPTION
                 "Not supported.

                  Not supported."

        VARIATION   sapCemRemoteMacAddr
            ACCESS  not-implemented
            DESCRIPTION
                 "Not supported.

                  Not supported."

        VARIATION   sapCemTimestampFreq
            ACCESS  not-implemented
            DESCRIPTION
                 "Not supported.

                  Not supported."

        VARIATION   sapCustMultSvcSite
            ACCESS  not-implemented
            DESCRIPTION
                 "Not supported.

                  Not supported."

        VARIATION   sapEgressFrameBasedAccounting
            ACCESS  not-implemented
            DESCRIPTION
                 "Not supported.

                  Not supported."

        VARIATION   sapEgressQinQMarkTopOnly
            ACCESS  not-implemented
            DESCRIPTION
                 "Not supported.

                  Not supported."

        VARIATION   sapIngUseMultipointShared
            ACCESS  not-implemented
            DESCRIPTION
                 "Not supported.

                  Not supported."

        VARIATION   sapIngressMatchQinQDot1PBits
            ACCESS  not-implemented
            DESCRIPTION
                 "Not supported.

                  Not supported."

        VARIATION   sapIngressSharedQueuePolicy
            ACCESS  not-implemented
            DESCRIPTION
                 "Not supported.

                  Not supported."

        VARIATION   sapIngressVlanTranslation
            ACCESS  not-implemented
            DESCRIPTION
                 "Not supported.

                  Not supported."

        VARIATION   sapIngressVlanTranslationId
            ACCESS  not-implemented
            DESCRIPTION
                 "Not supported.

                  Not supported."

        VARIATION   sapStaticHostMRtLastMgmtChange
            ACCESS  not-implemented
            DESCRIPTION
                 "Not supported (No Routed Subscriber Host feature).

                  Not supported (No Routed Subscriber Host feature)."

        VARIATION   sapStaticHostMRtRowStatus
            ACCESS  not-implemented
            DESCRIPTION
                 "Not supported (No Routed Subscriber Host feature).

                  Not supported (No Routed Subscriber Host feature)."

        VARIATION   sapStaticHostMRtStatus
            ACCESS  not-implemented
            DESCRIPTION
                 "Not supported (No Routed Subscriber Host feature).

                  Not supported (No Routed Subscriber Host feature)."

        VARIATION   sapStaticHostMRtTblLastChgd
            ACCESS  not-implemented
            DESCRIPTION
                 "Not supported (No Routed Subscriber Host feature).

                  Not supported (No Routed Subscriber Host feature)."

        VARIATION   sapTlsArpReplyAgent
            ACCESS  not-implemented
            DESCRIPTION
                 "Not supported.

                  Not supported."

        VARIATION   sapTlsAuthenticationPolicy
            ACCESS  not-implemented
            DESCRIPTION
                 "Not supported.

                  Not supported."

        VARIATION   sapTlsDhcpLeasePopulate
            ACCESS  not-implemented
            DESCRIPTION
                 "Not supported.

                  Not supported."

        VARIATION   sapTlsDhcpOperLeasePopulate
            ACCESS  not-implemented
            DESCRIPTION
                 "Not supported.

                  Not supported."

        VARIATION   sapTlsDhcpProxyAdminState
            ACCESS  not-implemented
            DESCRIPTION
                 "Not supported.

                  Not supported."

        VARIATION   sapTlsDhcpProxyLTRadiusOverride
            ACCESS  not-implemented
            DESCRIPTION
                 "Not supported.

                  Not supported."

        VARIATION   sapTlsDhcpProxyLeaseTime
            ACCESS  not-implemented
            DESCRIPTION
                 "Not supported.

                  Not supported."

        VARIATION   sapTlsDhcpProxyServerAddr
            ACCESS  not-implemented
            DESCRIPTION
                 "Not supported.

                  Not supported."

        VARIATION   sapTlsDhcpUserDb
            ACCESS  not-implemented
            DESCRIPTION
                 "Not supported.

                  Not supported."

        VARIATION   sapTlsEgressMcastGroup
            ACCESS  not-implemented
            DESCRIPTION
                 "Not supported.

                  Not supported."

        VARIATION   sapTlsL2ptForceBoundary
            ACCESS  not-implemented
            DESCRIPTION
                 "Not supported.

                  Not supported."

        VARIATION   sapTlsL2ptForceProtocols
            ACCESS  not-implemented
            DESCRIPTION
                 "Not supported.

                  Not supported."

        VARIATION   sapTlsMvplsMgmtMsti
            ACCESS  not-implemented
            DESCRIPTION
                 "Not supported.

                  Not supported."

        VARIATION   sapTlsRestProtSrcMac
            ACCESS  not-implemented
            DESCRIPTION
                 "Not supported.

                  Not supported."

        VARIATION   sapTlsRestProtSrcMacAction
            ACCESS  not-implemented
            DESCRIPTION
                 "Not supported.

                  Not supported."

        VARIATION   sapTlsRestUnprotDstMac
            ACCESS  not-implemented
            DESCRIPTION
                 "Not supported.

                  Not supported."

        VARIATION   sapTlsShcvAction
            ACCESS  not-implemented
            DESCRIPTION
                 "Not supported.

                  Not supported."

        VARIATION   sapTlsShcvInterval
            ACCESS  not-implemented
            DESCRIPTION
                 "Not supported.

                  Not supported."

        VARIATION   sapTlsShcvSrcIp
            ACCESS  not-implemented
            DESCRIPTION
                 "Not supported.

                  Not supported."

        VARIATION   sapTlsShcvSrcMac
            ACCESS  not-implemented
            DESCRIPTION
                 "Not supported.

                  Not supported."

        VARIATION   sapTlsStpBpduEncap
            SYNTAX  INTEGER {
                       dynamic              (1)
                    }
            DESCRIPTION
                 "The only value that can be assigned to sapTlsStpBpduEncap is
                  'dynamic (1)'. Additional values may be supported in a later
                  release.

                  The only value that can be assigned to sapTlsStpBpduEncap is
                  'dynamic (1)'. Additional values may be supported in a later
                  release."

        VARIATION   sapTlsStpInMstBpdus
            ACCESS  not-implemented
            DESCRIPTION
                 "Not supported.

                  Not supported."

        VARIATION   sapTlsStpInsideRegion
            ACCESS  not-implemented
            DESCRIPTION
                 "Not supported.

                  Not supported."

        VARIATION   sapTlsStpOutMstBpdus
            ACCESS  not-implemented
            DESCRIPTION
                 "Not supported.

                  Not supported."

    ::= { tmnxSASAgentV9v0  24 }

--
-- SAS SCHEDULER CAPABILITIES
--
tmnxSASSchedulerV9v0              AGENT-CAPABILITIES
    PRODUCT-RELEASE "Alcatel-Lucent SAS"
    STATUS          current
    DESCRIPTION
         "Implementation of time of day (tod) policies for Alcatel-Lucent SAS
          systems release 9.0."

    SUPPORTS        TIMETRA-SCHEDULER-MIB
        INCLUDES {
           tmnxCronSchedV5v0Group,
           tmnxTodPolicyV5v0Group
        }

        VARIATION   tTodSuiteOprEgrIpv6FilterIndex
            ACCESS  not-implemented
            DESCRIPTION
                 "Not supported.

                  Not supported."

        VARIATION   tTodSuiteOprIngrIpv6FilterIndex
            ACCESS  not-implemented
            DESCRIPTION
                 "Not supported.

                  Not supported."

        VARIATION   tmnxTodToolRetryIPv6FltrDownload
            ACCESS  not-implemented
            DESCRIPTION
                 "Not supported.

                  Not supported."

    ::= { tmnxSASAgentV9v0  21 }

--
-- SAS SCHEDULER CAPABILITIES
--
tmnxSASSchedulerV9v0              AGENT-CAPABILITIES
    PRODUCT-RELEASE "Alcatel-Lucent SAS"
    STATUS          current
    DESCRIPTION
         "Implementation of time of day (tod) policies for Alcatel-Lucent SAS
          systems release 9.0."

    SUPPORTS        TIMETRA-SCHEDULER-MIB
        INCLUDES {
           tmnxCronSchedV5v0Group,
           tmnxTodPolicyV5v0Group
        }

        VARIATION   tTodSuiteOprEgrIpv6FilterIndex
            ACCESS  not-implemented
            DESCRIPTION
                 "Not supported.

                  Not supported."

        VARIATION   tTodSuiteOprIngrIpv6FilterIndex
            ACCESS  not-implemented
            DESCRIPTION
                 "Not supported.

                  Not supported."

        VARIATION   tmnxTodToolRetryIPv6FltrDownload
            ACCESS  not-implemented
            DESCRIPTION
                 "Not supported.

                  Not supported."

    ::= { tmnxSASAgentV9v0  21 }

--
-- SAS SDP CAPABILITIES
--
tmnxSASSdpV9v0                    AGENT-CAPABILITIES
    PRODUCT-RELEASE "Alcatel-Lucent SAS"
    STATUS          current
    DESCRIPTION
         "Implementation of SDP capabilities for Alcatel-Lucent SAS systems
          release 9.0."

    SUPPORTS        TIMETRA-SDP-MIB
        INCLUDES {
           tmnxSdpBindCpipeV6v0Group,
           tmnxSdpBindMeshV6v0Group,
           tmnxSdpBindTlsL2ptV6v0Group,
           tmnxSdpBindTlsV6v0Group,
           tmnxSdpBindV6v0Group,
           tmnxSdpL2V6v0Group,
           tmnxSdpMixedLspModeV9v0Group,
           tmnxSdpNotifyV6v0Group,
           tmnxSdpV6v0Group
        }

        VARIATION   pwTemplateEgressIpFilterId
            ACCESS  not-implemented
            DESCRIPTION
                 "Not supported.

                  Not supported."

        VARIATION   pwTemplateEgressIpv6FilterId
            ACCESS  not-implemented
            DESCRIPTION
                 "Not supported.

                  Not supported."

        VARIATION   pwTemplateEgressMacFilterId
            ACCESS  not-implemented
            DESCRIPTION
                 "Not supported.

                  Not supported."

        VARIATION   pwTemplateIngressIpFilterId
            ACCESS  not-implemented
            DESCRIPTION
                 "Not supported.

                  Not supported."

        VARIATION   pwTemplateIngressIpv6FilterId
            ACCESS  not-implemented
            DESCRIPTION
                 "Not supported.

                  Not supported."

        VARIATION   pwTemplateIngressMacFilterId
            ACCESS  not-implemented
            DESCRIPTION
                 "Not supported.

                  Not supported."

        VARIATION   pwTemplateShgRestProtSrcMac
            ACCESS  not-implemented
            DESCRIPTION
                 "Not supported.

                  Not supported."

        VARIATION   pwTemplateShgRestUnprotDstMac
            ACCESS  not-implemented
            DESCRIPTION
                 "Not supported.

                  Not supported."

        VARIATION   sdpAvailableBandwidth
            ACCESS  not-implemented
            DESCRIPTION
                 "Not supported.

                  Not supported."

        VARIATION   sdpBandwidthBookingFactor
            ACCESS  not-implemented
            DESCRIPTION
                 "Not supported.

                  Not supported."

        VARIATION   sdpBindAdminBandwidth
            ACCESS  not-implemented
            DESCRIPTION
                 "Not supported.

                  Not supported."

        VARIATION   sdpBindBaseStatsIngressDroppedPackets
            ACCESS  not-implemented
            DESCRIPTION
                 "Not supported.

                  Not supported."

        VARIATION   sdpBindClassFwdingOperState
            ACCESS  not-implemented
            DESCRIPTION
                 "Not supported.

                  Not supported."

        VARIATION   sdpBindControlWordBit
            DESCRIPTION
                 "sdpBindControlWordBit is only supported for EPIPE service in
                  SAS-R 7210.

                  sdpBindControlWordBit is only supported for EPIPE service in
                  SAS-R 7210."

        VARIATION   sdpBindCpipeLocalCasTrunkFraming
            ACCESS  not-implemented
            DESCRIPTION
                 "Not supported.

                  Not supported."

        VARIATION   sdpBindCpipeLocalSigPkts
            ACCESS  not-implemented
            DESCRIPTION
                 "Not supported.

                  Not supported."

        VARIATION   sdpBindCpipePeerCasTrunkFraming
            ACCESS  not-implemented
            DESCRIPTION
                 "Not supported.

                  Not supported."

        VARIATION   sdpBindCpipePeerSigPkts
            ACCESS  not-implemented
            DESCRIPTION
                 "Not supported.

                  Not supported."

        VARIATION   sdpBindEgressIpFilterId
            ACCESS  not-implemented
            DESCRIPTION
                 "Not supported.

                  Not supported."

        VARIATION   sdpBindEgressIpv6FilterId
            ACCESS  not-implemented
            DESCRIPTION
                 "Not supported.

                  Not supported."

        VARIATION   sdpBindEgressMacFilterId
            ACCESS  not-implemented
            DESCRIPTION
                 "Not supported.

                  Not supported."

        VARIATION   sdpBindIesIfIndex
            ACCESS  not-implemented
            DESCRIPTION
                 "Not supported.

                  Not supported."

        VARIATION   sdpBindIngressIpFilterId
            ACCESS  not-implemented
            DESCRIPTION
                 "Not supported.

                  Not supported."

        VARIATION   sdpBindIngressIpv6FilterId
            ACCESS  not-implemented
            DESCRIPTION
                 "Not supported.

                  Not supported."

        VARIATION   sdpBindIngressMacFilterId
            ACCESS  not-implemented
            DESCRIPTION
                 "Not supported.

                  Not supported."

        VARIATION   sdpBindMeshTlsNotInMstRegion
            ACCESS  not-implemented
            DESCRIPTION
                 "Not supported.

                  Not supported."

        VARIATION   sdpBindOperBandwidth
            ACCESS  not-implemented
            DESCRIPTION
                 "Not supported.

                  Not supported."

        VARIATION   sdpBindOperGrp
            ACCESS  not-implemented
            DESCRIPTION
                 "Not supported.

                  Not supported."

        VARIATION   sdpBindTlsStpInMstBpdus
            ACCESS  not-implemented
            DESCRIPTION
                 "Not supported.

                  Not supported."

        VARIATION   sdpBindTlsStpOutMstBpdus
            ACCESS  not-implemented
            DESCRIPTION
                 "Not supported.

                  Not supported."

        VARIATION   sdpBindVcType
            SYNTAX  INTEGER {
                       undef                (1),
                       ether                (2),
                    -- vpls                 (3)
                       vlan                 (4),
                       mirror               (5),
                    -- atmSdu               (6)
                    -- atmCell              (7)
                    -- atmVcc               (8)
                    -- atmVpc               (9)
                    -- frDlci               (10)
                    -- ipipe                (11)
                       satopE1              (12),
                       satopT1              (13),
                    -- satopE3              (14)
                    -- satopT3              (15)
                       cesopsn              (16),
                       cesopsnCas           (17)
                    }
            DESCRIPTION
                 "The enumeration 'vpls (3)' is no longer supported. The values
                  - 'atmSdu (6)', - 'atmCell (7)', - 'atmVcc (8)', - 'atmVpc
                  (9)', - 'frDlci (10), - 'ipipe (11) - 'satopE3 (14)', -
                  'satopT3 (15)', are not supported on a SAS-R 7210 system.

                  The enumeration 'vpls (3)' is no longer supported. The values
                  - 'atmSdu (6)', - 'atmCell (7)', - 'atmVcc (8)', - 'atmVpc
                  (9)', - 'frDlci (10), - 'ipipe (11) - 'satopE3 (14)', -
                  'satopT3 (15)', are not supported on a SAS-R 7210 system."

        VARIATION   sdpClassFwdingDefaultLsp
            ACCESS  not-implemented
            DESCRIPTION
                 "Not supported.

                  Not supported."

        VARIATION   sdpClassFwdingEnabled
            ACCESS  not-implemented
            DESCRIPTION
                 "Not supported.

                  Not supported."

        VARIATION   sdpClassFwdingMcLsp
            ACCESS  not-implemented
            DESCRIPTION
                 "Not supported.

                  Not supported."

        VARIATION   sdpOperBandwidth
            ACCESS  not-implemented
            DESCRIPTION
                 "Not supported.

                  Not supported."

        VARIATION   sdpPBBEtype
            ACCESS  not-implemented
            DESCRIPTION
                 "Not supported.

                  Not supported."

    ::= { tmnxSASAgentV9v0  25 }

--
-- SAS SDP CAPABILITIES
--
tmnxSASSdpV9v0                    AGENT-CAPABILITIES
    PRODUCT-RELEASE "Alcatel-Lucent SAS"
    STATUS          current
    DESCRIPTION
         "Implementation of SDP capabilities for Alcatel-Lucent SAS systems
          release 9.0."

    SUPPORTS        TIMETRA-SDP-MIB
        INCLUDES {
           tmnxSdpBindCpipeV6v0Group,
           tmnxSdpBindMeshV6v0Group,
           tmnxSdpBindTlsL2ptV6v0Group,
           tmnxSdpBindTlsV6v0Group,
           tmnxSdpBindV6v0Group,
           tmnxSdpL2V6v0Group,
           tmnxSdpMixedLspModeV9v0Group,
           tmnxSdpNotifyV6v0Group,
           tmnxSdpV6v0Group
        }

        VARIATION   pwTemplateEgressIpFilterId
            ACCESS  not-implemented
            DESCRIPTION
                 "Not supported.

                  Not supported."

        VARIATION   pwTemplateEgressIpv6FilterId
            ACCESS  not-implemented
            DESCRIPTION
                 "Not supported.

                  Not supported."

        VARIATION   pwTemplateEgressMacFilterId
            ACCESS  not-implemented
            DESCRIPTION
                 "Not supported.

                  Not supported."

        VARIATION   pwTemplateIngressIpFilterId
            ACCESS  not-implemented
            DESCRIPTION
                 "Not supported.

                  Not supported."

        VARIATION   pwTemplateIngressIpv6FilterId
            ACCESS  not-implemented
            DESCRIPTION
                 "Not supported.

                  Not supported."

        VARIATION   pwTemplateIngressMacFilterId
            ACCESS  not-implemented
            DESCRIPTION
                 "Not supported.

                  Not supported."

        VARIATION   pwTemplateShgRestProtSrcMac
            ACCESS  not-implemented
            DESCRIPTION
                 "Not supported.

                  Not supported."

        VARIATION   pwTemplateShgRestUnprotDstMac
            ACCESS  not-implemented
            DESCRIPTION
                 "Not supported.

                  Not supported."

        VARIATION   sdpAvailableBandwidth
            ACCESS  not-implemented
            DESCRIPTION
                 "Not supported.

                  Not supported."

        VARIATION   sdpBandwidthBookingFactor
            ACCESS  not-implemented
            DESCRIPTION
                 "Not supported.

                  Not supported."

        VARIATION   sdpBindAdminBandwidth
            ACCESS  not-implemented
            DESCRIPTION
                 "Not supported.

                  Not supported."

        VARIATION   sdpBindBaseStatsIngressDroppedPackets
            ACCESS  not-implemented
            DESCRIPTION
                 "Not supported.

                  Not supported."

        VARIATION   sdpBindClassFwdingOperState
            ACCESS  not-implemented
            DESCRIPTION
                 "Not supported.

                  Not supported."

        VARIATION   sdpBindControlWordBit
            DESCRIPTION
                 "sdpBindControlWordBit is only supported for EPIPE service in
                  SAS-R 7210.

                  sdpBindControlWordBit is only supported for EPIPE service in
                  SAS-R 7210."

        VARIATION   sdpBindCpipeLocalCasTrunkFraming
            ACCESS  not-implemented
            DESCRIPTION
                 "Not supported.

                  Not supported."

        VARIATION   sdpBindCpipeLocalSigPkts
            ACCESS  not-implemented
            DESCRIPTION
                 "Not supported.

                  Not supported."

        VARIATION   sdpBindCpipePeerCasTrunkFraming
            ACCESS  not-implemented
            DESCRIPTION
                 "Not supported.

                  Not supported."

        VARIATION   sdpBindCpipePeerSigPkts
            ACCESS  not-implemented
            DESCRIPTION
                 "Not supported.

                  Not supported."

        VARIATION   sdpBindEgressIpFilterId
            ACCESS  not-implemented
            DESCRIPTION
                 "Not supported.

                  Not supported."

        VARIATION   sdpBindEgressIpv6FilterId
            ACCESS  not-implemented
            DESCRIPTION
                 "Not supported.

                  Not supported."

        VARIATION   sdpBindEgressMacFilterId
            ACCESS  not-implemented
            DESCRIPTION
                 "Not supported.

                  Not supported."

        VARIATION   sdpBindIesIfIndex
            ACCESS  not-implemented
            DESCRIPTION
                 "Not supported.

                  Not supported."

        VARIATION   sdpBindIngressIpFilterId
            ACCESS  not-implemented
            DESCRIPTION
                 "Not supported.

                  Not supported."

        VARIATION   sdpBindIngressIpv6FilterId
            ACCESS  not-implemented
            DESCRIPTION
                 "Not supported.

                  Not supported."

        VARIATION   sdpBindIngressMacFilterId
            ACCESS  not-implemented
            DESCRIPTION
                 "Not supported.

                  Not supported."

        VARIATION   sdpBindMeshTlsNotInMstRegion
            ACCESS  not-implemented
            DESCRIPTION
                 "Not supported.

                  Not supported."

        VARIATION   sdpBindOperBandwidth
            ACCESS  not-implemented
            DESCRIPTION
                 "Not supported.

                  Not supported."

        VARIATION   sdpBindOperGrp
            ACCESS  not-implemented
            DESCRIPTION
                 "Not supported.

                  Not supported."

        VARIATION   sdpBindTlsStpInMstBpdus
            ACCESS  not-implemented
            DESCRIPTION
                 "Not supported.

                  Not supported."

        VARIATION   sdpBindTlsStpOutMstBpdus
            ACCESS  not-implemented
            DESCRIPTION
                 "Not supported.

                  Not supported."

        VARIATION   sdpBindVcType
            SYNTAX  INTEGER {
                       undef                (1),
                       ether                (2),
                    -- vpls                 (3)
                       vlan                 (4),
                       mirror               (5),
                    -- atmSdu               (6)
                    -- atmCell              (7)
                    -- atmVcc               (8)
                    -- atmVpc               (9)
                    -- frDlci               (10)
                    -- ipipe                (11)
                       satopE1              (12),
                       satopT1              (13),
                    -- satopE3              (14)
                    -- satopT3              (15)
                       cesopsn              (16),
                       cesopsnCas           (17)
                    }
            DESCRIPTION
                 "The enumeration 'vpls (3)' is no longer supported. The values
                  - 'atmSdu (6)', - 'atmCell (7)', - 'atmVcc (8)', - 'atmVpc
                  (9)', - 'frDlci (10), - 'ipipe (11) - 'satopE3 (14)', -
                  'satopT3 (15)', are not supported on a SAS-R 7210 system.

                  The enumeration 'vpls (3)' is no longer supported. The values
                  - 'atmSdu (6)', - 'atmCell (7)', - 'atmVcc (8)', - 'atmVpc
                  (9)', - 'frDlci (10), - 'ipipe (11) - 'satopE3 (14)', -
                  'satopT3 (15)', are not supported on a SAS-R 7210 system."

        VARIATION   sdpClassFwdingDefaultLsp
            ACCESS  not-implemented
            DESCRIPTION
                 "Not supported.

                  Not supported."

        VARIATION   sdpClassFwdingEnabled
            ACCESS  not-implemented
            DESCRIPTION
                 "Not supported.

                  Not supported."

        VARIATION   sdpClassFwdingMcLsp
            ACCESS  not-implemented
            DESCRIPTION
                 "Not supported.

                  Not supported."

        VARIATION   sdpOperBandwidth
            ACCESS  not-implemented
            DESCRIPTION
                 "Not supported.

                  Not supported."

        VARIATION   sdpPBBEtype
            ACCESS  not-implemented
            DESCRIPTION
                 "Not supported.

                  Not supported."

    ::= { tmnxSASAgentV9v0  25 }

--
-- SAS SERVICES CAPABILITIES
--
tmnxSASServicesV9v0               AGENT-CAPABILITIES
    PRODUCT-RELEASE "Alcatel-Lucent SAS"
    STATUS          current
    DESCRIPTION
         "Implementation of Services capabilities for Alcatel-Lucent SAS systems
          release 9.0."

    SUPPORTS        TIMETRA-SAS-SERV-MIB
        INCLUDES {
           tmnxSapGlobalV1v0Group,
           tmnxSasSapQosV2v0Group
        }

        VARIATION   sapBaseInfoEgressStatsPktsMode
            ACCESS  not-implemented
            DESCRIPTION
                 "Not supported.

                  Not supported."

        VARIATION   sapBaseInfoIngressCounterMode
            ACCESS  not-implemented
            DESCRIPTION
                 "Not supported.

                  Not supported."

        VARIATION   sapBaseInfoIngressFabricPath
            ACCESS  not-implemented
            DESCRIPTION
                 "Not supported.

                  Not supported."

        VARIATION   sapBaseInfoIngressStatsEnable
            ACCESS  not-implemented
            DESCRIPTION
                 "Not supported.

                  Not supported."

        VARIATION   sapBaseInfoIngressWithAggregateMeter
            ACCESS  not-implemented
            DESCRIPTION
                 "Not supported.

                  Not supported."

        VARIATION   sapEgrQosQueueStatsExtnTable
            ACCESS  not-implemented
            DESCRIPTION
                 "Not supported.

                  Not supported."

        VARIATION   sapIngQosQueueStatsExtnTable
            ACCESS  not-implemented
            DESCRIPTION
                 "Not supported.

                  Not supported."

        VARIATION   svcUplinkType
            ACCESS  not-implemented
            DESCRIPTION
                 "Not supported.

                  Not supported."

        VARIATION   svcbVplsVid
            ACCESS  not-implemented
            DESCRIPTION
                 "Not supported.

                  Not supported."

    SUPPORTS        TIMETRA-SERV-MIB
        INCLUDES {
           tmnxCustV6v0Group,
           tmnxSvcEndPointV6v0Group,
           tmnxSvcEpipeV6v0Group,
           tmnxSvcIesIfV6v0Group,
           tmnxSvcNotifyObjsV7v0Group,
           tmnxSvcNotifyV7v0Group,
           tmnxSvcTlsBackbone6v1Group,
           tmnxSvcTlsFdbV7v0Group,
           tmnxSvcTlsMFibV6v0Group,
           tmnxSvcTlsV6v0Group,
           tmnxSvcV6v0Group
        }

        VARIATION   custEgrQosPortSchedFwdOctets
            ACCESS  not-implemented
            DESCRIPTION
                 "Not supported.

                  Not supported."

        VARIATION   custEgrQosPortSchedFwdPkts
            ACCESS  not-implemented
            DESCRIPTION
                 "Not supported.

                  Not supported."

        VARIATION   custEgrQosSchedStatsForwardedOctets
            ACCESS  not-implemented
            DESCRIPTION
                 "Not supported.

                  Not supported."

        VARIATION   custEgrQosSchedStatsForwardedPackets
            ACCESS  not-implemented
            DESCRIPTION
                 "Not supported.

                  Not supported."

        VARIATION   custEgrSchedPlcyPortStatsFwdOct
            ACCESS  not-implemented
            DESCRIPTION
                 "Not supported.

                  Not supported."

        VARIATION   custEgrSchedPlcyPortStatsFwdPkt
            ACCESS  not-implemented
            DESCRIPTION
                 "Not supported.

                  Not supported."

        VARIATION   custEgrSchedPlcyStatsFwdOct
            ACCESS  not-implemented
            DESCRIPTION
                 "Not supported.

                  Not supported."

        VARIATION   custEgrSchedPlcyStatsFwdPkt
            ACCESS  not-implemented
            DESCRIPTION
                 "Not supported.

                  Not supported."

        VARIATION   custIngQosPortSchedFwdOctets
            ACCESS  not-implemented
            DESCRIPTION
                 "Not supported.

                  Not supported."

        VARIATION   custIngQosPortSchedFwdPkts
            ACCESS  not-implemented
            DESCRIPTION
                 "Not supported.

                  Not supported."

        VARIATION   custIngQosSchedStatsForwardedOctets
            ACCESS  not-implemented
            DESCRIPTION
                 "Not supported.

                  Not supported."

        VARIATION   custIngQosSchedStatsForwardedPackets
            ACCESS  not-implemented
            DESCRIPTION
                 "Not supported.

                  Not supported."

        VARIATION   custIngSchedPlcyPortStatsFwdOct
            ACCESS  not-implemented
            DESCRIPTION
                 "Not supported.

                  Not supported."

        VARIATION   custIngSchedPlcyPortStatsFwdPkt
            ACCESS  not-implemented
            DESCRIPTION
                 "Not supported.

                  Not supported."

        VARIATION   custIngSchedPlcyStatsFwdOct
            ACCESS  not-implemented
            DESCRIPTION
                 "Not supported.

                  Not supported."

        VARIATION   custIngSchedPlcyStatsFwdPkt
            ACCESS  not-implemented
            DESCRIPTION
                 "Not supported.

                  Not supported."

        VARIATION   custMssEgrQosSCIR
            ACCESS  not-implemented
            DESCRIPTION
                 "Not supported.

                  Not supported."

        VARIATION   custMssEgrQosSLastMgmtChange
            ACCESS  not-implemented
            DESCRIPTION
                 "Not supported.

                  Not supported."

        VARIATION   custMssEgrQosSOverrideFlags
            ACCESS  not-implemented
            DESCRIPTION
                 "Not supported.

                  Not supported."

        VARIATION   custMssEgrQosSPIR
            ACCESS  not-implemented
            DESCRIPTION
                 "Not supported.

                  Not supported."

        VARIATION   custMssEgrQosSRowStatus
            ACCESS  not-implemented
            DESCRIPTION
                 "Not supported.

                  Not supported."

        VARIATION   custMssEgrQosSSummedCIR
            ACCESS  not-implemented
            DESCRIPTION
                 "Not supported.

                  Not supported."

        VARIATION   custMssIngQosSCIR
            ACCESS  not-implemented
            DESCRIPTION
                 "Not supported.

                  Not supported."

        VARIATION   custMssIngQosSLastMgmtChange
            ACCESS  not-implemented
            DESCRIPTION
                 "Not supported.

                  Not supported."

        VARIATION   custMssIngQosSOverrideFlags
            ACCESS  not-implemented
            DESCRIPTION
                 "Not supported.

                  Not supported."

        VARIATION   custMssIngQosSPIR
            ACCESS  not-implemented
            DESCRIPTION
                 "Not supported.

                  Not supported."

        VARIATION   custMssIngQosSRowStatus
            ACCESS  not-implemented
            DESCRIPTION
                 "Not supported.

                  Not supported."

        VARIATION   custMssIngQosSSummedCIR
            ACCESS  not-implemented
            DESCRIPTION
                 "Not supported.

                  Not supported."

        VARIATION   custMultSvcSiteAssignment
            ACCESS  not-implemented
            DESCRIPTION
                 "Not supported.

                  Not supported."

        VARIATION   custMultSvcSiteCurrentEgrSchedPlcy
            ACCESS  not-implemented
            DESCRIPTION
                 "Not supported.

                  Not supported."

        VARIATION   custMultSvcSiteCurrentIngrSchedPlcy
            ACCESS  not-implemented
            DESCRIPTION
                 "Not supported.

                  Not supported."

        VARIATION   custMultSvcSiteDescription
            ACCESS  not-implemented
            DESCRIPTION
                 "Not supported.

                  Not supported."

        VARIATION   custMultSvcSiteEgressAggRateLimit
            ACCESS  not-implemented
            DESCRIPTION
                 "Not supported.

                  Not supported."

        VARIATION   custMultSvcSiteEgressSchedulerPolicy
            ACCESS  not-implemented
            DESCRIPTION
                 "Not supported.

                  Not supported."

        VARIATION   custMultSvcSiteFrameBasedAccnt
            ACCESS  not-implemented
            DESCRIPTION
                 "Not supported.

                  Not supported."

        VARIATION   custMultSvcSiteIngressSchedulerPolicy
            ACCESS  not-implemented
            DESCRIPTION
                 "Not supported.

                  Not supported."

        VARIATION   custMultSvcSiteIntendedEgrSchedPlcy
            ACCESS  not-implemented
            DESCRIPTION
                 "Not supported.

                  Not supported."

        VARIATION   custMultSvcSiteIntendedIngrSchedPlcy
            ACCESS  not-implemented
            DESCRIPTION
                 "Not supported.

                  Not supported."

        VARIATION   custMultSvcSiteLastMgmtChange
            ACCESS  not-implemented
            DESCRIPTION
                 "Not supported.

                  Not supported."

        VARIATION   custMultSvcSiteName
            ACCESS  not-implemented
            DESCRIPTION
                 "Not supported.

                  Not supported."

        VARIATION   custMultSvcSiteRowStatus
            ACCESS  not-implemented
            DESCRIPTION
                 "Not supported.

                  Not supported."

        VARIATION   custMultSvcSiteScope
            ACCESS  not-implemented
            DESCRIPTION
                 "Not supported.

                  Not supported."

        VARIATION   custMultSvcSiteTodSuite
            ACCESS  not-implemented
            DESCRIPTION
                 "Not supported.

                  Not supported."

        VARIATION   iesGrpIfOperUpWhileEmpty
            ACCESS  not-implemented
            DESCRIPTION
                 "Not supported.

                  Not supported."

        VARIATION   iesIfFwdServId
            ACCESS  not-implemented
            DESCRIPTION
                 "Not supported. (No routed-co feature).

                  Not supported. (No routed-co feature)."

        VARIATION   iesIfParentIf
            ACCESS  not-implemented
            DESCRIPTION
                 "Not supported (No routed-co feature).

                  Not supported (No routed-co feature)."

        VARIATION   iesIfType
            SYNTAX  INTEGER {
                       service              (1),
                    -- subscriber           (2)
                    -- group                (3)
                    -- redundant            (4)
                    -- cem                  (5)
                    -- ipsec                (6)
                       ipMirror             (7)
                    }
            DESCRIPTION
                 "The values - 'subscriber (2)', - 'group (3)', - 'redundant
                  (4)' are not supported on SAS-R 7210 systems, as the routed-co
                  feature is not implemented.

                  Also the values - 'cem (5)', - 'ipsec (6)' are not supported
                  on SAS-R 7210 systems.

                  The values - 'subscriber (2)', - 'group (3)', - 'redundant
                  (4)' are not supported on SAS-R 7210 systems, as the routed-co
                  feature is not implemented.

                  Also the values - 'cem (5)', - 'ipsec (6)' are not supported
                  on SAS-R 7210 systems."

        VARIATION   svcApipeInterworking
            DESCRIPTION
                 "Not supported.

                  Not supported."

        VARIATION   svcDhcpManagedRouteStatus
            ACCESS  not-implemented
            DESCRIPTION
                 "Not supported. (No Routed Subscriber Host feature).

                  Not supported. (No Routed Subscriber Host feature)."

        VARIATION   svcEndPointStandbySigSlave
            ACCESS  not-implemented
            DESCRIPTION
                 "Not supported.

                  Not supported."

        VARIATION   svcIpRouting
            ACCESS  not-implemented
            DESCRIPTION
                 "Not supported.

                  Not supported."

        VARIATION   svcRadiusDiscovery
            ACCESS  not-implemented
            DESCRIPTION
                 "Not supported.

                  Not supported."

        VARIATION   svcRadiusDiscoveryShutdown
            ACCESS  not-implemented
            DESCRIPTION
                 "Not supported.

                  Not supported."

        VARIATION   svcRadiusPEDiscPolicy
            ACCESS  not-implemented
            DESCRIPTION
                 "Not supported.

                  Not supported."

        VARIATION   svcRadiusUserName
            ACCESS  not-implemented
            DESCRIPTION
                 "Not supported.

                  Not supported."

        VARIATION   svcRadiusUserNameType
            ACCESS  not-implemented
            DESCRIPTION
                 "Not supported.

                  Not supported."

        VARIATION   svcRestoreHostProblem
            ACCESS  not-implemented
            DESCRIPTION
                 "Not supported.

                  Not supported."

        VARIATION   svcTlsBackboneLDPMacFlush
            ACCESS  not-implemented
            DESCRIPTION
                 "Not supported.

                  Not supported."

        VARIATION   svcTlsBackboneLDPMacFlushNotMine
            ACCESS  not-implemented
            DESCRIPTION
                 "Not supported.

                  Not supported."

        VARIATION   svcTlsBackboneVplsStp
            ACCESS  not-implemented
            DESCRIPTION
                 "Not supported.

                  Not supported."

        VARIATION   svcTlsFdbNumDhcpEntries
            ACCESS  not-implemented
            DESCRIPTION
                 "Not supported.

                  Not supported."

        VARIATION   svcTlsFdbNumHostEntries
            ACCESS  not-implemented
            DESCRIPTION
                 "Not supported.

                  Not supported."

        VARIATION   svcTlsMcPathMgmtPlcyName
            ACCESS  not-implemented
            DESCRIPTION
                 "Not supported.

                  Not supported."

        VARIATION   svcTlsMrpAdminStatus
            ACCESS  not-implemented
            DESCRIPTION
                 "Not supported.

                  Not supported."

        VARIATION   svcTlsMrpAttrTblHighWatermark
            ACCESS  not-implemented
            DESCRIPTION
                 "Not supported.

                  Not supported."

        VARIATION   svcTlsMrpAttrTblLowWatermark
            ACCESS  not-implemented
            DESCRIPTION
                 "Not supported.

                  Not supported."

        VARIATION   svcTlsMrpAttributeCount
            ACCESS  not-implemented
            DESCRIPTION
                 "Not supported.

                  Not supported."

        VARIATION   svcTlsMrpFailedRegisterCount
            ACCESS  not-implemented
            DESCRIPTION
                 "Not supported.

                  Not supported."

        VARIATION   svcTlsMrpFloodTime
            ACCESS  not-implemented
            DESCRIPTION
                 "Not supported.

                  Not supported."

        VARIATION   svcTlsMrpMaxAttributes
            ACCESS  not-implemented
            DESCRIPTION
                 "Not supported.

                  Not supported."

        VARIATION   svcTlsShcvAction
            ACCESS  not-implemented
            DESCRIPTION
                 "Not supported.

                  Not supported."

        VARIATION   svcTlsShcvInterval
            ACCESS  not-implemented
            DESCRIPTION
                 "Not supported.

                  Not supported."

        VARIATION   svcTlsShcvSrcIp
            ACCESS  not-implemented
            DESCRIPTION
                 "Not supported.

                  Not supported."

        VARIATION   svcTlsShcvSrcMac
            ACCESS  not-implemented
            DESCRIPTION
                 "Not supported.

                  Not supported."

        VARIATION   svcTotalFdbMimDestIdxEntries
            ACCESS  not-implemented
            DESCRIPTION
                 "Not supported.

                  Not supported."

        VARIATION   svcType
            SYNTAX  INTEGER {
                       epipe                (1), -- Ethernet pipe
                       p3pipe               (2), -- POS pipe
                       tls                  (3), -- Virtual private LAN service
                       vprn                 (4), --Virtual private routed network
                       ies                  (5), -- Internet enhanced service
                       mirror               (6), -- Mirror service
                    -- apipe                (7) ATM pipe service
                    -- no aPIPE on SAS-R 7210
                    -- fpipe                (8) FR pipe service
                    -- no FPIPE on SAS-R 7210
                       ipipe                (9) -- IP interworking pipe service
                    -- cpipe                (10) Circuit Emulation pipe service
                    -- no CPIPE on SAS-R 7210
                    }
            DESCRIPTION
                 "The values - 'apipe (7)', - 'fpipe (8)', - 'cpipe (10)' are
                  invalid on a SAS-R 7210 system.

                  The values - 'apipe (7)', - 'fpipe (8)', - 'cpipe (10)' are
                  invalid on a SAS-R 7210 system."

        VARIATION   svcVllType
            SYNTAX  INTEGER {
                       undef                (1)
                    -- atmSdu               (6)
                    -- atmCell              (7)
                    -- atmVcc               (8)
                    -- atmVpc               (9)
                    -- frDlci               (10)
                    -- satopE3              (14)
                    -- satopT3              (15)
                    -- cesopsn              (16)
                    -- cesopsnCas           (17)
                    }
            DESCRIPTION
                 "The values - 'atmSdu (6)', - 'atmCell (7)', - 'atmVcc (8)', -
                  'atmVpc (9)', - 'frDlci (10)', - 'satopE3 (14)', - 'satopT3
                  (15)', - 'cesopsn (16)', - 'cesopsnCas (17)' are not supported
                  on a SAS-R 7210 system.

                  The values - 'atmSdu (6)', - 'atmCell (7)', - 'atmVcc (8)', -
                  'atmVpc (9)', - 'frDlci (10)', - 'satopE3 (14)', - 'satopT3
                  (15)', - 'cesopsn (16)', - 'cesopsnCas (17)' are not supported
                  on a SAS-R 7210 system."

        VARIATION   tlsEgrMcGrpAdminQinqFixedTagVal
            ACCESS  not-implemented
            DESCRIPTION
                 "Not supported.

                  Not supported."

        VARIATION   tlsEgrMcGrpQinqFixedTagPosition
            ACCESS  read-only
            DESCRIPTION
                 "read-only implementation.

                  read-only implementation."

        VARIATION   tlsFdbProtected
            ACCESS  not-implemented
            DESCRIPTION
                 "Not supported.

                  Not supported."

        VARIATION   tlsMFibStatsForwardedOctets
            ACCESS  not-implemented
            DESCRIPTION
                 "Not supported.

                  Not supported."

        VARIATION   tlsMFibStatsForwardedPkts
            ACCESS  not-implemented
            DESCRIPTION
                 "Not supported.

                  Not supported."

        VARIATION   tlsProtMacImplCount
            ACCESS  not-implemented
            DESCRIPTION
                 "Not supported.

                  Not supported."

        VARIATION   tlsProtMacLastMgmtChange
            ACCESS  not-implemented
            DESCRIPTION
                 "Not supported.

                  Not supported."

        VARIATION   tlsProtMacRowStatus
            ACCESS  not-implemented
            DESCRIPTION
                 "Not supported.

                  Not supported."

        VARIATION   tlsShgAutoLearnMacProtect
            ACCESS  not-implemented
            DESCRIPTION
                 "Not supported.

                  Not supported."

        VARIATION   tlsShgResidential
            ACCESS  not-implemented
            DESCRIPTION
                 "Not supported.

                  Not supported."

        VARIATION   tlsShgRestProtSrcMac
            ACCESS  not-implemented
            DESCRIPTION
                 "Not supported.

                  Not supported."

        VARIATION   tlsShgRestProtSrcMacAction
            ACCESS  not-implemented
            DESCRIPTION
                 "Not supported.

                  Not supported."

        VARIATION   tlsShgRestUnprotDstMac
            ACCESS  not-implemented
            DESCRIPTION
                 "Not supported.

                  Not supported."

    ::= { tmnxSASAgentV9v0  16 }

--
-- SAS SERVICES CAPABILITIES
--
tmnxSASServicesV9v0               AGENT-CAPABILITIES
    PRODUCT-RELEASE "Alcatel-Lucent SAS"
    STATUS          current
    DESCRIPTION
         "Implementation of Services capabilities for Alcatel-Lucent SAS systems
          release 9.0."

    SUPPORTS        TIMETRA-SAS-SERV-MIB
        INCLUDES {
           tmnxSapGlobalV1v0Group,
           tmnxSasSapQosV2v0Group
        }

        VARIATION   sapBaseInfoEgressStatsPktsMode
            ACCESS  not-implemented
            DESCRIPTION
                 "Not supported.

                  Not supported."

        VARIATION   sapBaseInfoIngressCounterMode
            ACCESS  not-implemented
            DESCRIPTION
                 "Not supported.

                  Not supported."

        VARIATION   sapBaseInfoIngressFabricPath
            ACCESS  not-implemented
            DESCRIPTION
                 "Not supported.

                  Not supported."

        VARIATION   sapBaseInfoIngressStatsEnable
            ACCESS  not-implemented
            DESCRIPTION
                 "Not supported.

                  Not supported."

        VARIATION   sapBaseInfoIngressWithAggregateMeter
            ACCESS  not-implemented
            DESCRIPTION
                 "Not supported.

                  Not supported."

        VARIATION   sapEgrQosQueueStatsExtnTable
            ACCESS  not-implemented
            DESCRIPTION
                 "Not supported.

                  Not supported."

        VARIATION   sapIngQosQueueStatsExtnTable
            ACCESS  not-implemented
            DESCRIPTION
                 "Not supported.

                  Not supported."

        VARIATION   svcUplinkType
            ACCESS  not-implemented
            DESCRIPTION
                 "Not supported.

                  Not supported."

        VARIATION   svcbVplsVid
            ACCESS  not-implemented
            DESCRIPTION
                 "Not supported.

                  Not supported."

    SUPPORTS        TIMETRA-SERV-MIB
        INCLUDES {
           tmnxCustV6v0Group,
           tmnxSvcEndPointV6v0Group,
           tmnxSvcEpipeV6v0Group,
           tmnxSvcIesIfV6v0Group,
           tmnxSvcNotifyObjsV7v0Group,
           tmnxSvcNotifyV7v0Group,
           tmnxSvcTlsBackbone6v1Group,
           tmnxSvcTlsFdbV7v0Group,
           tmnxSvcTlsMFibV6v0Group,
           tmnxSvcTlsV6v0Group,
           tmnxSvcV6v0Group
        }

        VARIATION   custEgrQosPortSchedFwdOctets
            ACCESS  not-implemented
            DESCRIPTION
                 "Not supported.

                  Not supported."

        VARIATION   custEgrQosPortSchedFwdPkts
            ACCESS  not-implemented
            DESCRIPTION
                 "Not supported.

                  Not supported."

        VARIATION   custEgrQosSchedStatsForwardedOctets
            ACCESS  not-implemented
            DESCRIPTION
                 "Not supported.

                  Not supported."

        VARIATION   custEgrQosSchedStatsForwardedPackets
            ACCESS  not-implemented
            DESCRIPTION
                 "Not supported.

                  Not supported."

        VARIATION   custEgrSchedPlcyPortStatsFwdOct
            ACCESS  not-implemented
            DESCRIPTION
                 "Not supported.

                  Not supported."

        VARIATION   custEgrSchedPlcyPortStatsFwdPkt
            ACCESS  not-implemented
            DESCRIPTION
                 "Not supported.

                  Not supported."

        VARIATION   custEgrSchedPlcyStatsFwdOct
            ACCESS  not-implemented
            DESCRIPTION
                 "Not supported.

                  Not supported."

        VARIATION   custEgrSchedPlcyStatsFwdPkt
            ACCESS  not-implemented
            DESCRIPTION
                 "Not supported.

                  Not supported."

        VARIATION   custIngQosPortSchedFwdOctets
            ACCESS  not-implemented
            DESCRIPTION
                 "Not supported.

                  Not supported."

        VARIATION   custIngQosPortSchedFwdPkts
            ACCESS  not-implemented
            DESCRIPTION
                 "Not supported.

                  Not supported."

        VARIATION   custIngQosSchedStatsForwardedOctets
            ACCESS  not-implemented
            DESCRIPTION
                 "Not supported.

                  Not supported."

        VARIATION   custIngQosSchedStatsForwardedPackets
            ACCESS  not-implemented
            DESCRIPTION
                 "Not supported.

                  Not supported."

        VARIATION   custIngSchedPlcyPortStatsFwdOct
            ACCESS  not-implemented
            DESCRIPTION
                 "Not supported.

                  Not supported."

        VARIATION   custIngSchedPlcyPortStatsFwdPkt
            ACCESS  not-implemented
            DESCRIPTION
                 "Not supported.

                  Not supported."

        VARIATION   custIngSchedPlcyStatsFwdOct
            ACCESS  not-implemented
            DESCRIPTION
                 "Not supported.

                  Not supported."

        VARIATION   custIngSchedPlcyStatsFwdPkt
            ACCESS  not-implemented
            DESCRIPTION
                 "Not supported.

                  Not supported."

        VARIATION   custMssEgrQosSCIR
            ACCESS  not-implemented
            DESCRIPTION
                 "Not supported.

                  Not supported."

        VARIATION   custMssEgrQosSLastMgmtChange
            ACCESS  not-implemented
            DESCRIPTION
                 "Not supported.

                  Not supported."

        VARIATION   custMssEgrQosSOverrideFlags
            ACCESS  not-implemented
            DESCRIPTION
                 "Not supported.

                  Not supported."

        VARIATION   custMssEgrQosSPIR
            ACCESS  not-implemented
            DESCRIPTION
                 "Not supported.

                  Not supported."

        VARIATION   custMssEgrQosSRowStatus
            ACCESS  not-implemented
            DESCRIPTION
                 "Not supported.

                  Not supported."

        VARIATION   custMssEgrQosSSummedCIR
            ACCESS  not-implemented
            DESCRIPTION
                 "Not supported.

                  Not supported."

        VARIATION   custMssIngQosSCIR
            ACCESS  not-implemented
            DESCRIPTION
                 "Not supported.

                  Not supported."

        VARIATION   custMssIngQosSLastMgmtChange
            ACCESS  not-implemented
            DESCRIPTION
                 "Not supported.

                  Not supported."

        VARIATION   custMssIngQosSOverrideFlags
            ACCESS  not-implemented
            DESCRIPTION
                 "Not supported.

                  Not supported."

        VARIATION   custMssIngQosSPIR
            ACCESS  not-implemented
            DESCRIPTION
                 "Not supported.

                  Not supported."

        VARIATION   custMssIngQosSRowStatus
            ACCESS  not-implemented
            DESCRIPTION
                 "Not supported.

                  Not supported."

        VARIATION   custMssIngQosSSummedCIR
            ACCESS  not-implemented
            DESCRIPTION
                 "Not supported.

                  Not supported."

        VARIATION   custMultSvcSiteAssignment
            ACCESS  not-implemented
            DESCRIPTION
                 "Not supported.

                  Not supported."

        VARIATION   custMultSvcSiteCurrentEgrSchedPlcy
            ACCESS  not-implemented
            DESCRIPTION
                 "Not supported.

                  Not supported."

        VARIATION   custMultSvcSiteCurrentIngrSchedPlcy
            ACCESS  not-implemented
            DESCRIPTION
                 "Not supported.

                  Not supported."

        VARIATION   custMultSvcSiteDescription
            ACCESS  not-implemented
            DESCRIPTION
                 "Not supported.

                  Not supported."

        VARIATION   custMultSvcSiteEgressAggRateLimit
            ACCESS  not-implemented
            DESCRIPTION
                 "Not supported.

                  Not supported."

        VARIATION   custMultSvcSiteEgressSchedulerPolicy
            ACCESS  not-implemented
            DESCRIPTION
                 "Not supported.

                  Not supported."

        VARIATION   custMultSvcSiteFrameBasedAccnt
            ACCESS  not-implemented
            DESCRIPTION
                 "Not supported.

                  Not supported."

        VARIATION   custMultSvcSiteIngressSchedulerPolicy
            ACCESS  not-implemented
            DESCRIPTION
                 "Not supported.

                  Not supported."

        VARIATION   custMultSvcSiteIntendedEgrSchedPlcy
            ACCESS  not-implemented
            DESCRIPTION
                 "Not supported.

                  Not supported."

        VARIATION   custMultSvcSiteIntendedIngrSchedPlcy
            ACCESS  not-implemented
            DESCRIPTION
                 "Not supported.

                  Not supported."

        VARIATION   custMultSvcSiteLastMgmtChange
            ACCESS  not-implemented
            DESCRIPTION
                 "Not supported.

                  Not supported."

        VARIATION   custMultSvcSiteName
            ACCESS  not-implemented
            DESCRIPTION
                 "Not supported.

                  Not supported."

        VARIATION   custMultSvcSiteRowStatus
            ACCESS  not-implemented
            DESCRIPTION
                 "Not supported.

                  Not supported."

        VARIATION   custMultSvcSiteScope
            ACCESS  not-implemented
            DESCRIPTION
                 "Not supported.

                  Not supported."

        VARIATION   custMultSvcSiteTodSuite
            ACCESS  not-implemented
            DESCRIPTION
                 "Not supported.

                  Not supported."

        VARIATION   iesGrpIfOperUpWhileEmpty
            ACCESS  not-implemented
            DESCRIPTION
                 "Not supported.

                  Not supported."

        VARIATION   iesIfFwdServId
            ACCESS  not-implemented
            DESCRIPTION
                 "Not supported. (No routed-co feature).

                  Not supported. (No routed-co feature)."

        VARIATION   iesIfParentIf
            ACCESS  not-implemented
            DESCRIPTION
                 "Not supported (No routed-co feature).

                  Not supported (No routed-co feature)."

        VARIATION   iesIfType
            SYNTAX  INTEGER {
                       service              (1),
                    -- subscriber           (2)
                    -- group                (3)
                    -- redundant            (4)
                    -- cem                  (5)
                    -- ipsec                (6)
                       ipMirror             (7)
                    }
            DESCRIPTION
                 "The values - 'subscriber (2)', - 'group (3)', - 'redundant
                  (4)' are not supported on SAS-R 7210 systems, as the routed-co
                  feature is not implemented.

                  Also the values - 'cem (5)', - 'ipsec (6)' are not supported
                  on SAS-R 7210 systems.

                  The values - 'subscriber (2)', - 'group (3)', - 'redundant
                  (4)' are not supported on SAS-R 7210 systems, as the routed-co
                  feature is not implemented.

                  Also the values - 'cem (5)', - 'ipsec (6)' are not supported
                  on SAS-R 7210 systems."

        VARIATION   svcApipeInterworking
            DESCRIPTION
                 "Not supported.

                  Not supported."

        VARIATION   svcDhcpManagedRouteStatus
            ACCESS  not-implemented
            DESCRIPTION
                 "Not supported. (No Routed Subscriber Host feature).

                  Not supported. (No Routed Subscriber Host feature)."

        VARIATION   svcEndPointStandbySigSlave
            ACCESS  not-implemented
            DESCRIPTION
                 "Not supported.

                  Not supported."

        VARIATION   svcIpRouting
            ACCESS  not-implemented
            DESCRIPTION
                 "Not supported.

                  Not supported."

        VARIATION   svcRadiusDiscovery
            ACCESS  not-implemented
            DESCRIPTION
                 "Not supported.

                  Not supported."

        VARIATION   svcRadiusDiscoveryShutdown
            ACCESS  not-implemented
            DESCRIPTION
                 "Not supported.

                  Not supported."

        VARIATION   svcRadiusPEDiscPolicy
            ACCESS  not-implemented
            DESCRIPTION
                 "Not supported.

                  Not supported."

        VARIATION   svcRadiusUserName
            ACCESS  not-implemented
            DESCRIPTION
                 "Not supported.

                  Not supported."

        VARIATION   svcRadiusUserNameType
            ACCESS  not-implemented
            DESCRIPTION
                 "Not supported.

                  Not supported."

        VARIATION   svcRestoreHostProblem
            ACCESS  not-implemented
            DESCRIPTION
                 "Not supported.

                  Not supported."

        VARIATION   svcTlsBackboneLDPMacFlush
            ACCESS  not-implemented
            DESCRIPTION
                 "Not supported.

                  Not supported."

        VARIATION   svcTlsBackboneLDPMacFlushNotMine
            ACCESS  not-implemented
            DESCRIPTION
                 "Not supported.

                  Not supported."

        VARIATION   svcTlsBackboneVplsStp
            ACCESS  not-implemented
            DESCRIPTION
                 "Not supported.

                  Not supported."

        VARIATION   svcTlsFdbNumDhcpEntries
            ACCESS  not-implemented
            DESCRIPTION
                 "Not supported.

                  Not supported."

        VARIATION   svcTlsFdbNumHostEntries
            ACCESS  not-implemented
            DESCRIPTION
                 "Not supported.

                  Not supported."

        VARIATION   svcTlsMcPathMgmtPlcyName
            ACCESS  not-implemented
            DESCRIPTION
                 "Not supported.

                  Not supported."

        VARIATION   svcTlsMrpAdminStatus
            ACCESS  not-implemented
            DESCRIPTION
                 "Not supported.

                  Not supported."

        VARIATION   svcTlsMrpAttrTblHighWatermark
            ACCESS  not-implemented
            DESCRIPTION
                 "Not supported.

                  Not supported."

        VARIATION   svcTlsMrpAttrTblLowWatermark
            ACCESS  not-implemented
            DESCRIPTION
                 "Not supported.

                  Not supported."

        VARIATION   svcTlsMrpAttributeCount
            ACCESS  not-implemented
            DESCRIPTION
                 "Not supported.

                  Not supported."

        VARIATION   svcTlsMrpFailedRegisterCount
            ACCESS  not-implemented
            DESCRIPTION
                 "Not supported.

                  Not supported."

        VARIATION   svcTlsMrpFloodTime
            ACCESS  not-implemented
            DESCRIPTION
                 "Not supported.

                  Not supported."

        VARIATION   svcTlsMrpMaxAttributes
            ACCESS  not-implemented
            DESCRIPTION
                 "Not supported.

                  Not supported."

        VARIATION   svcTlsShcvAction
            ACCESS  not-implemented
            DESCRIPTION
                 "Not supported.

                  Not supported."

        VARIATION   svcTlsShcvInterval
            ACCESS  not-implemented
            DESCRIPTION
                 "Not supported.

                  Not supported."

        VARIATION   svcTlsShcvSrcIp
            ACCESS  not-implemented
            DESCRIPTION
                 "Not supported.

                  Not supported."

        VARIATION   svcTlsShcvSrcMac
            ACCESS  not-implemented
            DESCRIPTION
                 "Not supported.

                  Not supported."

        VARIATION   svcTotalFdbMimDestIdxEntries
            ACCESS  not-implemented
            DESCRIPTION
                 "Not supported.

                  Not supported."

        VARIATION   svcType
            SYNTAX  INTEGER {
                       epipe                (1), -- Ethernet pipe
                       p3pipe               (2), -- POS pipe
                       tls                  (3), -- Virtual private LAN service
                       vprn                 (4), --Virtual private routed network
                       ies                  (5), -- Internet enhanced service
                       mirror               (6), -- Mirror service
                    -- apipe                (7) ATM pipe service
                    -- no aPIPE on SAS-R 7210
                    -- fpipe                (8) FR pipe service
                    -- no FPIPE on SAS-R 7210
                       ipipe                (9) -- IP interworking pipe service
                    -- cpipe                (10) Circuit Emulation pipe service
                    -- no CPIPE on SAS-R 7210
                    }
            DESCRIPTION
                 "The values - 'apipe (7)', - 'fpipe (8)', - 'cpipe (10)' are
                  invalid on a SAS-R 7210 system.

                  The values - 'apipe (7)', - 'fpipe (8)', - 'cpipe (10)' are
                  invalid on a SAS-R 7210 system."

        VARIATION   svcVllType
            SYNTAX  INTEGER {
                       undef                (1)
                    -- atmSdu               (6)
                    -- atmCell              (7)
                    -- atmVcc               (8)
                    -- atmVpc               (9)
                    -- frDlci               (10)
                    -- satopE3              (14)
                    -- satopT3              (15)
                    -- cesopsn              (16)
                    -- cesopsnCas           (17)
                    }
            DESCRIPTION
                 "The values - 'atmSdu (6)', - 'atmCell (7)', - 'atmVcc (8)', -
                  'atmVpc (9)', - 'frDlci (10)', - 'satopE3 (14)', - 'satopT3
                  (15)', - 'cesopsn (16)', - 'cesopsnCas (17)' are not supported
                  on a SAS-R 7210 system.

                  The values - 'atmSdu (6)', - 'atmCell (7)', - 'atmVcc (8)', -
                  'atmVpc (9)', - 'frDlci (10)', - 'satopE3 (14)', - 'satopT3
                  (15)', - 'cesopsn (16)', - 'cesopsnCas (17)' are not supported
                  on a SAS-R 7210 system."

        VARIATION   tlsEgrMcGrpAdminQinqFixedTagVal
            ACCESS  not-implemented
            DESCRIPTION
                 "Not supported.

                  Not supported."

        VARIATION   tlsEgrMcGrpQinqFixedTagPosition
            ACCESS  read-only
            DESCRIPTION
                 "read-only implementation.

                  read-only implementation."

        VARIATION   tlsFdbProtected
            ACCESS  not-implemented
            DESCRIPTION
                 "Not supported.

                  Not supported."

        VARIATION   tlsMFibStatsForwardedOctets
            ACCESS  not-implemented
            DESCRIPTION
                 "Not supported.

                  Not supported."

        VARIATION   tlsMFibStatsForwardedPkts
            ACCESS  not-implemented
            DESCRIPTION
                 "Not supported.

                  Not supported."

        VARIATION   tlsProtMacImplCount
            ACCESS  not-implemented
            DESCRIPTION
                 "Not supported.

                  Not supported."

        VARIATION   tlsProtMacLastMgmtChange
            ACCESS  not-implemented
            DESCRIPTION
                 "Not supported.

                  Not supported."

        VARIATION   tlsProtMacRowStatus
            ACCESS  not-implemented
            DESCRIPTION
                 "Not supported.

                  Not supported."

        VARIATION   tlsShgAutoLearnMacProtect
            ACCESS  not-implemented
            DESCRIPTION
                 "Not supported.

                  Not supported."

        VARIATION   tlsShgResidential
            ACCESS  not-implemented
            DESCRIPTION
                 "Not supported.

                  Not supported."

        VARIATION   tlsShgRestProtSrcMac
            ACCESS  not-implemented
            DESCRIPTION
                 "Not supported.

                  Not supported."

        VARIATION   tlsShgRestProtSrcMacAction
            ACCESS  not-implemented
            DESCRIPTION
                 "Not supported.

                  Not supported."

        VARIATION   tlsShgRestUnprotDstMac
            ACCESS  not-implemented
            DESCRIPTION
                 "Not supported.

                  Not supported."

    ::= { tmnxSASAgentV9v0  16 }

--
-- SAS SNMP CAPABILITIES
--
tmnxSASSnmpV9v0                   AGENT-CAPABILITIES
    PRODUCT-RELEASE "Alcatel-Lucent SAS"
    STATUS          current
    DESCRIPTION
         "Implementation of SNMP capabilities for Alcatel-Lucent SAS systems
          release 9.0."

    SUPPORTS        SNMP-COMMUNITY-MIB
        INCLUDES {
           snmpCommunityTableGroup
        }

        VARIATION   snmpCommunityContextEngineID
            ACCESS  read-only
            DESCRIPTION
                 "snmpCommunityContextEngineID is implemented as read-only
                  because only one SNMP Engine ID is supported. The engine ID
                  may change when a redundancy failover from active to standby
                  CPM happens.

                  snmpCommunityContextEngineID is implemented as read-only
                  because only one SNMP Engine ID is supported. The engine ID
                  may change when a redundancy failover from active to standby
                  CPM happens."

    SUPPORTS        SNMP-FRAMEWORK-MIB
        INCLUDES {
           snmpEngineGroup
        }

    SUPPORTS        SNMP-MPD-MIB
        INCLUDES {
           snmpMPDGroup
        }

    SUPPORTS        SNMP-NOTIFICATION-MIB
        INCLUDES {
           snmpNotifyFilterGroup,
           snmpNotifyGroup
        }

        VARIATION   snmpNotifyRowStatus
            DESCRIPTION
                 "The only values allowed for the snmpNotifyName index is the
                  ASCII numerical value of the TiMOS event log ID that the
                  notification group is associated with. Event log IDs have a
                  range of [1..100]. Leading zero, '0', characters are not
                  allowed.

                  The only values allowed for the snmpNotifyName index is the
                  ASCII numerical value of the TiMOS event log ID that the
                  notification group is associated with. Event log IDs have a
                  range of [1..100]. Leading zero, '0', characters are not
                  allowed."

    SUPPORTS        SNMP-TARGET-MIB
        INCLUDES {
           snmpTargetBasicGroup
-- EXCLUDE snmpTargetCommandResponderGroup,
-- EXCLUDE snmpTargetResponseGroup
        }

    SUPPORTS        SNMP-USER-BASED-SM-MIB
        INCLUDES {
           usmMIBBasicGroup
        }

        VARIATION   usmUserStorageType
            SYNTAX  INTEGER {
                       nonVolatile          (3)
                    }
            DESCRIPTION
                 "Only the StorageType TC value 'nonVolatile (3)' is supported
                  for usmUserStorageType.

                  Only the StorageType TC value 'nonVolatile (3)' is supported
                  for usmUserStorageType."

    SUPPORTS        SNMP-VIEW-BASED-ACM-MIB
        INCLUDES {
           vacmBasicGroup
        }

    SUPPORTS        SNMPv2-MIB
        INCLUDES {
-- EXCLUDE SNMPv2-MIB.snmpMIB
-- EXCLUDE SNMPv2-MIB.snmpProxyDrops
-- EXCLUDE SNMPv2-MIB.snmpSet
-- EXCLUDE SNMPv2-MIB.snmpSilentDrops
-- EXCLUDE SNMPv2-MIB.snmpTrap
-- EXCLUDE SNMPv2-MIB.sysORLastChange
-- EXCLUDE SNMPv2-MIB.sysORTable
           snmpBasicNotificationsGroup,
           snmpCommunityGroup,
           snmpGroup,
           snmpNotificationGroup,
           snmpObsoleteGroup,
           snmpWarmStartNotificationGroup,
           systemGroup
        }

        VARIATION   coldStart
            DESCRIPTION
                 "coldStart notification is generated on all system reboots -
                  not only for power cycle reboots.

                  coldStart notification is generated on all system reboots -
                  not only for power cycle reboots."

        VARIATION   snmpInBadValues
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGenErrs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGetNexts
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGetResponses
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInNoSuchNames
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInReadOnlys
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInSetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTooBigs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTotalReqVars
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTotalSetVars
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTraps
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutBadValues
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGenErrs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGetNexts
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGetResponses
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutNoSuchNames
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutPkts
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutSetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutTooBigs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutTraps
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   sysContact
            SYNTAX  DisplayString (SIZE(0..80))
            DESCRIPTION
                 "The maximum length supported for the system contact is 80
                  characters.

                  The maximum length supported for the system contact is 80
                  characters."

        VARIATION   sysLocation
            SYNTAX  DisplayString (SIZE(0..80))
            DESCRIPTION
                 "The maximum length supported for the system location is 80
                  characters.

                  The maximum length supported for the system location is 80
                  characters."

        VARIATION   sysName
            SYNTAX  DisplayString (SIZE(0..32))
            DESCRIPTION
                 "The maximum length supported for the system name is 32
                  characters. Setting sysName to the empty string, ''H, resets
                  sysName to the TiMOS default value.

                  The maximum length supported for the system name is 32
                  characters. Setting sysName to the empty string, ''H, resets
                  sysName to the TiMOS default value."

        VARIATION   sysORTable
            ACCESS  not-implemented
            DESCRIPTION
                 "sysORTable is not supported on Nokia SAS-R 7210 systems.

                  sysORTable is not supported on Nokia SAS-R 7210 systems."

        VARIATION   warmStart
            DESCRIPTION
                 "warmStart notification is generated by the new active CPM
                  following a CPM switchover. This notification has been
                  supported starting with the 7450 3.0 release.

                  When the standby CPM card takes over following a failure or
                  reboot of the active CPM card, tmnxRedPrimaryCPMFail,
                  sbiBootConfig and sbiBootSnmpd events from the
                  TIMETRA-SYSTEM-MIB are generated to indicate the secondary CPM
                  has successfully taken control of the system.

                  warmStart notification is generated by the new active CPM
                  following a CPM switchover. This notification has been
                  supported starting with the 7450 3.0 release.

                  When the standby CPM card takes over following a failure or
                  reboot of the active CPM card, tmnxRedPrimaryCPMFail,
                  sbiBootConfig and sbiBootSnmpd events from the
                  TIMETRA-SYSTEM-MIB are generated to indicate the secondary CPM
                  has successfully taken control of the system."

    ::= { tmnxSASAgentV9v0  14 }

--
-- SAS SNMP CAPABILITIES
--
tmnxSASSnmpV9v0                   AGENT-CAPABILITIES
    PRODUCT-RELEASE "Alcatel-Lucent SAS"
    STATUS          current
    DESCRIPTION
         "Implementation of SNMP capabilities for Alcatel-Lucent SAS systems
          release 9.0."

    SUPPORTS        SNMP-COMMUNITY-MIB
        INCLUDES {
           snmpCommunityTableGroup
        }

        VARIATION   snmpCommunityContextEngineID
            ACCESS  read-only
            DESCRIPTION
                 "snmpCommunityContextEngineID is implemented as read-only
                  because only one SNMP Engine ID is supported. The engine ID
                  may change when a redundancy failover from active to standby
                  CPM happens.

                  snmpCommunityContextEngineID is implemented as read-only
                  because only one SNMP Engine ID is supported. The engine ID
                  may change when a redundancy failover from active to standby
                  CPM happens."

    SUPPORTS        SNMP-FRAMEWORK-MIB
        INCLUDES {
           snmpEngineGroup
        }

    SUPPORTS        SNMP-MPD-MIB
        INCLUDES {
           snmpMPDGroup
        }

    SUPPORTS        SNMP-NOTIFICATION-MIB
        INCLUDES {
           snmpNotifyFilterGroup,
           snmpNotifyGroup
        }

        VARIATION   snmpNotifyRowStatus
            DESCRIPTION
                 "The only values allowed for the snmpNotifyName index is the
                  ASCII numerical value of the TiMOS event log ID that the
                  notification group is associated with. Event log IDs have a
                  range of [1..100]. Leading zero, '0', characters are not
                  allowed.

                  The only values allowed for the snmpNotifyName index is the
                  ASCII numerical value of the TiMOS event log ID that the
                  notification group is associated with. Event log IDs have a
                  range of [1..100]. Leading zero, '0', characters are not
                  allowed."

    SUPPORTS        SNMP-TARGET-MIB
        INCLUDES {
           snmpTargetBasicGroup
-- EXCLUDE snmpTargetCommandResponderGroup,
-- EXCLUDE snmpTargetResponseGroup
        }

    SUPPORTS        SNMP-USER-BASED-SM-MIB
        INCLUDES {
           usmMIBBasicGroup
        }

        VARIATION   usmUserStorageType
            SYNTAX  INTEGER {
                       nonVolatile          (3)
                    }
            DESCRIPTION
                 "Only the StorageType TC value 'nonVolatile (3)' is supported
                  for usmUserStorageType.

                  Only the StorageType TC value 'nonVolatile (3)' is supported
                  for usmUserStorageType."

    SUPPORTS        SNMP-VIEW-BASED-ACM-MIB
        INCLUDES {
           vacmBasicGroup
        }

    SUPPORTS        SNMPv2-MIB
        INCLUDES {
-- EXCLUDE SNMPv2-MIB.snmpMIB
-- EXCLUDE SNMPv2-MIB.snmpProxyDrops
-- EXCLUDE SNMPv2-MIB.snmpSet
-- EXCLUDE SNMPv2-MIB.snmpSilentDrops
-- EXCLUDE SNMPv2-MIB.snmpTrap
-- EXCLUDE SNMPv2-MIB.sysORLastChange
-- EXCLUDE SNMPv2-MIB.sysORTable
           snmpBasicNotificationsGroup,
           snmpCommunityGroup,
           snmpGroup,
           snmpNotificationGroup,
           snmpObsoleteGroup,
           snmpWarmStartNotificationGroup,
           systemGroup
        }

        VARIATION   coldStart
            DESCRIPTION
                 "coldStart notification is generated on all system reboots -
                  not only for power cycle reboots.

                  coldStart notification is generated on all system reboots -
                  not only for power cycle reboots."

        VARIATION   snmpInBadValues
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGenErrs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGetNexts
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInGetResponses
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInNoSuchNames
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInReadOnlys
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInSetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTooBigs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTotalReqVars
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTotalSetVars
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpInTraps
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutBadValues
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGenErrs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGetNexts
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutGetResponses
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutNoSuchNames
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutPkts
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutSetRequests
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutTooBigs
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   snmpOutTraps
            DESCRIPTION
                 "This object was defined in RFC1213 for SNMPv1 agents but it
                  was made obsolete in SNMPv2-MIB. However, many customers and
                  NMS developers find this counter useful so this agent
                  continues to support it.

                  This object was defined in RFC1213 for SNMPv1 agents but it
                  was made obsolete in SNMPv2-MIB. However, many customers and
                  NMS developers find this counter useful so this agent
                  continues to support it."

        VARIATION   sysContact
            SYNTAX  DisplayString (SIZE(0..80))
            DESCRIPTION
                 "The maximum length supported for the system contact is 80
                  characters.

                  The maximum length supported for the system contact is 80
                  characters."

        VARIATION   sysLocation
            SYNTAX  DisplayString (SIZE(0..80))
            DESCRIPTION
                 "The maximum length supported for the system location is 80
                  characters.

                  The maximum length supported for the system location is 80
                  characters."

        VARIATION   sysName
            SYNTAX  DisplayString (SIZE(0..32))
            DESCRIPTION
                 "The maximum length supported for the system name is 32
                  characters. Setting sysName to the empty string, ''H, resets
                  sysName to the TiMOS default value.

                  The maximum length supported for the system name is 32
                  characters. Setting sysName to the empty string, ''H, resets
                  sysName to the TiMOS default value."

        VARIATION   sysORTable
            ACCESS  not-implemented
            DESCRIPTION
                 "sysORTable is not supported on Nokia SAS-R 7210 systems.

                  sysORTable is not supported on Nokia SAS-R 7210 systems."

        VARIATION   warmStart
            DESCRIPTION
                 "warmStart notification is generated by the new active CPM
                  following a CPM switchover. This notification has been
                  supported starting with the 7450 3.0 release.

                  When the standby CPM card takes over following a failure or
                  reboot of the active CPM card, tmnxRedPrimaryCPMFail,
                  sbiBootConfig and sbiBootSnmpd events from the
                  TIMETRA-SYSTEM-MIB are generated to indicate the secondary CPM
                  has successfully taken control of the system.

                  warmStart notification is generated by the new active CPM
                  following a CPM switchover. This notification has been
                  supported starting with the 7450 3.0 release.

                  When the standby CPM card takes over following a failure or
                  reboot of the active CPM card, tmnxRedPrimaryCPMFail,
                  sbiBootConfig and sbiBootSnmpd events from the
                  TIMETRA-SYSTEM-MIB are generated to indicate the secondary CPM
                  has successfully taken control of the system."

    ::= { tmnxSASAgentV9v0  14 }

--
-- SAS SYSTEM CAPABILITIES
--
tmnxSASSystemV9v0                 AGENT-CAPABILITIES
    PRODUCT-RELEASE "Alcatel-Lucent SAS"
    STATUS          current
    DESCRIPTION
         "Implementation of System capabilities for Alcatel-Lucent SAS systems
          release 9.0."

    SUPPORTS        TIMETRA-SAS-SYSTEM-MIB
        INCLUDES {
           tmnxSASChassisGroup,
           tmnxSASSysConsoleV6v0Group,
           tmnxSASSysQosV5v0Group,
           tmnxSASSysV2v0Group,
           tmnxSASSysV3v0Group,
           tmnxSASSysV4v0Group,
           tmnxSASSysV5v0Group,
           tmnxSASSysV6v0Group
        }

        VARIATION   sbiExpansionCardType
            ACCESS  not-implemented
            DESCRIPTION
                 "Not supported.

                  Not supported."

        VARIATION   sbiNoServicePortOne
            ACCESS  not-implemented
            DESCRIPTION
                 "Not supported.

                  Not supported."

        VARIATION   sbiNoServicePortTwo
            ACCESS  not-implemented
            DESCRIPTION
                 "Not supported.

                  Not supported."

        VARIATION   sbiUplinkAdminMode
            ACCESS  not-implemented
            DESCRIPTION
                 "Not supported.

                  Not supported."

        VARIATION   sbiUplinkOperMode
            ACCESS  not-implemented
            DESCRIPTION
                 "Not supported.

                  Not supported."

        VARIATION   sysDhcpSnoopingEnable
            ACCESS  not-implemented
            DESCRIPTION
                 "Not supported.

                  Not supported."

        VARIATION   sysDhcpSnoopingSdpEnable
            ACCESS  not-implemented
            DESCRIPTION
                 "Not supported.

                  Not supported."

        VARIATION   sysG8032FastFloodEnable
            ACCESS  not-implemented
            DESCRIPTION
                 "Not supported.

                  Not supported."

        VARIATION   sysResEgrSapEgrClass
            ACCESS  not-implemented
            DESCRIPTION
                 "Not supported.

                  Not supported."

        VARIATION   sysResEgrSapEgrClassIpv4
            ACCESS  not-implemented
            DESCRIPTION
                 "Not supported.

                  Not supported."

        VARIATION   sysResEgrSapEgrClassIpv4Ipv6
            ACCESS  not-implemented
            DESCRIPTION
                 "Not supported.

                  Not supported."

        VARIATION   sysResEgrSapEgrClassMac
            ACCESS  not-implemented
            DESCRIPTION
                 "Not supported.

                  Not supported."

        VARIATION   sysResEgrTcamEgrAcl128bitIpv4Ipv6
            ACCESS  not-implemented
            DESCRIPTION
                 "Not supported.

                  Not supported."

        VARIATION   sysResEgrTcamEgrAcl64bitIpv4Ipv6
            ACCESS  not-implemented
            DESCRIPTION
                 "Not supported.

                  Not supported."

        VARIATION   sysResEgrTcamEgrAcl64bitIpv6Only
            ACCESS  not-implemented
            DESCRIPTION
                 "Not supported.

                  Not supported."

        VARIATION   sysResEgrTcamEgrAclIpv4
            ACCESS  not-implemented
            DESCRIPTION
                 "Not supported.

                  Not supported."

        VARIATION   sysResEgrTcamEgrAclMac
            ACCESS  not-implemented
            DESCRIPTION
                 "Not supported.

                  Not supported."

        VARIATION   sysResEgrTcamSapEgrAcl
            ACCESS  not-implemented
            DESCRIPTION
                 "Not supported.

                  Not supported."

        VARIATION   sysResFabricPathBandwidth
            ACCESS  not-implemented
            DESCRIPTION
                 "Not supported.

                  Not supported."

        VARIATION   sysResIngSapIngClass
            ACCESS  not-implemented
            DESCRIPTION
                 "Not supported.

                  Not supported."

        VARIATION   sysResIngSapIngClassIpv4
            ACCESS  not-implemented
            DESCRIPTION
                 "Not supported.

                  Not supported."

        VARIATION   sysResIngSapIngClassIpv4Ipv6
            ACCESS  not-implemented
            DESCRIPTION
                 "Not supported.

                  Not supported."

        VARIATION   sysResIngSapIngClassMac
            ACCESS  not-implemented
            DESCRIPTION
                 "Not supported.

                  Not supported."

        VARIATION   sysResIngTcamEthCfm
            ACCESS  not-implemented
            DESCRIPTION
                 "Not supported.

                  Not supported."

        VARIATION   sysResIngTcamEthCfmUpMep
            ACCESS  not-implemented
            DESCRIPTION
                 "Not supported.

                  Not supported."

        VARIATION   sysResIngTcamIngAcl128bitIpv4Ipv6
            ACCESS  not-implemented
            DESCRIPTION
                 "Not supported.

                  Not supported."

        VARIATION   sysResIngTcamIngAcl64bitIpv4Ipv6
            ACCESS  not-implemented
            DESCRIPTION
                 "Not supported.

                  Not supported."

        VARIATION   sysResIngTcamIngAcl64bitIpv6Only
            ACCESS  not-implemented
            DESCRIPTION
                 "Not supported.

                  Not supported."

        VARIATION   sysResIngTcamIngAclIpv4
            ACCESS  not-implemented
            DESCRIPTION
                 "Not supported.

                  Not supported."

        VARIATION   sysResIngTcamIngAclMac
            ACCESS  not-implemented
            DESCRIPTION
                 "Not supported.

                  Not supported."

        VARIATION   sysResIngTcamSapAggMeter
            ACCESS  not-implemented
            DESCRIPTION
                 "Not supported.

                  Not supported."

        VARIATION   sysResIngTcamSapAggMeterOperVal
            ACCESS  not-implemented
            DESCRIPTION
                 "Not supported.

                  Not supported."

        VARIATION   sysResIngTcamSapIngAcl
            ACCESS  not-implemented
            DESCRIPTION
                 "Not supported.

                  Not supported."

        VARIATION   sysResQosSapIngQMode
            ACCESS  not-implemented
            DESCRIPTION
                 "Not supported.

                  Not supported."

        VARIATION   sysResQosSapIngQOperMode
            ACCESS  not-implemented
            DESCRIPTION
                 "Not supported.

                  Not supported."

        VARIATION   sysResRouterEcmpMaxRoutesDstOperVal
            ACCESS  not-implemented
            DESCRIPTION
                 "Not supported.

                  Not supported."

        VARIATION   tmnxChassisFanCfgMode
            ACCESS  not-implemented
            DESCRIPTION
                 "Not supported.

                  Not supported."

        VARIATION   tmnxChassisFanOperMode
            ACCESS  not-implemented
            DESCRIPTION
                 "Not supported.

                  Not supported."

        VARIATION   tmnxChassisGoldenBootstrapImageSrc
            ACCESS  not-implemented
            DESCRIPTION
                 "Not supported.

                  Not supported."

        VARIATION   tmnxChassisGoldenBootstrapImageVersion
            ACCESS  not-implemented
            DESCRIPTION
                 "Not supported.

                  Not supported."

        VARIATION   tmnxChassisRebootAutoInit
            ACCESS  not-implemented
            DESCRIPTION
                 "Not supported.

                  Not supported."

        VARIATION   tmnxChassisSystemLEDState
            ACCESS  not-implemented
            DESCRIPTION
                 "Not supported.

                  Not supported."

        VARIATION   tmnxChassisUpdateGoldenBootstrapImage
            ACCESS  not-implemented
            DESCRIPTION
                 "Not supported.

                  Not supported."

        VARIATION   tmnxChassisValidateGoldenBootstrapImage
            ACCESS  not-implemented
            DESCRIPTION
                 "Not supported.

                  Not supported."

        VARIATION   tmnxFabricPolicyCBS
            ACCESS  not-implemented
            DESCRIPTION
                 "Not supported.

                  Not supported."

        VARIATION   tmnxFabricPolicyCIR
            ACCESS  not-implemented
            DESCRIPTION
                 "Not supported.

                  Not supported."

        VARIATION   tmnxFabricPolicyIndex
            ACCESS  not-implemented
            DESCRIPTION
                 "Not supported.

                  Not supported."

        VARIATION   tmnxFabricPolicyMBS
            ACCESS  not-implemented
            DESCRIPTION
                 "Not supported.

                  Not supported."

        VARIATION   tmnxFabricPolicyMpointFabricPort
            ACCESS  not-implemented
            DESCRIPTION
                 "Not supported.

                  Not supported."

        VARIATION   tmnxFabricPolicyPIR
            ACCESS  not-implemented
            DESCRIPTION
                 "Not supported.

                  Not supported."

        VARIATION   tmnxFabricPolicyRowStatus
            ACCESS  not-implemented
            DESCRIPTION
                 "Not supported.

                  Not supported."

        VARIATION   tmnxSysConsoleAlarmInput
            ACCESS  not-implemented
            DESCRIPTION
                 "Not supported.

                  Not supported."

    SUPPORTS        TIMETRA-SYSTEM-MIB
        INCLUDES {
           tmnxSysBofV6v0Group,
           tmnxSysConfigV3v0Group,
           tmnxSysGeneralV3v0Group,
           tmnxSysGeneralV7v0Group,
           tmnxSysIcmpVSV6v1Group,
           tmnxSysLoginControlSecGroup,
           tmnxSysNotificationV6v0Group,
           tmnxSysRadiusServerV5v0Group,
           tmnxSysTacPlusServerV5v0Group,
           tmnxSysTimeV4v0Group
        }

        VARIATION   sbiLiLocalSave
            ACCESS  not-implemented
            DESCRIPTION
                 "Not supported.

                  Not supported."

        VARIATION   sbiLiSeparate
            ACCESS  not-implemented
            DESCRIPTION
                 "Not supported.

                  Not supported."

        VARIATION   sbiStandbyIpAddr
            ACCESS  not-implemented
            DESCRIPTION
                 "Not supported.

                  Not supported."

        VARIATION   sbiStandbyIpMask
            ACCESS  not-implemented
            DESCRIPTION
                 "Not supported.

                  Not supported."

        VARIATION   sbiStaticRouteNextHop
            ACCESS  not-implemented
            DESCRIPTION
                 "Not supported.

                  Not supported."

        VARIATION   sbiStaticRouteRowStatus
            ACCESS  not-implemented
            DESCRIPTION
                 "Not supported.

                  Not supported."

        VARIATION   sgiKbMemoryAvailable
            ACCESS  not-implemented
            DESCRIPTION
                 "Not supported.

                  Not supported."

        VARIATION   sgiKbMemoryPoolAllocated
            ACCESS  not-implemented
            DESCRIPTION
                 "Not supported.

                  Not supported."

        VARIATION   sgiKbMemoryUsed
            ACCESS  not-implemented
            DESCRIPTION
                 "Not supported.

                  Not supported."

        VARIATION   slcSSHMinTTLValue
            ACCESS  not-implemented
            DESCRIPTION
                 "Not supported.

                  Not supported."

        VARIATION   slcTelnetMinTTLValue
            ACCESS  not-implemented
            DESCRIPTION
                 "Not supported.

                  Not supported."

        VARIATION   sntpTimeDiffExceedsThreshold
            ACCESS  not-implemented
            DESCRIPTION
                 "Not supported.

                  Not supported."

        VARIATION   spiDhcpSrvPersistenceDescr
            ACCESS  not-implemented
            DESCRIPTION
                 "Not supported.

                  Not supported."

        VARIATION   spiDhcpSrvPersistenceFileLoc
            ACCESS  not-implemented
            DESCRIPTION
                 "Not supported.

                  Not supported."

        VARIATION   sysIcmpVSEnhancement
            ACCESS  not-implemented
            DESCRIPTION
                 "Not supported.

                  Not supported."

    ::= { tmnxSASAgentV9v0  17 }

--
-- SAS SYSTEM CAPABILITIES
--
tmnxSASSystemV9v0                 AGENT-CAPABILITIES
    PRODUCT-RELEASE "Alcatel-Lucent SAS"
    STATUS          current
    DESCRIPTION
         "Implementation of System capabilities for Alcatel-Lucent SAS systems
          release 9.0."

    SUPPORTS        TIMETRA-SAS-SYSTEM-MIB
        INCLUDES {
           tmnxSASChassisGroup,
           tmnxSASSysConsoleV6v0Group,
           tmnxSASSysQosV5v0Group,
           tmnxSASSysV2v0Group,
           tmnxSASSysV3v0Group,
           tmnxSASSysV4v0Group,
           tmnxSASSysV5v0Group,
           tmnxSASSysV6v0Group
        }

        VARIATION   sbiExpansionCardType
            ACCESS  not-implemented
            DESCRIPTION
                 "Not supported.

                  Not supported."

        VARIATION   sbiNoServicePortOne
            ACCESS  not-implemented
            DESCRIPTION
                 "Not supported.

                  Not supported."

        VARIATION   sbiNoServicePortTwo
            ACCESS  not-implemented
            DESCRIPTION
                 "Not supported.

                  Not supported."

        VARIATION   sbiUplinkAdminMode
            ACCESS  not-implemented
            DESCRIPTION
                 "Not supported.

                  Not supported."

        VARIATION   sbiUplinkOperMode
            ACCESS  not-implemented
            DESCRIPTION
                 "Not supported.

                  Not supported."

        VARIATION   sysDhcpSnoopingEnable
            ACCESS  not-implemented
            DESCRIPTION
                 "Not supported.

                  Not supported."

        VARIATION   sysDhcpSnoopingSdpEnable
            ACCESS  not-implemented
            DESCRIPTION
                 "Not supported.

                  Not supported."

        VARIATION   sysG8032FastFloodEnable
            ACCESS  not-implemented
            DESCRIPTION
                 "Not supported.

                  Not supported."

        VARIATION   sysResEgrSapEgrClass
            ACCESS  not-implemented
            DESCRIPTION
                 "Not supported.

                  Not supported."

        VARIATION   sysResEgrSapEgrClassIpv4
            ACCESS  not-implemented
            DESCRIPTION
                 "Not supported.

                  Not supported."

        VARIATION   sysResEgrSapEgrClassIpv4Ipv6
            ACCESS  not-implemented
            DESCRIPTION
                 "Not supported.

                  Not supported."

        VARIATION   sysResEgrSapEgrClassMac
            ACCESS  not-implemented
            DESCRIPTION
                 "Not supported.

                  Not supported."

        VARIATION   sysResEgrTcamEgrAcl128bitIpv4Ipv6
            ACCESS  not-implemented
            DESCRIPTION
                 "Not supported.

                  Not supported."

        VARIATION   sysResEgrTcamEgrAcl64bitIpv4Ipv6
            ACCESS  not-implemented
            DESCRIPTION
                 "Not supported.

                  Not supported."

        VARIATION   sysResEgrTcamEgrAcl64bitIpv6Only
            ACCESS  not-implemented
            DESCRIPTION
                 "Not supported.

                  Not supported."

        VARIATION   sysResEgrTcamEgrAclIpv4
            ACCESS  not-implemented
            DESCRIPTION
                 "Not supported.

                  Not supported."

        VARIATION   sysResEgrTcamEgrAclMac
            ACCESS  not-implemented
            DESCRIPTION
                 "Not supported.

                  Not supported."

        VARIATION   sysResEgrTcamSapEgrAcl
            ACCESS  not-implemented
            DESCRIPTION
                 "Not supported.

                  Not supported."

        VARIATION   sysResFabricPathBandwidth
            ACCESS  not-implemented
            DESCRIPTION
                 "Not supported.

                  Not supported."

        VARIATION   sysResIngSapIngClass
            ACCESS  not-implemented
            DESCRIPTION
                 "Not supported.

                  Not supported."

        VARIATION   sysResIngSapIngClassIpv4
            ACCESS  not-implemented
            DESCRIPTION
                 "Not supported.

                  Not supported."

        VARIATION   sysResIngSapIngClassIpv4Ipv6
            ACCESS  not-implemented
            DESCRIPTION
                 "Not supported.

                  Not supported."

        VARIATION   sysResIngSapIngClassMac
            ACCESS  not-implemented
            DESCRIPTION
                 "Not supported.

                  Not supported."

        VARIATION   sysResIngTcamEthCfm
            ACCESS  not-implemented
            DESCRIPTION
                 "Not supported.

                  Not supported."

        VARIATION   sysResIngTcamEthCfmUpMep
            ACCESS  not-implemented
            DESCRIPTION
                 "Not supported.

                  Not supported."

        VARIATION   sysResIngTcamIngAcl128bitIpv4Ipv6
            ACCESS  not-implemented
            DESCRIPTION
                 "Not supported.

                  Not supported."

        VARIATION   sysResIngTcamIngAcl64bitIpv4Ipv6
            ACCESS  not-implemented
            DESCRIPTION
                 "Not supported.

                  Not supported."

        VARIATION   sysResIngTcamIngAcl64bitIpv6Only
            ACCESS  not-implemented
            DESCRIPTION
                 "Not supported.

                  Not supported."

        VARIATION   sysResIngTcamIngAclIpv4
            ACCESS  not-implemented
            DESCRIPTION
                 "Not supported.

                  Not supported."

        VARIATION   sysResIngTcamIngAclMac
            ACCESS  not-implemented
            DESCRIPTION
                 "Not supported.

                  Not supported."

        VARIATION   sysResIngTcamSapAggMeter
            ACCESS  not-implemented
            DESCRIPTION
                 "Not supported.

                  Not supported."

        VARIATION   sysResIngTcamSapAggMeterOperVal
            ACCESS  not-implemented
            DESCRIPTION
                 "Not supported.

                  Not supported."

        VARIATION   sysResIngTcamSapIngAcl
            ACCESS  not-implemented
            DESCRIPTION
                 "Not supported.

                  Not supported."

        VARIATION   sysResQosSapIngQMode
            ACCESS  not-implemented
            DESCRIPTION
                 "Not supported.

                  Not supported."

        VARIATION   sysResQosSapIngQOperMode
            ACCESS  not-implemented
            DESCRIPTION
                 "Not supported.

                  Not supported."

        VARIATION   sysResRouterEcmpMaxRoutesDstOperVal
            ACCESS  not-implemented
            DESCRIPTION
                 "Not supported.

                  Not supported."

        VARIATION   tmnxChassisFanCfgMode
            ACCESS  not-implemented
            DESCRIPTION
                 "Not supported.

                  Not supported."

        VARIATION   tmnxChassisFanOperMode
            ACCESS  not-implemented
            DESCRIPTION
                 "Not supported.

                  Not supported."

        VARIATION   tmnxChassisGoldenBootstrapImageSrc
            ACCESS  not-implemented
            DESCRIPTION
                 "Not supported.

                  Not supported."

        VARIATION   tmnxChassisGoldenBootstrapImageVersion
            ACCESS  not-implemented
            DESCRIPTION
                 "Not supported.

                  Not supported."

        VARIATION   tmnxChassisRebootAutoInit
            ACCESS  not-implemented
            DESCRIPTION
                 "Not supported.

                  Not supported."

        VARIATION   tmnxChassisSystemLEDState
            ACCESS  not-implemented
            DESCRIPTION
                 "Not supported.

                  Not supported."

        VARIATION   tmnxChassisUpdateGoldenBootstrapImage
            ACCESS  not-implemented
            DESCRIPTION
                 "Not supported.

                  Not supported."

        VARIATION   tmnxChassisValidateGoldenBootstrapImage
            ACCESS  not-implemented
            DESCRIPTION
                 "Not supported.

                  Not supported."

        VARIATION   tmnxFabricPolicyCBS
            ACCESS  not-implemented
            DESCRIPTION
                 "Not supported.

                  Not supported."

        VARIATION   tmnxFabricPolicyCIR
            ACCESS  not-implemented
            DESCRIPTION
                 "Not supported.

                  Not supported."

        VARIATION   tmnxFabricPolicyIndex
            ACCESS  not-implemented
            DESCRIPTION
                 "Not supported.

                  Not supported."

        VARIATION   tmnxFabricPolicyMBS
            ACCESS  not-implemented
            DESCRIPTION
                 "Not supported.

                  Not supported."

        VARIATION   tmnxFabricPolicyMpointFabricPort
            ACCESS  not-implemented
            DESCRIPTION
                 "Not supported.

                  Not supported."

        VARIATION   tmnxFabricPolicyPIR
            ACCESS  not-implemented
            DESCRIPTION
                 "Not supported.

                  Not supported."

        VARIATION   tmnxFabricPolicyRowStatus
            ACCESS  not-implemented
            DESCRIPTION
                 "Not supported.

                  Not supported."

        VARIATION   tmnxSysConsoleAlarmInput
            ACCESS  not-implemented
            DESCRIPTION
                 "Not supported.

                  Not supported."

    SUPPORTS        TIMETRA-SYSTEM-MIB
        INCLUDES {
           tmnxSysBofV6v0Group,
           tmnxSysConfigV3v0Group,
           tmnxSysGeneralV3v0Group,
           tmnxSysGeneralV7v0Group,
           tmnxSysIcmpVSV6v1Group,
           tmnxSysLoginControlSecGroup,
           tmnxSysNotificationV6v0Group,
           tmnxSysRadiusServerV5v0Group,
           tmnxSysTacPlusServerV5v0Group,
           tmnxSysTimeV4v0Group
        }

        VARIATION   sbiLiLocalSave
            ACCESS  not-implemented
            DESCRIPTION
                 "Not supported.

                  Not supported."

        VARIATION   sbiLiSeparate
            ACCESS  not-implemented
            DESCRIPTION
                 "Not supported.

                  Not supported."

        VARIATION   sbiStandbyIpAddr
            ACCESS  not-implemented
            DESCRIPTION
                 "Not supported.

                  Not supported."

        VARIATION   sbiStandbyIpMask
            ACCESS  not-implemented
            DESCRIPTION
                 "Not supported.

                  Not supported."

        VARIATION   sbiStaticRouteNextHop
            ACCESS  not-implemented
            DESCRIPTION
                 "Not supported.

                  Not supported."

        VARIATION   sbiStaticRouteRowStatus
            ACCESS  not-implemented
            DESCRIPTION
                 "Not supported.

                  Not supported."

        VARIATION   sgiKbMemoryAvailable
            ACCESS  not-implemented
            DESCRIPTION
                 "Not supported.

                  Not supported."

        VARIATION   sgiKbMemoryPoolAllocated
            ACCESS  not-implemented
            DESCRIPTION
                 "Not supported.

                  Not supported."

        VARIATION   sgiKbMemoryUsed
            ACCESS  not-implemented
            DESCRIPTION
                 "Not supported.

                  Not supported."

        VARIATION   slcSSHMinTTLValue
            ACCESS  not-implemented
            DESCRIPTION
                 "Not supported.

                  Not supported."

        VARIATION   slcTelnetMinTTLValue
            ACCESS  not-implemented
            DESCRIPTION
                 "Not supported.

                  Not supported."

        VARIATION   sntpTimeDiffExceedsThreshold
            ACCESS  not-implemented
            DESCRIPTION
                 "Not supported.

                  Not supported."

        VARIATION   spiDhcpSrvPersistenceDescr
            ACCESS  not-implemented
            DESCRIPTION
                 "Not supported.

                  Not supported."

        VARIATION   spiDhcpSrvPersistenceFileLoc
            ACCESS  not-implemented
            DESCRIPTION
                 "Not supported.

                  Not supported."

        VARIATION   sysIcmpVSEnhancement
            ACCESS  not-implemented
            DESCRIPTION
                 "Not supported.

                  Not supported."

    ::= { tmnxSASAgentV9v0  17 }

--
-- SAS TWAMP CAPABILITIES
--
tmnxSASTwampV9v0                  AGENT-CAPABILITIES
    PRODUCT-RELEASE "Alcatel-Lucent SAS"
    STATUS          current
    DESCRIPTION
         "Implementation of Two-Way Active Measurement Protocol (TWAMP)
          capabilities for Alcatel-Lucent SAS systems release 9.0."

    SUPPORTS        TIMETRA-TWAMP-MIB
        INCLUDES {
           tmnxTwampSrvNotifyObjsV9v0Group,
           tmnxTwampSrvNotifyV9v0Group,
           tmnxTwampSrvV9v0Group
        }

        VARIATION   tmnxTwampSrvMaxConnections
            DESCRIPTION
                 "tmnxTwampSrvMaxConnections has a range of 0 to 16 with default
                  as 8

                  tmnxTwampSrvMaxConnections has a range of 0 to 16 with
                  default as 8"

        VARIATION   tmnxTwampSrvMaxSessions
            DESCRIPTION
                 "tmnxTwampSrvMaxSessions has a range of 0 to 16 with default as
                  8

                  tmnxTwampSrvMaxSessions has a range of 0 to 16 with default
                  as 8"

        VARIATION   tmnxTwampSrvPrefixMaxConnections
            DESCRIPTION
                 "tmnxTwampSrvPrefixMaxConnections has a range of 0 to 16 with
                  default as 8

                  tmnxTwampSrvPrefixMaxConnections has a range of 0 to 16 with
                  default as 8"

        VARIATION   tmnxTwampSrvPrefixMaxSessions
            DESCRIPTION
                 "tmnxTwampSrvPrefixMaxSessions has a range of 0 to 16 with
                  default as 8

                  tmnxTwampSrvPrefixMaxSessions has a range of 0 to 16 with
                  default as 8"

    ::= { tmnxSASAgentV9v0  32 }

--
-- SAS TWAMP CAPABILITIES
--
tmnxSASTwampV9v0                  AGENT-CAPABILITIES
    PRODUCT-RELEASE "Alcatel-Lucent SAS"
    STATUS          current
    DESCRIPTION
         "Implementation of Two-Way Active Measurement Protocol (TWAMP)
          capabilities for Alcatel-Lucent SAS systems release 9.0."

    SUPPORTS        TIMETRA-TWAMP-MIB
        INCLUDES {
           tmnxTwampSrvNotifyObjsV9v0Group,
           tmnxTwampSrvNotifyV9v0Group,
           tmnxTwampSrvV9v0Group
        }

        VARIATION   tmnxTwampSrvMaxConnections
            DESCRIPTION
                 "tmnxTwampSrvMaxConnections has a range of 0 to 16 with default
                  as 8

                  tmnxTwampSrvMaxConnections has a range of 0 to 16 with
                  default as 8"

        VARIATION   tmnxTwampSrvMaxSessions
            DESCRIPTION
                 "tmnxTwampSrvMaxSessions has a range of 0 to 16 with default as
                  8

                  tmnxTwampSrvMaxSessions has a range of 0 to 16 with default
                  as 8"

        VARIATION   tmnxTwampSrvPrefixMaxConnections
            DESCRIPTION
                 "tmnxTwampSrvPrefixMaxConnections has a range of 0 to 16 with
                  default as 8

                  tmnxTwampSrvPrefixMaxConnections has a range of 0 to 16 with
                  default as 8"

        VARIATION   tmnxTwampSrvPrefixMaxSessions
            DESCRIPTION
                 "tmnxTwampSrvPrefixMaxSessions has a range of 0 to 16 with
                  default as 8

                  tmnxTwampSrvPrefixMaxSessions has a range of 0 to 16 with
                  default as 8"

    ::= { tmnxSASAgentV9v0  32 }

--
-- SASR VRRP CAPABILITIES
--
tmnxSASRVrrpV9v0                  AGENT-CAPABILITIES
    PRODUCT-RELEASE "Alcatel-Lucent SAS"
    STATUS          current
    DESCRIPTION
         "Implementation of VRRP protocol capabilities for Alcatel-Lucent SASR
          systems release 9.0."

    SUPPORTS        TIMETRA-VRRP-MIB
        INCLUDES {
           tVrrpBfdV9v0Group,
           tVrrpHostUnreachableV7v0Group,
           tVrrpMasterV7v0Group,
           tVrrpNotificationV7v0Group,
           tVrrpOpV7v0Group,
           tVrrpRouteUnknownV7v0Group,
           tVrrpRouterAdverV7v0Group,
           tVrrpStatV7v0Group,
           tmnxVrrpNotificationV6v1Group,
           tmnxVrrpOperV6v1Group,
           tmnxVrrpPolicyV5v0Group,
           tmnxVrrpPriorityEventsGroup,
           tmnxVrrpRouteMasterGroup,
           tmnxVrrpStatsGroup
        }

        VARIATION   tmnxVrrpOperVirtualMacAddr
            ACCESS  not-implemented
            DESCRIPTION
                 "Not supported."

    ::= { tmnxSASRAgentV9v0  35 }

--
-- SAS VRTR CAPABILITIES
--
tmnxSASVrtrV9v0                   AGENT-CAPABILITIES
    PRODUCT-RELEASE "Alcatel-Lucent SAS"
    STATUS          current
    DESCRIPTION
         "Implementation of Virtual Router capabilities for Alcatel-Lucent SAS
          systems release 9.0."

    SUPPORTS        TIMETRA-VRTR-MIB
        INCLUDES {
           tmnxDscpAppV6v0Group,
           tmnxVRtrBfdV6v0Group,
           tmnxVRtrDHCPIfLseStatesExceeded,
           tmnxVRtrGlobalV6v0Group,
           tmnxVRtrIfDHCPRelayV6v1Group,
           tmnxVRtrIfDHCPRelayV9v0Group,
           tmnxVRtrIfSubscrAuthV3v0Group,
           tmnxVRtrIfV5v0Group,
           tmnxVRtrIpV7v0Group,
           tmnxVRtrNotificationV7v0Group,
           tmnxVRtrQosQGrplV10v0Group,
           tmnxVRtrV6v1Group,
           tmnxVRtrV7v0Group
        }

        VARIATION   tmnxDot1pAppId
            SYNTAX  INTEGER {
                       arp                  (1),
                       isis                 (2)
                    -- pppoe                (3)
                    }
            DESCRIPTION
                 "tmnxDot1pAppId does not support value 'pppoe (3)' as PPPoE is
                  not available on SAS-R 7210 systems.

                  tmnxDot1pAppId does not support value 'pppoe (3)' as PPPoE is
                  not available on SAS-R 7210 systems."

        VARIATION   tmnxDscpAppId
            SYNTAX  INTEGER {
                       bgp                  (1),
                    -- cflowd               (2)
                       dhcp                 (3),
                       dns                  (4),
                       ftp                  (5),
                       icmp                 (6),
                    -- igmp                 (7)
                    -- l2tp                 (8)
                       ldp                  (9),
                    -- mld                  (10)
                    -- msdp                 (11)
                    -- ndis                 (12)
                       ntp                  (13),
                       ospf                 (14),
                    -- pim                  (15)
                       radius               (16),
                       rip                  (17),
                       rsvp                 (18),
                       snmp                 (19),
                       snmp-notification    (20),
                    -- srrp                 (21)
                       ssh                  (22),
                       syslog               (23),
                       tacplus              (24),
                       telnet               (25),
                       tftp                 (26),
                       traceroute           (27),
                       vrrp                 (28)
                    }
            DESCRIPTION
                 "tmnxDscpAppId does not support TDSCPAppId values of 'srrp',
                  'cflowd', 'igmp', 'mld', 'msdp', 'ndis' and 'pim' as SRRP,
                  CFLOWD, IGMP, MLD, MSDP, IPv6 and PIM are not available on
                  SAS-R 7210 systems.

                  tmnxDscpAppId does not support TDSCPAppId values of 'srrp',
                  'cflowd', 'igmp', 'mld', 'msdp', 'ndis' and 'pim' as SRRP,
                  CFLOWD, IGMP, MLD, MSDP, IPv6 and PIM are not available on
                  SAS-R 7210 systems."

        VARIATION   vRiaInetGwAddress
            ACCESS  not-implemented
            DESCRIPTION
                 "Not supported.

                  Not supported.

                  Not supported.

                  Not supported."

        VARIATION   vRiaInetGwAddressType
            ACCESS  not-implemented
            DESCRIPTION
                 "Not supported.

                  Not supported.

                  Not supported.

                  Not supported."

        VARIATION   vRtrConfederationAS4Byte
            ACCESS  not-implemented
            DESCRIPTION
                 "Not supported.

                  Not supported."

        VARIATION   vRtrDHCP6DropStatLastCleared
            ACCESS  not-implemented
            DESCRIPTION
                 "Not supported.

                  Not supported."

        VARIATION   vRtrDHCP6DropStatPktsDropped
            ACCESS  not-implemented
            DESCRIPTION
                 "Not supported.

                  Not supported."

        VARIATION   vRtrDHCP6MsgStatsDropped
            ACCESS  not-implemented
            DESCRIPTION
                 "Not supported.

                  Not supported."

        VARIATION   vRtrDHCP6MsgStatsLstClrd
            ACCESS  not-implemented
            DESCRIPTION
                 "Not supported.

                  Not supported."

        VARIATION   vRtrDHCP6MsgStatsRcvd
            ACCESS  not-implemented
            DESCRIPTION
                 "Not supported.

                  Not supported."

        VARIATION   vRtrDHCP6MsgStatsSent
            ACCESS  not-implemented
            DESCRIPTION
                 "Not supported.

                  Not supported.

                  Not supported.

                  Not supported."

        VARIATION   vRtrHighRouteThreshold
            ACCESS  not-implemented
            DESCRIPTION
                 "Not supported.

                  Not supported."

        VARIATION   vRtrIPv6HighRouteThreshold
            ACCESS  not-implemented
            DESCRIPTION
                 "Not supported.

                  Not supported."

        VARIATION   vRtrIPv6RouteThresholdSoakTime
            ACCESS  not-implemented
            DESCRIPTION
                 "Not supported.

                  Not supported."

        VARIATION   vRtrIfCflowd
            ACCESS  not-implemented
            DESCRIPTION
                 "Not supported (No CFLOWD).

                  Not supported (No CFLOWD)."

        VARIATION   vRtrIfDHCPAntiSpoofMacAddr
            ACCESS  not-implemented
            DESCRIPTION
                 "Not supported.

                  Not supported."

        VARIATION   vRtrIfDHCPAuthPolicy
            ACCESS  not-implemented
            DESCRIPTION
                 "Not supported.

                  Not supported."

        VARIATION   vRtrIfDHCPFilterId
            ACCESS  not-implemented
            DESCRIPTION
                 "Not supported.

                  Not supported."

        VARIATION   vRtrIfDHCPLayer2Header
            ACCESS  not-implemented
            DESCRIPTION
                 "Not supported.

                  Not supported."

        VARIATION   vRtrIfDHCPLeasePopulate
            DESCRIPTION
                 "The default value of vRtrIfDHCPLeasePopulate is '1', not '0',
                  when the interface running DHCP has vRtrIfType
                  'serviceIesGroup'.

                  The default value of vRtrIfDHCPLeasePopulate is '1', not '0',
                  when the interface running DHCP has vRtrIfType
                  'serviceIesGroup'.

                  Not supported.

                  Not supported."

        VARIATION   vRtrIfDHCPMatchOption82
            ACCESS  not-implemented
            DESCRIPTION
                 "Not supported.

                  Not supported."

        VARIATION   vRtrIfDHCPOperLeasePopulate
            ACCESS  not-implemented
            DESCRIPTION
                 "Not supported.

                  Not supported."

        VARIATION   vRtrIfDHCPProxyAdminState
            ACCESS  not-implemented
            DESCRIPTION
                 "Not supported.

                  Not supported."

        VARIATION   vRtrIfDHCPProxyLTRadiusOverride
            ACCESS  not-implemented
            DESCRIPTION
                 "Not supported.

                  Not supported."

        VARIATION   vRtrIfDHCPProxyLeaseTime
            ACCESS  not-implemented
            DESCRIPTION
                 "Not supported.

                  Not supported."

        VARIATION   vRtrIfDHCPProxyServerAddr
            ACCESS  not-implemented
            DESCRIPTION
                 "Not supported.

                  Not supported."

        VARIATION   vRtrIfDHCPUseArpForReply
            ACCESS  not-implemented
            DESCRIPTION
                 "Not supported.

                  Not supported."

        VARIATION   vRtrIfDHCPUserDb
            ACCESS  not-implemented
            DESCRIPTION
                 "Not supported.

                  Not supported."

        VARIATION   vRtrIfDelayUpTimer
            ACCESS  not-implemented
            DESCRIPTION
                 "Not supported.

                  Not supported."

        VARIATION   vRtrIfEgressFilterId
            DESCRIPTION
                 "Not supported in RVPLS.

                  Not supported in RVPLS."

        VARIATION   vRtrIfInitDelayEnable
            ACCESS  not-implemented
            DESCRIPTION
                 "Not supported.

                  Not supported."

        VARIATION   vRtrIfQosEgrPortRedirectQGrp
            DESCRIPTION
                 "Not supported .

                  Not supported ."

        VARIATION   vRtrIfQosEgrQGrpInstanceId
            DESCRIPTION
                 "Not supported.

                  Not supported. "

        VARIATION   vRtrIfQosIngFpRedirectQGrp
            DESCRIPTION
                 "Not supported.

                  Not supported. "

        VARIATION   vRtrIfQosIngQGrpInstanceId
            DESCRIPTION
                 "Not supported.

                  Not supported. "

        VARIATION   vRtrIfType
            SYNTAX  INTEGER {
                       network              (1),
                       service              (2),
                       serviceIes           (3),
                    -- serviceRtdVpls       (4)
                       serviceVprn          (5),
                    -- serviceIesSubscriber (6)
                    -- serviceIesGroup      (7)
                    -- serviceVprnSubscriber (8)
                    -- serviceVprnGroup     (9)
                    -- serviceIesRedundant  (10)
                    -- serviceVprnRedundant (11)
                       serviceVpls          (12),
                    -- serviceIesCem        (13)
                    -- serviceVprnCem       (14)
                    -- serviceVprnIPsec     (15)
                       serviceVprnIPMirror  (16)
                    }
            DESCRIPTION
                 "The values - 'serviceRtdVpls (4)' (obsoleted) -
                  'serviceIesSubscriber (6)', (routed CO) - 'serviceIesGroup
                  (7)', (routed CO) - 'serviceVprnSubscriber (8)', -
                  'serviceVprnGroup (9)', - 'serviceIesRedundant (10)', -
                  'serviceVprnRedundant (11)', - 'serviceIesCem (13)', -
                  'serviceVprnCem (14)', - 'serviceVprnIPsec (15)' (IPsec
                  Tunneling) are not suppoted on SAS-R 7210 systems.

                  The values - 'serviceRtdVpls (4)' (obsoleted) -
                  'serviceIesSubscriber (6)', (routed CO) - 'serviceIesGroup
                  (7)', (routed CO) - 'serviceVprnSubscriber (8)', -
                  'serviceVprnGroup (9)', - 'serviceIesRedundant (10)', -
                  'serviceVprnRedundant (11)', - 'serviceIesCem (13)', -
                  'serviceVprnCem (14)', - 'serviceVprnIPsec (15)' (IPsec
                  Tunneling) are not suppoted on SAS-R 7210 systems."

        VARIATION   vRtrIgnoreIcmpRedirect
            DESCRIPTION
                 "The default value of vRtrIgnoreIcmpRedirect is changed to
                  'true' from 'false' in release 4.0-R13 and 5.0-R3.

                  The default value of vRtrIgnoreIcmpRedirect is changed to
                  'true' from 'false' in release 4.0-R13 and 5.0-R3."

        VARIATION   vRtrIgnoreNextHopMetric
            ACCESS  not-implemented
            DESCRIPTION
                 "Not supported.

                  Not supported."

        VARIATION   vRtrIllegalLabelThreshold
            ACCESS  not-implemented
            DESCRIPTION
                 "Not supported.

                  Not supported."

        VARIATION   vRtrInetCidrProtocolInstance
            ACCESS  not-implemented
            DESCRIPTION
                 "Not supported.

                  Not supported."

        VARIATION   vRtrInetCidrRouteTunnEndpntInfo
            ACCESS  not-implemented
            DESCRIPTION
                 "Not supported.

                  Not supported."

        VARIATION   vRtrInetStaticRouteCpeAddr
            SYNTAX  InetAddress (SIZE (0|4))
            DESCRIPTION
                 "vRtrInetStaticRouteCpeAddr supports only InetAddressType
                  values 'unknown' and 'ipv4'.

                  vRtrInetStaticRouteCpeAddr supports only InetAddressType
                  values 'unknown' and 'ipv4'."

        VARIATION   vRtrInetStaticRouteCpeAddrType
            SYNTAX  INTEGER {
                       unknown              (0),
                       ipv4                 (1)
                    -- ipv6                 (2)
                    -- ipv4z                (3)
                    -- ipv6z                (4)
                    -- dns                  (16)
                    }
            DESCRIPTION
                 "vRtrInetStaticRouteCpeAddrType supports only InetAddressType
                  values 'unknown' and 'ipv4'.

                  vRtrInetStaticRouteCpeAddrType supports only InetAddressType
                  values 'unknown' and 'ipv4'."

        VARIATION   vRtrInetStaticRouteDisallowIgp
            ACCESS  not-implemented
            DESCRIPTION
                 "Not supported.

                  Not supported."

        VARIATION   vRtrInetStaticRouteIgpShortcut
            ACCESS  not-implemented
            DESCRIPTION
                 "Not supported.

                  Not supported."

        VARIATION   vRtrInetStaticRouteNHTunnelName
            ACCESS  not-implemented
            DESCRIPTION
                 "Not supported.

                  Not supported."

        VARIATION   vRtrInetSvcIpRangeExclusive
            ACCESS  not-implemented
            DESCRIPTION
                 "Not supported.

                  Not supported."

        VARIATION   vRtrInetSvcIpRangeRowStatus
            ACCESS  not-implemented
            DESCRIPTION
                 "Not supported.

                  Not supported."

        VARIATION   vRtrIpCidrRoutePreference
            ACCESS  read-only
            DESCRIPTION
                 "read-only implementation.

                  read-only implementation."

        VARIATION   vRtrManagedActiveRoutes
            ACCESS  not-implemented
            DESCRIPTION
                 "Not supported (No Routed Subscriber Host).

                  Not supported (No Routed Subscriber Host)."

        VARIATION   vRtrManagedRoutes
            ACCESS  not-implemented
            DESCRIPTION
                 "Not supported (No Routed Subscriber Host).

                  Not supported (No Routed Subscriber Host)."

        VARIATION   vRtrMcPathMgmtPlcyName
            ACCESS  not-implemented
            DESCRIPTION
                 "Not supported (no way to join multicast streams).

                  Not supported (no way to join multicast streams).

                  Not supported.

                  Not supported.

                  Not supported.

                  Not supported."

        VARIATION   vRtrMldStatus
            ACCESS  not-implemented
            DESCRIPTION
                 "Not supported (No MLD).

                  Not supported (No MLD).

                  Not supported.

                  Not supported."

        VARIATION   vRtrMsdpStatus
            ACCESS  not-implemented
            DESCRIPTION
                 "Not supported (No MSDP).

                  Not supported (No MSDP)."

        VARIATION   vRtrMulticastRoutes
            ACCESS  not-implemented
            DESCRIPTION
                 "Not supported (No IPM).

                  Not supported (No IPM)."

        VARIATION   vRtrNextVRtrID
            ACCESS  read-only
            DESCRIPTION
                 "read-only implementation.

                  read-only implementation."

        VARIATION   vRtrRIPActiveRoutes
            ACCESS  not-implemented
            DESCRIPTION
                 "Not supported.

                  Not supported."

        VARIATION   vRtrRIPRoutes
            ACCESS  not-implemented
            DESCRIPTION
                 "Not supported.

                  Not supported."

        VARIATION   vRtrRipStatus
            ACCESS  not-implemented
            DESCRIPTION
                 "Not supported.

                  Not supported."

        VARIATION   vRtrRouteThresholdSoakTime
            ACCESS  read-only
            DESCRIPTION
                 "read-only implementation.

                  read-only implementation."

        VARIATION   vRtrSecondaryVrfId
            ACCESS  not-implemented
            DESCRIPTION
                 "Not supported.

                  Not supported."

        VARIATION   vRtrStatActiveRsvpTunnels
            ACCESS  not-implemented
            DESCRIPTION
                 "Not supported.

                  Not supported."

        VARIATION   vRtrStatTotalRsvpTunnels
            ACCESS  not-implemented
            DESCRIPTION
                 "Not supported.

                  Not supported."

        VARIATION   vRtrStaticRouteDisallowIgp
            ACCESS  not-implemented
            DESCRIPTION
                 "Not supported.

                  Not supported."

        VARIATION   vRtrStaticRouteIgpShortcut
            ACCESS  not-implemented
            DESCRIPTION
                 "Not supported.

                  Not supported."

        VARIATION   vRtrStaticRouteNextHopUnnumberedIf
            ACCESS  not-implemented
            DESCRIPTION
                 "Not supported.

                  Not supported."

        VARIATION   vRtrSubMgmtActiveRoutes
            ACCESS  not-implemented
            DESCRIPTION
                 "Not supported (No routed-CO).

                  Not supported (No routed-CO)."

        VARIATION   vRtrSubMgmtRoutes
            ACCESS  not-implemented
            DESCRIPTION
                 "Not supported (No routed-CO).

                  Not supported (No routed-CO)."

        VARIATION   vRtrSvcIpRangeAddress
            ACCESS  not-implemented
            DESCRIPTION
                 "Not supported.

                  Not supported."

        VARIATION   vRtrSvcIpRangeExclusive
            ACCESS  not-implemented
            DESCRIPTION
                 "Not supported.

                  Not supported."

        VARIATION   vRtrSvcIpRangeMask
            ACCESS  not-implemented
            DESCRIPTION
                 "Not supported.

                  Not supported."

        VARIATION   vRtrSvcIpRangeRowStatus
            ACCESS  not-implemented
            DESCRIPTION
                 "Not supported.

                  Not supported."

        VARIATION   vRtrType
            ACCESS  read-only
            DESCRIPTION
                 "read-only implementation.

                  read-only implementation."

        VARIATION   vRtrV6StatActiveRsvpTunnels
            ACCESS  not-implemented
            DESCRIPTION
                 "Not supported.

                  Not supported."

        VARIATION   vRtrV6StatTotalRsvpTunnels
            ACCESS  not-implemented
            DESCRIPTION
                 "Not supported.

                  Not supported."

        VARIATION   vRtrVprnType
            SYNTAX  INTEGER {
                       regular              (1)
                    }
            DESCRIPTION
                 "On 7210 SAS-R platforms only regular is supported for
                  vRtrVprnType.

                  On 7210 SAS-R platforms only regular is supported for
                  vRtrVprnType."

    ::= { tmnxSASAgentV9v0  18 }

--
-- SAS VRTR CAPABILITIES
--
tmnxSASVrtrV9v0                   AGENT-CAPABILITIES
    PRODUCT-RELEASE "Alcatel-Lucent SAS"
    STATUS          current
    DESCRIPTION
         "Implementation of Virtual Router capabilities for Alcatel-Lucent SAS
          systems release 9.0."

    SUPPORTS        TIMETRA-VRTR-MIB
        INCLUDES {
           tmnxDscpAppV6v0Group,
           tmnxVRtrBfdV6v0Group,
           tmnxVRtrDHCPIfLseStatesExceeded,
           tmnxVRtrGlobalV6v0Group,
           tmnxVRtrIfDHCPRelayV6v1Group,
           tmnxVRtrIfDHCPRelayV9v0Group,
           tmnxVRtrIfSubscrAuthV3v0Group,
           tmnxVRtrIfV5v0Group,
           tmnxVRtrIpV7v0Group,
           tmnxVRtrNotificationV7v0Group,
           tmnxVRtrQosQGrplV10v0Group,
           tmnxVRtrV6v1Group,
           tmnxVRtrV7v0Group
        }

        VARIATION   tmnxDot1pAppId
            SYNTAX  INTEGER {
                       arp                  (1),
                       isis                 (2)
                    -- pppoe                (3)
                    }
            DESCRIPTION
                 "tmnxDot1pAppId does not support value 'pppoe (3)' as PPPoE is
                  not available on SAS-R 7210 systems.

                  tmnxDot1pAppId does not support value 'pppoe (3)' as PPPoE is
                  not available on SAS-R 7210 systems."

        VARIATION   tmnxDscpAppId
            SYNTAX  INTEGER {
                       bgp                  (1),
                    -- cflowd               (2)
                       dhcp                 (3),
                       dns                  (4),
                       ftp                  (5),
                       icmp                 (6),
                    -- igmp                 (7)
                    -- l2tp                 (8)
                       ldp                  (9),
                    -- mld                  (10)
                    -- msdp                 (11)
                    -- ndis                 (12)
                       ntp                  (13),
                       ospf                 (14),
                    -- pim                  (15)
                       radius               (16),
                       rip                  (17),
                       rsvp                 (18),
                       snmp                 (19),
                       snmp-notification    (20),
                    -- srrp                 (21)
                       ssh                  (22),
                       syslog               (23),
                       tacplus              (24),
                       telnet               (25),
                       tftp                 (26),
                       traceroute           (27),
                       vrrp                 (28)
                    }
            DESCRIPTION
                 "tmnxDscpAppId does not support TDSCPAppId values of 'srrp',
                  'cflowd', 'igmp', 'mld', 'msdp', 'ndis' and 'pim' as SRRP,
                  CFLOWD, IGMP, MLD, MSDP, IPv6 and PIM are not available on
                  SAS-R 7210 systems.

                  tmnxDscpAppId does not support TDSCPAppId values of 'srrp',
                  'cflowd', 'igmp', 'mld', 'msdp', 'ndis' and 'pim' as SRRP,
                  CFLOWD, IGMP, MLD, MSDP, IPv6 and PIM are not available on
                  SAS-R 7210 systems."

        VARIATION   vRiaInetGwAddress
            ACCESS  not-implemented
            DESCRIPTION
                 "Not supported.

                  Not supported.

                  Not supported.

                  Not supported."

        VARIATION   vRiaInetGwAddressType
            ACCESS  not-implemented
            DESCRIPTION
                 "Not supported.

                  Not supported.

                  Not supported.

                  Not supported."

        VARIATION   vRtrConfederationAS4Byte
            ACCESS  not-implemented
            DESCRIPTION
                 "Not supported.

                  Not supported."

        VARIATION   vRtrDHCP6DropStatLastCleared
            ACCESS  not-implemented
            DESCRIPTION
                 "Not supported.

                  Not supported."

        VARIATION   vRtrDHCP6DropStatPktsDropped
            ACCESS  not-implemented
            DESCRIPTION
                 "Not supported.

                  Not supported."

        VARIATION   vRtrDHCP6MsgStatsDropped
            ACCESS  not-implemented
            DESCRIPTION
                 "Not supported.

                  Not supported."

        VARIATION   vRtrDHCP6MsgStatsLstClrd
            ACCESS  not-implemented
            DESCRIPTION
                 "Not supported.

                  Not supported."

        VARIATION   vRtrDHCP6MsgStatsRcvd
            ACCESS  not-implemented
            DESCRIPTION
                 "Not supported.

                  Not supported."

        VARIATION   vRtrDHCP6MsgStatsSent
            ACCESS  not-implemented
            DESCRIPTION
                 "Not supported.

                  Not supported.

                  Not supported.

                  Not supported."

        VARIATION   vRtrHighRouteThreshold
            ACCESS  not-implemented
            DESCRIPTION
                 "Not supported.

                  Not supported."

        VARIATION   vRtrIPv6HighRouteThreshold
            ACCESS  not-implemented
            DESCRIPTION
                 "Not supported.

                  Not supported."

        VARIATION   vRtrIPv6RouteThresholdSoakTime
            ACCESS  not-implemented
            DESCRIPTION
                 "Not supported.

                  Not supported."

        VARIATION   vRtrIfCflowd
            ACCESS  not-implemented
            DESCRIPTION
                 "Not supported (No CFLOWD).

                  Not supported (No CFLOWD)."

        VARIATION   vRtrIfDHCPAntiSpoofMacAddr
            ACCESS  not-implemented
            DESCRIPTION
                 "Not supported.

                  Not supported."

        VARIATION   vRtrIfDHCPAuthPolicy
            ACCESS  not-implemented
            DESCRIPTION
                 "Not supported.

                  Not supported."

        VARIATION   vRtrIfDHCPFilterId
            ACCESS  not-implemented
            DESCRIPTION
                 "Not supported.

                  Not supported."

        VARIATION   vRtrIfDHCPLayer2Header
            ACCESS  not-implemented
            DESCRIPTION
                 "Not supported.

                  Not supported."

        VARIATION   vRtrIfDHCPLeasePopulate
            DESCRIPTION
                 "The default value of vRtrIfDHCPLeasePopulate is '1', not '0',
                  when the interface running DHCP has vRtrIfType
                  'serviceIesGroup'.

                  The default value of vRtrIfDHCPLeasePopulate is '1', not '0',
                  when the interface running DHCP has vRtrIfType
                  'serviceIesGroup'.

                  Not supported.

                  Not supported."

        VARIATION   vRtrIfDHCPMatchOption82
            ACCESS  not-implemented
            DESCRIPTION
                 "Not supported.

                  Not supported."

        VARIATION   vRtrIfDHCPOperLeasePopulate
            ACCESS  not-implemented
            DESCRIPTION
                 "Not supported.

                  Not supported."

        VARIATION   vRtrIfDHCPProxyAdminState
            ACCESS  not-implemented
            DESCRIPTION
                 "Not supported.

                  Not supported."

        VARIATION   vRtrIfDHCPProxyLTRadiusOverride
            ACCESS  not-implemented
            DESCRIPTION
                 "Not supported.

                  Not supported."

        VARIATION   vRtrIfDHCPProxyLeaseTime
            ACCESS  not-implemented
            DESCRIPTION
                 "Not supported.

                  Not supported."

        VARIATION   vRtrIfDHCPProxyServerAddr
            ACCESS  not-implemented
            DESCRIPTION
                 "Not supported.

                  Not supported."

        VARIATION   vRtrIfDHCPUseArpForReply
            ACCESS  not-implemented
            DESCRIPTION
                 "Not supported.

                  Not supported."

        VARIATION   vRtrIfDHCPUserDb
            ACCESS  not-implemented
            DESCRIPTION
                 "Not supported.

                  Not supported."

        VARIATION   vRtrIfDelayUpTimer
            ACCESS  not-implemented
            DESCRIPTION
                 "Not supported.

                  Not supported."

        VARIATION   vRtrIfEgressFilterId
            DESCRIPTION
                 "Not supported in RVPLS.

                  Not supported in RVPLS."

        VARIATION   vRtrIfInitDelayEnable
            ACCESS  not-implemented
            DESCRIPTION
                 "Not supported.

                  Not supported."

        VARIATION   vRtrIfQosEgrPortRedirectQGrp
            DESCRIPTION
                 "Not supported .

                  Not supported ."

        VARIATION   vRtrIfQosEgrQGrpInstanceId
            DESCRIPTION
                 "Not supported.

                  Not supported. "

        VARIATION   vRtrIfQosIngFpRedirectQGrp
            DESCRIPTION
                 "Not supported.

                  Not supported. "

        VARIATION   vRtrIfQosIngQGrpInstanceId
            DESCRIPTION
                 "Not supported.

                  Not supported. "

        VARIATION   vRtrIfType
            SYNTAX  INTEGER {
                       network              (1),
                       service              (2),
                       serviceIes           (3),
                    -- serviceRtdVpls       (4)
                       serviceVprn          (5),
                    -- serviceIesSubscriber (6)
                    -- serviceIesGroup      (7)
                    -- serviceVprnSubscriber (8)
                    -- serviceVprnGroup     (9)
                    -- serviceIesRedundant  (10)
                    -- serviceVprnRedundant (11)
                       serviceVpls          (12),
                    -- serviceIesCem        (13)
                    -- serviceVprnCem       (14)
                    -- serviceVprnIPsec     (15)
                       serviceVprnIPMirror  (16)
                    }
            DESCRIPTION
                 "The values - 'serviceRtdVpls (4)' (obsoleted) -
                  'serviceIesSubscriber (6)', (routed CO) - 'serviceIesGroup
                  (7)', (routed CO) - 'serviceVprnSubscriber (8)', -
                  'serviceVprnGroup (9)', - 'serviceIesRedundant (10)', -
                  'serviceVprnRedundant (11)', - 'serviceIesCem (13)', -
                  'serviceVprnCem (14)', - 'serviceVprnIPsec (15)' (IPsec
                  Tunneling) are not suppoted on SAS-R 7210 systems.

                  The values - 'serviceRtdVpls (4)' (obsoleted) -
                  'serviceIesSubscriber (6)', (routed CO) - 'serviceIesGroup
                  (7)', (routed CO) - 'serviceVprnSubscriber (8)', -
                  'serviceVprnGroup (9)', - 'serviceIesRedundant (10)', -
                  'serviceVprnRedundant (11)', - 'serviceIesCem (13)', -
                  'serviceVprnCem (14)', - 'serviceVprnIPsec (15)' (IPsec
                  Tunneling) are not suppoted on SAS-R 7210 systems."

        VARIATION   vRtrIgnoreIcmpRedirect
            DESCRIPTION
                 "The default value of vRtrIgnoreIcmpRedirect is changed to
                  'true' from 'false' in release 4.0-R13 and 5.0-R3.

                  The default value of vRtrIgnoreIcmpRedirect is changed to
                  'true' from 'false' in release 4.0-R13 and 5.0-R3."

        VARIATION   vRtrIgnoreNextHopMetric
            ACCESS  not-implemented
            DESCRIPTION
                 "Not supported.

                  Not supported."

        VARIATION   vRtrIllegalLabelThreshold
            ACCESS  not-implemented
            DESCRIPTION
                 "Not supported.

                  Not supported."

        VARIATION   vRtrInetCidrProtocolInstance
            ACCESS  not-implemented
            DESCRIPTION
                 "Not supported.

                  Not supported."

        VARIATION   vRtrInetCidrRouteTunnEndpntInfo
            ACCESS  not-implemented
            DESCRIPTION
                 "Not supported.

                  Not supported."

        VARIATION   vRtrInetStaticRouteCpeAddr
            SYNTAX  InetAddress (SIZE (0|4))
            DESCRIPTION
                 "vRtrInetStaticRouteCpeAddr supports only InetAddressType
                  values 'unknown' and 'ipv4'.

                  vRtrInetStaticRouteCpeAddr supports only InetAddressType
                  values 'unknown' and 'ipv4'."

        VARIATION   vRtrInetStaticRouteCpeAddrType
            SYNTAX  INTEGER {
                       unknown              (0),
                       ipv4                 (1)
                    -- ipv6                 (2)
                    -- ipv4z                (3)
                    -- ipv6z                (4)
                    -- dns                  (16)
                    }
            DESCRIPTION
                 "vRtrInetStaticRouteCpeAddrType supports only InetAddressType
                  values 'unknown' and 'ipv4'.

                  vRtrInetStaticRouteCpeAddrType supports only InetAddressType
                  values 'unknown' and 'ipv4'."

        VARIATION   vRtrInetStaticRouteDisallowIgp
            ACCESS  not-implemented
            DESCRIPTION
                 "Not supported.

                  Not supported."

        VARIATION   vRtrInetStaticRouteIgpShortcut
            ACCESS  not-implemented
            DESCRIPTION
                 "Not supported.

                  Not supported."

        VARIATION   vRtrInetStaticRouteNHTunnelName
            ACCESS  not-implemented
            DESCRIPTION
                 "Not supported.

                  Not supported."

        VARIATION   vRtrInetSvcIpRangeExclusive
            ACCESS  not-implemented
            DESCRIPTION
                 "Not supported.

                  Not supported."

        VARIATION   vRtrInetSvcIpRangeRowStatus
            ACCESS  not-implemented
            DESCRIPTION
                 "Not supported.

                  Not supported."

        VARIATION   vRtrIpCidrRoutePreference
            ACCESS  read-only
            DESCRIPTION
                 "read-only implementation.

                  read-only implementation."

        VARIATION   vRtrManagedActiveRoutes
            ACCESS  not-implemented
            DESCRIPTION
                 "Not supported (No Routed Subscriber Host).

                  Not supported (No Routed Subscriber Host)."

        VARIATION   vRtrManagedRoutes
            ACCESS  not-implemented
            DESCRIPTION
                 "Not supported (No Routed Subscriber Host).

                  Not supported (No Routed Subscriber Host)."

        VARIATION   vRtrMcPathMgmtPlcyName
            ACCESS  not-implemented
            DESCRIPTION
                 "Not supported (no way to join multicast streams).

                  Not supported (no way to join multicast streams).

                  Not supported.

                  Not supported.

                  Not supported.

                  Not supported."

        VARIATION   vRtrMldStatus
            ACCESS  not-implemented
            DESCRIPTION
                 "Not supported (No MLD).

                  Not supported (No MLD).

                  Not supported.

                  Not supported."

        VARIATION   vRtrMsdpStatus
            ACCESS  not-implemented
            DESCRIPTION
                 "Not supported (No MSDP).

                  Not supported (No MSDP)."

        VARIATION   vRtrMulticastRoutes
            ACCESS  not-implemented
            DESCRIPTION
                 "Not supported (No IPM).

                  Not supported (No IPM)."

        VARIATION   vRtrNextVRtrID
            ACCESS  read-only
            DESCRIPTION
                 "read-only implementation.

                  read-only implementation."

        VARIATION   vRtrRIPActiveRoutes
            ACCESS  not-implemented
            DESCRIPTION
                 "Not supported.

                  Not supported."

        VARIATION   vRtrRIPRoutes
            ACCESS  not-implemented
            DESCRIPTION
                 "Not supported.

                  Not supported."

        VARIATION   vRtrRipStatus
            ACCESS  not-implemented
            DESCRIPTION
                 "Not supported.

                  Not supported."

        VARIATION   vRtrRouteThresholdSoakTime
            ACCESS  read-only
            DESCRIPTION
                 "read-only implementation.

                  read-only implementation."

        VARIATION   vRtrSecondaryVrfId
            ACCESS  not-implemented
            DESCRIPTION
                 "Not supported.

                  Not supported."

        VARIATION   vRtrStatActiveRsvpTunnels
            ACCESS  not-implemented
            DESCRIPTION
                 "Not supported.

                  Not supported."

        VARIATION   vRtrStatTotalRsvpTunnels
            ACCESS  not-implemented
            DESCRIPTION
                 "Not supported.

                  Not supported."

        VARIATION   vRtrStaticRouteDisallowIgp
            ACCESS  not-implemented
            DESCRIPTION
                 "Not supported.

                  Not supported."

        VARIATION   vRtrStaticRouteIgpShortcut
            ACCESS  not-implemented
            DESCRIPTION
                 "Not supported.

                  Not supported."

        VARIATION   vRtrStaticRouteNextHopUnnumberedIf
            ACCESS  not-implemented
            DESCRIPTION
                 "Not supported.

                  Not supported."

        VARIATION   vRtrSubMgmtActiveRoutes
            ACCESS  not-implemented
            DESCRIPTION
                 "Not supported (No routed-CO).

                  Not supported (No routed-CO)."

        VARIATION   vRtrSubMgmtRoutes
            ACCESS  not-implemented
            DESCRIPTION
                 "Not supported (No routed-CO).

                  Not supported (No routed-CO)."

        VARIATION   vRtrSvcIpRangeAddress
            ACCESS  not-implemented
            DESCRIPTION
                 "Not supported.

                  Not supported."

        VARIATION   vRtrSvcIpRangeExclusive
            ACCESS  not-implemented
            DESCRIPTION
                 "Not supported.

                  Not supported."

        VARIATION   vRtrSvcIpRangeMask
            ACCESS  not-implemented
            DESCRIPTION
                 "Not supported.

                  Not supported."

        VARIATION   vRtrSvcIpRangeRowStatus
            ACCESS  not-implemented
            DESCRIPTION
                 "Not supported.

                  Not supported."

        VARIATION   vRtrType
            ACCESS  read-only
            DESCRIPTION
                 "read-only implementation.

                  read-only implementation."

        VARIATION   vRtrV6StatActiveRsvpTunnels
            ACCESS  not-implemented
            DESCRIPTION
                 "Not supported.

                  Not supported."

        VARIATION   vRtrV6StatTotalRsvpTunnels
            ACCESS  not-implemented
            DESCRIPTION
                 "Not supported.

                  Not supported."

        VARIATION   vRtrVprnType
            SYNTAX  INTEGER {
                       regular              (1)
                    }
            DESCRIPTION
                 "On 7210 SAS-R platforms only regular is supported for
                  vRtrVprnType.

                  On 7210 SAS-R platforms only regular is supported for
                  vRtrVprnType."

    ::= { tmnxSASAgentV9v0  18 }

END
