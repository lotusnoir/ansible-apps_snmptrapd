TIMETRA-WLAN-GW-MIB DEFINITIONS ::= BEGIN

IMPORTS
    Unsigned32, Gauge32, Counter32, Counter64,
    Integer32,
    MODULE-IDENTITY,
    OBJECT-TYPE,
    NOTIFICATION-TYPE
                                                                FROM SNMPv2-SMI


    RowStatus, TEXTUAL-CONVENTION, 
    TimeStamp, DateAndTime, TruthValue,
    DisplayString,
    MacAddress
                                                                 FROM SNMPv2-TC


    OBJECT-GROUP, MODULE-COMPLIANCE,
    NOTIFICATION-GROUP
                                                               FROM SNMPv2-CONF

    InterfaceIndex                                                  FROM IF-MIB
    
    InetAddressType, InetAddress, InetAddressIPv6,
    InetAddressPrefixLength,
    InetPortNumber
                                                          FROM INET-ADDRESS-MIB
                                                         
    MplsLabel                                                 FROM MPLS-LSR-MIB
    
    timetraSRMIBModules, tmnxSRObjs, tmnxSRConfs, 
    tmnxSRNotifyPrefix
                                                        FROM TIMETRA-GLOBAL-MIB

    TItemDescription, TNamedItem, TNamedItemOrEmpty,  
    TmnxVRtrID, TmnxVRtrIDOrZero, TmnxServId,
    TmnxAdminState, TmnxOperState, TmnxEnabledDisabled,
    TPolicyID, TPortSchedulerPIR, TmnxPortID, 
    TmnxEncapVal,
    QTagFullRange, QTagFullRangeOrNone,
    SvcISID,
    TmnxMacSpecification,
    TmnxActionType,
    TmnxHttpRedirectUrl, TIpProtocol, TOperator,
    TAdaptationRule, TPIRRate, TCIRRate,
    TmnxBsxIsaAaGroupIndexOrZero,
    TmnxWlanGwIsaGrpIdOrZero, TmnxWlanGwIsaGrpId
                                                            FROM TIMETRA-TC-MIB

    TmnxMobProfIpTtl,
    TmnxMobMccOrEmpty, TmnxMobMncOrEmpty,
    TmnxMobApn, TmnxMobApnOrZero, TmnxMobApnDomainName, 
    TmnxMobImsiStr,
    TmnxMobService,
    TmnxMobProfMbrRate, TmnxMobProfGbrRate, TmnxMobArp, TmnxMobArpValue,
    TmnxMobQci, TmnxMobQciValueOrZero,
    TmnxMobBearerId, TmnxMobPathMgmtState
                                                         FROM TIMETRA-TC-MG-MIB

    tmnxChassisIndex, tmnxCardSlotNum,
    TmnxChassisIndexOrZero, TmnxSlotNumOrZero
                                                       FROM TIMETRA-CHASSIS-MIB
    
    vRtrID                                          
                                                          FROM TIMETRA-VRTR-MIB
 
    svcId, iesIfIndex,
    svcTlsInfoEntry
                                                          FROM TIMETRA-SERV-MIB

    sapPortId, sapEncapValue                               
                                                           FROM TIMETRA-SAP-MIB
    
    TmnxMobProfMsgReTxTimeout,
    TmnxMobProfMsgReTxRetryCount,
    TmnxMobProfKeepAliveTimeout,
    TmnxMobProfKeepAliveRetryCount,
    TmnxMobProfKeepAliveResponse,
    TmnxMobProfKeepAliveInterval
                                                FROM TIMETRA-MOBILE-PROFILE-MIB                                                          
    TIPFilterID
                                               FROM TIMETRA-FILTER-MIB                                          
    ;
timetraWlanGwMIBModule    MODULE-IDENTITY
    LAST-UPDATED    "201501010000Z"
    ORGANIZATION    "Nokia"
    CONTACT-INFO
    "Nokia 7xxx Support
    Web: http://www.nokia.com"
    DESCRIPTION
    "This document is the SNMP MIB module to manage and provision
    the Wireless Local Access Network Gateway function
    for the Nokia 7xxx device.

    Copyright 2011-2015 Nokia. All rights reserved.
    Reproduction of this document is authorized on the condition that
    the foregoing copyright notice is included.

    This SNMP MIB module (Specification) embodies Nokia's
    proprietary intellectual property. Nokia retains all title and
    ownership in the Specification, including any revisions.

    Nokia grants all interested parties a non-exclusive
    license to use and distribute an unmodified copy of this
    Specification in connection with management of Nokia products,
    and without fee, provided this copyright notice and license appear
    on all copies.

    This Specification is supplied 'as is', and Nokia
    makes no warranty, either express or implied, as to the use,
    operation, condition, or performance of the Specification."

--
--  Revision History
--
    REVISION        "201501010000Z"
    DESCRIPTION     "Rev 13.0                 1 Jan 2015 12:00
                     13.0 release of the TIMETRA-WLAN-GW-MIB."

    REVISION        "201401010000Z"
    DESCRIPTION     "Rev 12.0                 1 Jan 2014 12:00
                     12.0 release of the TIMETRA-WLAN-GW-MIB."

    REVISION        "201202281200Z"
    DESCRIPTION     "Rev 10.0                28 Feb 2012 12:00
                     10.0 release of the TIMETRA-WLAN-GW-MIB."

    ::= { timetraSRMIBModules 81 }

-- ----------------------------------------------------------------------------
--  Nokia 7xxx series WLAN Gateway MIB structure
-- ----------------------------------------------------------------------------
tmnxWlanGw                     OBJECT IDENTIFIER ::= { tmnxSRObjs 81 }
    tmnxWlanGwObjs             OBJECT IDENTIFIER ::= { tmnxWlanGw 1 }
    tmnxWlanGwNotificationObjs OBJECT IDENTIFIER ::= { tmnxWlanGw 2 }

tmnxWlanGwConformance          OBJECT IDENTIFIER ::= { tmnxSRConfs 81 }
    tmnxWlanGwCompliances      OBJECT IDENTIFIER ::= { tmnxWlanGwConformance 1 }
    tmnxWlanGwGroups           OBJECT IDENTIFIER ::= { tmnxWlanGwConformance 2 }

tmnxWlanGwNotifyPrefix         OBJECT IDENTIFIER ::= { tmnxSRNotifyPrefix 81 }
    tmnxWlanGwNotifications    OBJECT IDENTIFIER ::= { tmnxWlanGwNotifyPrefix 0 }

--
-- Subtrees
--
tmnxWlanGwIsaObjs              OBJECT IDENTIFIER ::= { tmnxWlanGwObjs 1 }
tmnxWlanGwSoftGreObjs          OBJECT IDENTIFIER ::= { tmnxWlanGwObjs 2 }
tmnxWlanGwMgwObjs          OBJECT IDENTIFIER ::= { tmnxWlanGwObjs 6 }
tmnxWlanGwSysCfgObjs           OBJECT IDENTIFIER ::= { tmnxWlanGwObjs 7 }
tmnxWlanGwDsmSubObjs            OBJECT IDENTIFIER ::= { tmnxWlanGwObjs 9 }
tmnxWlanGwGtpIsaObjs            OBJECT IDENTIFIER ::= { tmnxWlanGwObjs 10 }
tmnxWlanGwUeObjs                OBJECT IDENTIFIER ::= { tmnxWlanGwObjs 11 }
tmnxWlanGwVlanSubObjs           OBJECT IDENTIFIER ::= { tmnxWlanGwObjs 13 }

-- ----------------------------------------------------------------------------
--  Textual Conventions
-- ----------------------------------------------------------------------------
TmnxWlanGwBurstSize ::= TEXTUAL-CONVENTION
    STATUS  current
    DESCRIPTION
        "The amount of burst capacity (in kbytes) assigned to a policer."
    SYNTAX Integer32 (0..131071)
    
TmnxWlanGwIsaIomOperState ::= TEXTUAL-CONVENTION
    STATUS  current
    DESCRIPTION         
        "TmnxWlanGwIsaIomOperState is an enumerated integer 
         that indicates the operational state of a WLAN Gateway ISA IOM 
         within a WLAN Gateway ISA group."
    SYNTAX INTEGER {
               unavail (0),
               primary (1),
               backup  (2),
               busy    (3)
           }

TmnxWlanGwMgwInterfaceType ::= TEXTUAL-CONVENTION
    STATUS  current
    DESCRIPTION         
        "TmnxWlanGwMgwInterfaceType is an enumerated integer 
         that identifies the interface type of the connection
         between WLAN Gateway and Mobile Gateway.
         
         The possible values are:
         'gn' for the Gn interface,
         's2a' for the S2a interface,
         's2b' for the S2b interface."
    SYNTAX      INTEGER {
                    gn                               (1),
                    s2a                              (2),
                    s2b                              (3) 
                }

TmnxWlanGwDsmFilterAction ::= TEXTUAL-CONVENTION
    STATUS  current
    DESCRIPTION         
        "TmnxWlanGwDsmFilterAction is an enumerated integer 
         that indicates the action to take for packets
         matching distributed-sub-mgmt filter criteria.
 
         - drop        : packets matching the filter entry are dropped.
         - forward     : packets matching the filter entry are forwarded."
    SYNTAX INTEGER {
               drop    (1),
               forward (2)
           }

TmnxWlanGwDsmFilterActionOrNone ::= TEXTUAL-CONVENTION
    STATUS  current
    DESCRIPTION         
        "TmnxWlanGwDsmFilterActionOrNone is an enumerated integer 
         that extends TmnxWlanGwDsmFilterAction with the value 'none'
         that specifies that the filter entry is inactive."
    SYNTAX INTEGER {
               none    (0),
               drop    (1),
               forward (2)
           }

TmnxWlanGwQoSOperState ::= TEXTUAL-CONVENTION
    STATUS  current
    DESCRIPTION         
        "TmnxWlanGwQoSOperState is an enumerated integer 
         that indicates the operational state of a WLAN Gateway
         User Equipment (UE)."
    SYNTAX      INTEGER {
                adminDown (0),
                active (1),
                pending (2),
                problem (3)
                }

TmnxWlanGwGtpSeIdentifier ::= TEXTUAL-CONVENTION
    STATUS  current
    DESCRIPTION
        "The distributed GTP session identifier."
    SYNTAX OCTET STRING (SIZE (8))
    


TmnxWlanGwUeEncapsulation ::= TEXTUAL-CONVENTION
    STATUS  current
    DESCRIPTION         
        "TmnxWlanGwUeEncapsulation is an enumerated integer 
         that indicates the type of encapsulation of
         User Equipment traffic.
         
         The meaning of the values is
         'gre' : Soft GRE
         'l2tp': Soft L2TPv3
         'vlan': IEEE 802.1Q or IEEE 802.1ad."
    SYNTAX INTEGER {
                   notSpecified (0),
                   gre (1),
                   l2tp (2),
                   vlan (3)
           }
TmnxWlanGwUeIdentifier ::= TEXTUAL-CONVENTION
    STATUS  current
    DESCRIPTION
        "The User Equipment identifier."
    SYNTAX OCTET STRING (SIZE (8))
    
TmnxWlanGwChargingCharBits ::= TEXTUAL-CONVENTION
    STATUS  current
    DESCRIPTION         
        "TmnxWlanGwChargingCharBits is a BITS construct 
         that specifies Charging Characteristics bits.
         
         The meaning of the bits is opaque to this system."
    SYNTAX      BITS {
                    bit0  (0),
                    bit1  (1),
                    bit2  (2),
                    bit3  (3),
                    bit4  (4),
                    bit5  (5),
                    bit6  (6),
                    bit7  (7),
                    bit8  (8),
                    bit9  (9),
                    bit10 (10),
                    bit11 (11),
                    bit12 (12),
                    bit13 (13),
                    bit14 (14),
                    bit15 (15)
                }

TmnxWlanGwSubIfIpsAddrFamily ::= TEXTUAL-CONVENTION
    STATUS  current
    DESCRIPTION         
        "TmnxWlanGwSubIfIpsAddrFamily is an enumerated integer 
         that indicates the address family of the pool"
    SYNTAX INTEGER {
                   dhcpv6 (0),
                   slaac (1)
           }
           
 TmnxWlanGwVlanIdleTimeoutAction ::= TEXTUAL-CONVENTION
    STATUS  current
    DESCRIPTION         
        "TmnxWlanGwVlanIdleTimeoutAction is an enumerated integer 
         that indicates the action to be performed when the
         idle-timeout timer goes off."
    SYNTAX INTEGER {
                   remove (0),
                   shcv (1)
           }
           
-- ----------------------------------------------------------------------------
--      The "WLAN Gateway ISA" Group
-- ----------------------------------------------------------------------------

--
--      The WLAN Gateway ISA Group Table
--

tmnxWlanGwGrpTable   OBJECT-TYPE
    SYNTAX      SEQUENCE OF TmnxWlanGwGrpEntry
    MAX-ACCESS  not-accessible
    STATUS      current
    DESCRIPTION
       "The tmnxWlanGwGrpTable contains objects to configure 
        WLAN Gateway Integrated Service Adaptor (ISA) Groups.
        
        A WLAN Gateway ISA group is used to represent multiple hardware 
        adaptors as a single entity, allowing for warm redundancy between 
        multiple WLAN Gateway ISA's."
    ::= { tmnxWlanGwIsaObjs 1 }

tmnxWlanGwGrpEntry   OBJECT-TYPE
        SYNTAX          TmnxWlanGwGrpEntry
        MAX-ACCESS      not-accessible
        STATUS          current
        DESCRIPTION
       "Each conceptual row represents a WLAN Gateway
        Integrated Service Adaptor Group.

        Entries in this table can be created or deleted via SNMP operations."
    INDEX { tmnxWlanGwGrpId }
    ::= { tmnxWlanGwGrpTable 1 }

TmnxWlanGwGrpEntry ::= 
    SEQUENCE {
        tmnxWlanGwGrpId                  TmnxWlanGwIsaGrpId,
        tmnxWlanGwGrpRowStatus           RowStatus,
        tmnxWlanGwGrpLastMgmtChange      TimeStamp,
        tmnxWlanGwGrpDescription         TItemDescription,
        tmnxWlanGwGrpAdminState          TmnxAdminState,
        tmnxWlanGwGrpActiveIomLimit      Unsigned32,
        tmnxWlanGwGrpPortPlcy            TNamedItemOrEmpty,
        tmnxWlanGwGrpTunnelPortPlcy      TNamedItemOrEmpty,
        tmnxWlanGwGrpIsaAaGroup          TmnxBsxIsaAaGroupIndexOrZero,
        tmnxWlanGwGrpOperState           TmnxOperState,
        tmnxWlanGwGrpDegraded            TruthValue
    }
        
tmnxWlanGwGrpId OBJECT-TYPE
    SYNTAX      TmnxWlanGwIsaGrpId
    MAX-ACCESS  not-accessible
    STATUS      current
    DESCRIPTION
       "The value of the object tmnxWlanGwGrpId specifies the identifier of
        the WLAN Gateway Integrated Service Adaptor group."
    ::= { tmnxWlanGwGrpEntry 1 }

tmnxWlanGwGrpRowStatus OBJECT-TYPE
    SYNTAX      RowStatus
    MAX-ACCESS  read-create
    STATUS      current
    DESCRIPTION
       "The value of tmnxWlanGwGrpRowStatus specifies the row status of
        this row."
    ::= { tmnxWlanGwGrpEntry 2 }

tmnxWlanGwGrpLastMgmtChange OBJECT-TYPE
    SYNTAX      TimeStamp
    MAX-ACCESS  read-only
    STATUS      current
    DESCRIPTION
        "The value of tmnxWlanGwGrpLastMgmtChange indicates the sysUpTime at
         the time of the most recent management-initiated change to this
         table row."
    ::= { tmnxWlanGwGrpEntry 3 }

tmnxWlanGwGrpDescription OBJECT-TYPE
    SYNTAX      TItemDescription
    MAX-ACCESS  read-create
    STATUS      current
    DESCRIPTION
       "The value of tmnxWlanGwGrpDescription specifies the
        description of this WLAN Gateway ISA group."
    DEFVAL { "" }
    ::= { tmnxWlanGwGrpEntry 4 }

tmnxWlanGwGrpAdminState OBJECT-TYPE
    SYNTAX      TmnxAdminState
    MAX-ACCESS  read-create
    STATUS      current
    DESCRIPTION
       "The value of tmnxWlanGwGrpAdminState specifies the
        administrative state of this WLAN Gateway ISA group."
    DEFVAL { outOfService }
    ::= { tmnxWlanGwGrpEntry 5 }

tmnxWlanGwGrpActiveIomLimit OBJECT-TYPE
    SYNTAX      Unsigned32 (0..7)
    MAX-ACCESS  read-create
    STATUS      current
    DESCRIPTION
       "The value of tmnxWlanGwGrpActiveIomLimit specifies the
        number of IOM's in this WLAN Gateway ISA group that are intended for 
        active use.

        A non-zero value must be specified before setting the value of 
        tmnxWlanGwGrpAdminState to 'inService'."
    DEFVAL { 0 }
    ::= { tmnxWlanGwGrpEntry 6 }

tmnxWlanGwGrpPortPlcy OBJECT-TYPE
    SYNTAX      TNamedItemOrEmpty
    MAX-ACCESS  read-create
    STATUS      current
    DESCRIPTION
       "The value of tmnxWlanGwGrpPortPlcy specifies the
        port policy of this WLAN Gateway ISA group.
        
        This object refers to a row in 
        the TIMETRA-PORT-MIB::tmnxPortPlcyTable.
        
        If a port policy is associated with a WLAN Gateway ISA group,
        ports created for this group can take applicable configuration
        from that port policy.
        
        This port policy is applicable to those ports 
        that take part in the per-UE QoS processing."
    DEFVAL { "" }
    ::= { tmnxWlanGwGrpEntry 7 }

tmnxWlanGwGrpTunnelPortPlcy OBJECT-TYPE
    SYNTAX      TNamedItemOrEmpty
    MAX-ACCESS  read-create
    STATUS      current
    DESCRIPTION
       "The value of tmnxWlanGwGrpTunnelPortPlcy specifies a
        port policy of this WLAN Gateway ISA group.
        
        This object refers to a row in 
        the TIMETRA-PORT-MIB::tmnxPortPlcyTable.
        
        If a port policy is associated with a WLAN Gateway ISA group,
        ports created for this group can take applicable configuration
        from that port policy.
        
        This port policy is applicable to those ports 
        that take part in the per-tunnel QoS processing."
    DEFVAL { "" }
    ::= { tmnxWlanGwGrpEntry 8 }


tmnxWlanGwGrpIsaAaGroup OBJECT-TYPE
    SYNTAX      TmnxBsxIsaAaGroupIndexOrZero
    MAX-ACCESS  read-create
    STATUS      current
    DESCRIPTION
       "The value of tmnxWlanGwGrpIsaAaGroup specifies
        an Application Assurance ISA group associated with
        this WLAN Gateway ISA group.
        
        This object refers to a row in 
        the TIMETRA-BSX-NG-MIB::tmnxBsxIsaAaGrpTable."
    DEFVAL { 0 }
    ::= { tmnxWlanGwGrpEntry 9 }

tmnxWlanGwGrpOperState  OBJECT-TYPE
    SYNTAX      TmnxOperState 
    MAX-ACCESS  read-only
    STATUS      current
    DESCRIPTION
        "The value of tmnxWlanGwGrpOperState indicates the operational 
         status of this WLAN Gateway ISA group."
    ::= { tmnxWlanGwGrpEntry 50 }

tmnxWlanGwGrpDegraded  OBJECT-TYPE
    SYNTAX      TruthValue 
    MAX-ACCESS  read-only
    STATUS      current
    DESCRIPTION
        "The value of tmnxWlanGwGrpDegraded indicates 
         if this WLAN Gateway ISA group is degraded,
         while operationally still in service.
         
         The value of this object is only relevant while the value
         of the object tmnxWlanGwGrpOperState is equal to 'inService'."
    ::= { tmnxWlanGwGrpEntry 51 }


--
--      The WLAN Gateway ISA Group IOM Table
--

tmnxWlanGwIomTable   OBJECT-TYPE
    SYNTAX      SEQUENCE OF TmnxWlanGwIomEntry
    MAX-ACCESS  not-accessible
    STATUS      current
    DESCRIPTION
       "The tmnxWlanGwIomTable contains objects to configure 
        the WLAN Gateway ISA Group Input/Output Modules (IOM)."
    ::= { tmnxWlanGwIsaObjs 2 }

tmnxWlanGwIomEntry   OBJECT-TYPE
    SYNTAX      TmnxWlanGwIomEntry
    MAX-ACCESS  not-accessible
    STATUS      current
    DESCRIPTION
       "Each conceptual row represents an WLAN Gateway 
        ISA Input/Output Module (IOM) of a WLAN Gateway ISA Group.

        Entries in this table can be created or deleted via SNMP operations."
    INDEX { tmnxWlanGwGrpId ,
            tmnxChassisIndex, 
            tmnxCardSlotNum }
    ::= { tmnxWlanGwIomTable 1 }

TmnxWlanGwIomEntry ::= 
    SEQUENCE {
        tmnxWlanGwIomRowStatus           RowStatus,
        tmnxWlanGwIomLastMgmtChange      TimeStamp,
        tmnxWlanGwIomOperState           TmnxWlanGwIsaIomOperState
    }

tmnxWlanGwIomRowStatus OBJECT-TYPE
    SYNTAX      RowStatus
    MAX-ACCESS  read-create
    STATUS      current
    DESCRIPTION
       "The value of tmnxWlanGwIomRowStatus specifies the row status of
        this row."
    ::= { tmnxWlanGwIomEntry 1 }

tmnxWlanGwIomLastMgmtChange OBJECT-TYPE
    SYNTAX      TimeStamp
    MAX-ACCESS  read-only
    STATUS      current
    DESCRIPTION
        "The value of tmnxWlanGwIomLastMgmtChange indicates the sysUpTime at
         the time of the most recent management-initiated change to this
         table row."
    ::= { tmnxWlanGwIomEntry 2 }

tmnxWlanGwIomOperState OBJECT-TYPE
    SYNTAX      TmnxWlanGwIsaIomOperState
    MAX-ACCESS  read-only
    STATUS      current
    DESCRIPTION
       "The value of tmnxWlanGwIomOperState indicates the
        operational state of this WLAN Gateway ISA IOM."
    ::= { tmnxWlanGwIomEntry 3 }
    
--
--      The WLAN Gateway group ISA Member Table
--


tmnxWlanGwIsaMemberTable   OBJECT-TYPE
    SYNTAX      SEQUENCE OF TmnxWlanGwIsaMemberEntry
    MAX-ACCESS  not-accessible
    STATUS      current
    DESCRIPTION
       "The tmnxWlanGwIsaMemberTable contains status and statistics information 
        about the members of a WLAN Gateway ISA Group.
        
        A member of a WLAN Gateway ISA Group can be mapped to a physical ISA MDA."
    ::= { tmnxWlanGwIsaObjs 3 }

tmnxWlanGwIsaMemberEntry   OBJECT-TYPE
    SYNTAX      TmnxWlanGwIsaMemberEntry
    MAX-ACCESS  not-accessible
    STATUS      current
    DESCRIPTION
       "Each conceptual row contains WLAN Gateway-specific
        status and basic statistics information
        about a member of a WLAN Gateway ISA Group.

        Entries in this table are created and removed automatically by the 
        system."
    INDEX { tmnxWlanGwGrpId,
            tmnxWlanGwIsaMemberId }
    ::= { tmnxWlanGwIsaMemberTable 1 }

TmnxWlanGwIsaMemberEntry ::= 
    SEQUENCE {
        tmnxWlanGwIsaMemberId            Unsigned32,
        tmnxWlanGwIsaMemberChassisIndex  TmnxChassisIndexOrZero,
        tmnxWlanGwIsaMemberCardSlotNum   TmnxSlotNumOrZero,
        tmnxWlanGwIsaMemberSlotNum       Unsigned32,
        tmnxWlanGwIsaMemberNumSoftGreTu  Gauge32,
        tmnxWlanGwIsaMemberNumUe         Gauge32,
        tmnxWlanGwIsaMemberEegMemberAct  Gauge32,
        tmnxWlanGwIsaMemberEegMemberPend Gauge32,
        tmnxWlanGwIsaMemberTuQosProblem  Gauge32
    }
        
tmnxWlanGwIsaMemberId OBJECT-TYPE
    SYNTAX      Unsigned32
    MAX-ACCESS  not-accessible
    STATUS      current
    DESCRIPTION
       "The value of the object tmnxWlanGwIsaMemberId indicates the identifier of
        this WLAN Gateway ISA Group member."
    ::= { tmnxWlanGwIsaMemberEntry 1 }

tmnxWlanGwIsaMemberChassisIndex OBJECT-TYPE
    SYNTAX      TmnxChassisIndexOrZero
    MAX-ACCESS  read-only
    STATUS      current
    DESCRIPTION
       "The value of tmnxWlanGwIsaMemberChassisIndex indicates the
        chassis of the MDA associated with this member.
        
        The value zero means that there is currently no MDA associated with this
        member."
    ::= { tmnxWlanGwIsaMemberEntry 2 }

tmnxWlanGwIsaMemberCardSlotNum OBJECT-TYPE
    SYNTAX      TmnxSlotNumOrZero
    MAX-ACCESS  read-only
    STATUS      current
    DESCRIPTION
       "The value of tmnxWlanGwIsaMemberCardSlotNum indicates the
        IOM slot of the MDA associated with this member.
        
        The value zero means that there is currently no MDA associated with this
        member."
    ::= { tmnxWlanGwIsaMemberEntry 3 }

tmnxWlanGwIsaMemberSlotNum OBJECT-TYPE
    SYNTAX      Unsigned32
    MAX-ACCESS  read-only
    STATUS      current
    DESCRIPTION
       "The value of tmnxWlanGwIsaMemberSlotNum indicates the
        MDA slot within the IOM of the MDA associated with this member.
        
        The value zero means that there is currently no MDA associated with this
        member."
    ::= { tmnxWlanGwIsaMemberEntry 4 }

tmnxWlanGwIsaMemberNumSoftGreTu OBJECT-TYPE
    SYNTAX      Gauge32
    MAX-ACCESS  read-only
    STATUS      current
    DESCRIPTION
       "The value of tmnxWlanGwIsaMemberNumSoftGreTu indicates the
        number of tunnels processed by the MDA associated with this member."
    ::= { tmnxWlanGwIsaMemberEntry 5 }

tmnxWlanGwIsaMemberNumUe OBJECT-TYPE
    SYNTAX      Gauge32
    MAX-ACCESS  read-only
    STATUS      current
    DESCRIPTION
       "The value of tmnxWlanGwIsaMemberNumUe indicates the
        number of UE processed by the MDA 
        associated with this member."
    ::= { tmnxWlanGwIsaMemberEntry 6 }

tmnxWlanGwIsaMemberEegMemberAct OBJECT-TYPE
    SYNTAX      Gauge32
    MAX-ACCESS  read-only
    STATUS      current
    DESCRIPTION
       "The value of tmnxWlanGwIsaMemberEegMemberAct indicates the
        number of activated Egress Encapsulation Group members 
        associated with this ISA group member."
    ::= { tmnxWlanGwIsaMemberEntry 7 }

tmnxWlanGwIsaMemberEegMemberPend OBJECT-TYPE
    SYNTAX      Gauge32
    MAX-ACCESS  read-only
    STATUS      current
    DESCRIPTION
       "The value of tmnxWlanGwIsaMemberEegMemberPend indicates the
        number of pending Egress Encapsulation Group members 
        associated with this ISA group member."
    ::= { tmnxWlanGwIsaMemberEntry 8 }

tmnxWlanGwIsaMemberTuQosProblem OBJECT-TYPE
    SYNTAX      Gauge32
    MAX-ACCESS  read-only
    STATUS      current
    DESCRIPTION
       "The value of tmnxWlanGwIsaMemberTuQosProblem indicates the
        number of tunnel Qos infrastructure configuration instances 
        on the MDA associated with this ISA group member 
        that have a resource issue."
    ::= { tmnxWlanGwIsaMemberEntry 9 }

--
--      The WLAN Gateway ISA Group Member Statistics Table
--


tmnxWlanGwIsaMemberStatsTable   OBJECT-TYPE
    SYNTAX      SEQUENCE OF TmnxWlanGwIsaMemberStatsEntry
    MAX-ACCESS  not-accessible
    STATUS      current
    DESCRIPTION
       "The tmnxWlanGwIsaMemberStatsTable contains detailed statistics information 
        about the members of a WLAN Gateway ISA ISA Group."
    ::= { tmnxWlanGwIsaObjs 4 }

tmnxWlanGwIsaMemberStatsEntry   OBJECT-TYPE
    SYNTAX      TmnxWlanGwIsaMemberStatsEntry
    MAX-ACCESS  not-accessible
    STATUS      current
    DESCRIPTION
       "Each conceptual row contains detailed statistics information
        about a member of a WLAN Gateway ISA Group.

        Entries in this table are created and removed automatically by the 
        system."
    INDEX { tmnxWlanGwGrpId,
            tmnxWlanGwIsaMemberId,
            tmnxWlanGwIsaMemberStatsType }
    ::= { tmnxWlanGwIsaMemberStatsTable 1 }

TmnxWlanGwIsaMemberStatsEntry ::= 
    SEQUENCE {
        tmnxWlanGwIsaMemberStatsType        Unsigned32,
        tmnxWlanGwIsaMemberStatsName        DisplayString,
        tmnxWlanGwIsaMemberStatsVal         Counter32,
        tmnxWlanGwIsaMemberStatsValHw       Counter32,
        tmnxWlanGwIsaMemberStatsValue       Counter64
    }

tmnxWlanGwIsaMemberStatsType OBJECT-TYPE
    SYNTAX      Unsigned32 (0..199)
    MAX-ACCESS  not-accessible
    STATUS      current
    DESCRIPTION
        "The value of tmnxWlanGwIsaMemberStatsType indicates
         the type of WLAN Gateway statistics contained in this conceptual row."
    ::= { tmnxWlanGwIsaMemberStatsEntry 1 }

tmnxWlanGwIsaMemberStatsName OBJECT-TYPE
    SYNTAX      DisplayString (SIZE (1..64))
    MAX-ACCESS  read-only
    STATUS      current
    DESCRIPTION 
       "The value of the object tmnxWlanGwIsaMemberStatsName indicates
        the human-readable identifier of the statistics 
        contained in this conceptual row."
    ::= { tmnxWlanGwIsaMemberStatsEntry 2 }

tmnxWlanGwIsaMemberStatsVal OBJECT-TYPE
    SYNTAX      Counter32
    MAX-ACCESS  read-only
    STATUS      current
    DESCRIPTION 
       "The value of the object tmnxWlanGwIsaMemberStatsVal indicates
        the lower 32-bits word of the statistics 
        contained in this conceptual row."
    ::= { tmnxWlanGwIsaMemberStatsEntry 3 }

tmnxWlanGwIsaMemberStatsValHw OBJECT-TYPE
    SYNTAX      Counter32
    MAX-ACCESS  read-only
    STATUS      current
    DESCRIPTION 
       "The value of the object tmnxWlanGwIsaMemberStatsValHw indicates
        the higher 32-bits word of the statistics 
        contained in this conceptual row."
    ::= { tmnxWlanGwIsaMemberStatsEntry 4 }

tmnxWlanGwIsaMemberStatsValue OBJECT-TYPE
    SYNTAX      Counter64
    MAX-ACCESS  read-only
    STATUS      current
    DESCRIPTION 
       "The value of the object tmnxWlanGwIsaMemberStatsValue indicates
        the value of the statistics contained in this conceptual row."
    ::= { tmnxWlanGwIsaMemberStatsEntry 5 }

-- --------------------------------------------------------
--      Soft GRE 
-- --------------------------------------------------------
--
--      Soft GRE Group Interface Table
--
--      Sparse augment of the TIMETRA-SERV-MIB::iesIfTable

tmnxWlanGwSoftGreIfTable   OBJECT-TYPE
    SYNTAX      SEQUENCE OF TmnxWlanGwSoftGreIfEntry
    MAX-ACCESS  not-accessible
    STATUS      current
    DESCRIPTION
       "The tmnxWlanGwSoftGreIfTable contains objects to configure 
        WLAN Gateway Group-Interfaces.
        
        Entries in this table are created and destroyed by the system.
        
        The system automatically creates an entry in this table for each
        entry in the TIMETRA-SERV-MIB::iesIfTable where the value of iesIfType
        is equal to 'group' and the value of iesIfGroupInterfaceType is equal to 'softGre'. 
        
        Deletion of such a row in the iesIfTable results in the same fate
        for the corresponding row in this table."
    ::= { tmnxWlanGwSoftGreObjs 1 }

tmnxWlanGwSoftGreIfEntry OBJECT-TYPE
    SYNTAX      TmnxWlanGwSoftGreIfEntry
    MAX-ACCESS  not-accessible
    STATUS      current
    DESCRIPTION
        "Each conceptual row contains Soft GRE specific information of a specific group interface."
    INDEX { svcId, iesIfIndex }
    ::= { tmnxWlanGwSoftGreIfTable 1 }

TmnxWlanGwSoftGreIfEntry ::=
    SEQUENCE {
        tmnxWlanGwSoftGreIfLastCh        TimeStamp,
        tmnxWlanGwSoftGreIfAdminState    TmnxAdminState,
        tmnxWlanGwSoftGreIfRouter        TmnxVRtrIDOrZero,
        tmnxWlanGwSoftGreIfGwAddrType    InetAddressType,
        tmnxWlanGwSoftGreIfGwAddr        InetAddress,
        tmnxWlanGwSoftGreIfGrpId         TmnxWlanGwIsaGrpIdOrZero,
        tmnxWlanGwSoftGreIfShapingType   INTEGER,
        tmnxWlanGwSoftGreIfShapeMultiUe  TruthValue,
        tmnxWlanGwSoftGreIfEQosPlcy      TPolicyID,
        tmnxWlanGwSoftGreIfESchedPlcy    TNamedItemOrEmpty,
        tmnxWlanGwSoftGreIfEAggRateLimit TPortSchedulerPIR,
        tmnxWlanGwSoftGreIfMobTrigger    BITS,
        tmnxWlanGwSoftGreIfMobHoldTime   Unsigned32,
        tmnxWlanGwSoftGreIfDefRetailSvc  TmnxServId,
        tmnxWlanGwSoftGreIfTcpMssAdjust  Unsigned32,
        tmnxWlanGwSoftGreIfEHoldTime     Unsigned32,
        tmnxWlanGwSoftGreIfDataTrigg     TmnxEnabledDisabled,
        tmnxWlanGwSoftGreIfAuthPlcy      TNamedItemOrEmpty,
        tmnxWlanGwSoftGreIfAuthHoldTime  Unsigned32,
        tmnxWlanGwSoftGreIfRadProxVrtr   TmnxVRtrIDOrZero,
        tmnxWlanGwSoftGreIfRadProxSrv    TNamedItemOrEmpty,
        tmnxWlanGwSoftGreIfRadProxMacFmt TmnxMacSpecification,
        tmnxWlanGwSoftGreIfGwV6AddrType  InetAddressType,
        tmnxWlanGwSoftGreIfGwV6Addr      InetAddress,
        tmnxWlanGwSoftGreIfMobArpAp      TmnxEnabledDisabled,
        tmnxWlanGwSoftGreIfDownIfGrpDeg  TruthValue,
        tmnxWlanGwSoftGreIfL2ApEncapType INTEGER,
        tmnxWlanGwSoftGreIfMultiTuType TruthValue,
        tmnxWlanGwSoftGreIfL2tpLrnCookie INTEGER,
        tmnxWlanGwSoftGreIfL2tpCookie OCTET STRING,
        tmnxWlanGwSoftGreIfNumSoftGreTu  Gauge32
    }

tmnxWlanGwSoftGreIfLastCh OBJECT-TYPE
    SYNTAX      TimeStamp
    MAX-ACCESS  read-only
    STATUS      current
    DESCRIPTION
        "The value of tmnxWlanGwSoftGreIfLastCh indicates the sysUpTime at
         the time of the most recent management-initiated change to this
         table row."
    ::= { tmnxWlanGwSoftGreIfEntry 1 }

tmnxWlanGwSoftGreIfAdminState OBJECT-TYPE
    SYNTAX      TmnxAdminState
    MAX-ACCESS  read-create
    STATUS      current
    DESCRIPTION
       "The value of tmnxWlanGwSoftGreIfAdminState specifies the
        administrative state of Soft GRE on this group interface."
    DEFVAL { outOfService }
    ::= { tmnxWlanGwSoftGreIfEntry 2 }

tmnxWlanGwSoftGreIfRouter OBJECT-TYPE
    SYNTAX      TmnxVRtrIDOrZero
    MAX-ACCESS  read-create
    STATUS      current
    DESCRIPTION
        "The value of tmnxWlanGwSoftGreIfRouter specifies 
         the identifier of the virtual router instance 
         where the tunneled User Equipment traffic is routed.
         
         The value zero specifies that the router instance corresponding
         to the service containing this interface is used." 
    DEFVAL { 0 }
    ::= { tmnxWlanGwSoftGreIfEntry 3 }
    
tmnxWlanGwSoftGreIfGwAddrType OBJECT-TYPE
    SYNTAX      InetAddressType
    MAX-ACCESS  read-create
    STATUS      current
    DESCRIPTION
        "The value of tmnxWlanGwSoftGreIfGwAddrType specifies the type of
         address stored in tmnxWlanGwSoftGreIfGwAddr."
    DEFVAL { unknown }
    ::= { tmnxWlanGwSoftGreIfEntry 4 }

tmnxWlanGwSoftGreIfGwAddr OBJECT-TYPE
    SYNTAX      InetAddress (SIZE(0|4|16))
    MAX-ACCESS  read-create
    STATUS      current
    DESCRIPTION
        "The value of tmnxWlanGwSoftGreIfGwAddr specifies the IP address of
         the WLAN Gateway GRE function of this system on this group interface."
    DEFVAL { ''H }  
    ::= { tmnxWlanGwSoftGreIfEntry 5 }

tmnxWlanGwSoftGreIfGrpId OBJECT-TYPE
    SYNTAX      TmnxWlanGwIsaGrpIdOrZero
    MAX-ACCESS  read-create
    STATUS      current
    DESCRIPTION
        "The value of tmnxWlanGwSoftGreIfGrpId specifies the identifier
         of the WLAN Gateway ISA group that terminates GRE for this group interface."
    DEFVAL { 0 }
    ::= { tmnxWlanGwSoftGreIfEntry 6 }
    
tmnxWlanGwSoftGreIfShapingType OBJECT-TYPE
    SYNTAX      INTEGER {
                    none      (0),
                    perTunnel (1),
                    perRetailer (2)
                }
    MAX-ACCESS  read-create
    STATUS      current
    DESCRIPTION
       "The value of tmnxWlanGwSoftGreIfShapingType specifies 
        the granularity of the egress shaping 
        for Soft GRE on this group interface.
        
        The value of this object can only be modified 
        while the value of tmnxWlanGwSoftGreIfAdminState 
        is equal to 'outOfService'.
        
        The value 'perTunnel' specifies that a separate shaper is applied
        to each Soft GRE tunnel; the value 'perRetailer' specifies that a separate
        shaper is applied to each retailer Mobile Network Operator's fraction of the
        Soft GRE tunnel payload."
    DEFVAL { none }
    ::= { tmnxWlanGwSoftGreIfEntry 7 }

tmnxWlanGwSoftGreIfShapeMultiUe OBJECT-TYPE
    SYNTAX      TruthValue
    MAX-ACCESS  read-create
    STATUS      current
    DESCRIPTION
       "The value of tmnxWlanGwSoftGreIfShapeMultiUe specifies 
        conditional egress shaping.
        
        If the value of tmnxWlanGwSoftGreIfShapeMultiUe is equal to 'true',
        egress shaping is only enabled for a Soft GRE tunnel while there are
        multiple UE (User Equipment) using it.
        
        If the value of tmnxWlanGwSoftGreIfShapeMultiUe is equal to 'false',
        egress shaping is always enabled for every Soft GRE tunnel, 
        also while there is only a single UE using it."
    DEFVAL { false }
    ::= { tmnxWlanGwSoftGreIfEntry 8 }

tmnxWlanGwSoftGreIfEQosPlcy OBJECT-TYPE
    SYNTAX      TPolicyID (1..65535)
    MAX-ACCESS  read-create
    STATUS      current
    DESCRIPTION
        "The value of tmnxWlanGwSoftGreIfEQosPlcy specifies the identifier
         of the egress QoS policy associated with each Soft GRE tunnel
         of this interface."
    DEFVAL { 1 }
    ::= { tmnxWlanGwSoftGreIfEntry 9 }

tmnxWlanGwSoftGreIfESchedPlcy OBJECT-TYPE
    SYNTAX      TNamedItemOrEmpty
    MAX-ACCESS  read-create
    STATUS      current
    DESCRIPTION
        "The value of tmnxWlanGwSoftGreIfESchedPlcy specifies the identifier
         of the egress scheduler policy associated with each Soft GRE tunnel
         of this interface."
    DEFVAL { "" }
    ::= { tmnxWlanGwSoftGreIfEntry 10 }
    
tmnxWlanGwSoftGreIfEAggRateLimit OBJECT-TYPE
    SYNTAX      TPortSchedulerPIR
    UNITS       "kbps"
    MAX-ACCESS  read-create
    STATUS      current
    DESCRIPTION
        "The value of tmnxWlanGwSoftGreIfEAggRateLimit specifies
         the aggregate rate limit of each shaper associated with this interface.
         
         The value minus one specifies that there is no limit configured."
    DEFVAL { -1 }
    ::= { tmnxWlanGwSoftGreIfEntry 11 }
    
tmnxWlanGwSoftGreIfMobTrigger OBJECT-TYPE
    SYNTAX      BITS {
                    data (0),
                    iapp (1)
                }
    MAX-ACCESS  read-create
    STATUS      current
    DESCRIPTION
       "The value of tmnxWlanGwSoftGreIfMobTrigger specifies 
        what is used as a trigger for mobility detection.
        
        The value 'data' specifies that data traffic be used as a trigger.
        
        The value 'iapp' specifies that Inter Access Point Protocol (IAPP)
        messages be used as a trigger"
    DEFVAL { { } }
    ::= { tmnxWlanGwSoftGreIfEntry 12 }

tmnxWlanGwSoftGreIfMobHoldTime OBJECT-TYPE
    SYNTAX      Unsigned32 (0..255)
    UNITS       "seconds"
    MAX-ACCESS  read-create
    STATUS      current
    DESCRIPTION
        "The value of tmnxWlanGwSoftGreIfMobHoldTime specifies
         the minimum time that a User Equipment will be held 
         associated with its current Access Point (AP)
         before being associated with a new AP.
         
         The hold time is used to prevent overwhelming the system
         with mobility triggers, by limiting the rate at which 
         a UE can move from one AP to another while the system 
         is very busy already."
    DEFVAL { 5 }
    ::= { tmnxWlanGwSoftGreIfEntry 13 }
    
tmnxWlanGwSoftGreIfDefRetailSvc OBJECT-TYPE
    SYNTAX      TmnxServId
    MAX-ACCESS  read-create
    STATUS      current
    DESCRIPTION
       "The value of tmnxWlanGwSoftGreIfDefRetailSvc specifies
        the identifier of the retail service to be used by the
        default vlan range.
        
        The value zero specifies that there is no default retail
        service configured."
    DEFVAL { 0 }
    ::= { tmnxWlanGwSoftGreIfEntry 14 }
    
tmnxWlanGwSoftGreIfTcpMssAdjust OBJECT-TYPE
    SYNTAX      Unsigned32 (0|160..10240)
    UNITS       "bytes"
    MAX-ACCESS  read-create
    STATUS      current
    DESCRIPTION
        "The value of tmnxWlanGwSoftGreIfTcpMssAdjust specifies 
         the value to put into the TCP Maximum Segment Size (MSS) option
         if not already present, or if the present value is higher.
         
         The value zero means that no MSS option adjustment is done."
    DEFVAL { 0 }
    ::= { tmnxWlanGwSoftGreIfEntry 15 }

tmnxWlanGwSoftGreIfEHoldTime OBJECT-TYPE
    SYNTAX      Unsigned32 (0..86400 | 'ffffffff'h)
    UNITS       "seconds"
    MAX-ACCESS  read-create
    STATUS      current
    DESCRIPTION
        "The value of tmnxWlanGwSoftGreIfEHoldTime specifies
         the minimum time that the egress QoS resources associated with 
         a Soft GRE tunnel (such as a shaper) are held after the last 
         User Equipment of the Soft GRE tunnel has disappeared.
         
         The value all ones specifies an infinite time.
         
         The value zero specifies that the resources are released immediately."
    DEFVAL { 0 }
    ::= { tmnxWlanGwSoftGreIfEntry 16 }
    
tmnxWlanGwSoftGreIfDataTrigg OBJECT-TYPE
    SYNTAX      TmnxEnabledDisabled
    MAX-ACCESS  read-create
    STATUS      obsolete
    DESCRIPTION
       "The object tmnxWlanGwSoftGreIfDataTrigg is obsolete.
       
        Please use the object tmnxWlanGwVlanDataTrigg in the 
        tmnxWlanGwVlanTable instead, with the default VLAN
        tag range [4096-4096], to configure the default properties for
        the WLAN Gateway interface."
    DEFVAL { disabled }
    ::= { tmnxWlanGwSoftGreIfEntry 18 }
    
tmnxWlanGwSoftGreIfAuthPlcy OBJECT-TYPE
    SYNTAX      TNamedItemOrEmpty
    MAX-ACCESS  read-create
    STATUS      obsolete
    DESCRIPTION
        "The object tmnxWlanGwSoftGreIfAuthPlcy is obsolete.
       
        Please use the object tmnxWlanGwVlanAuthPlcy in the 
        tmnxWlanGwVlanTable instead, with the default VLAN
        tag range [4096-4096], to configure the default properties for
        the WLAN Gateway interface."
    DEFVAL { "" }
    ::= { tmnxWlanGwSoftGreIfEntry 19 }
    
tmnxWlanGwSoftGreIfAuthHoldTime OBJECT-TYPE
    SYNTAX      Unsigned32 (0..3600)
    UNITS       "seconds"
    MAX-ACCESS  read-create
    STATUS      obsolete
    DESCRIPTION
        "The object tmnxWlanGwSoftGreIfAuthHoldTime is obsolete.
       
        Please use the object tmnxWlanGwVlanAuthHoldTime in the 
        tmnxWlanGwVlanTable instead, with the default VLAN
        tag range [4096-4096], to configure the default properties for
        the WLAN Gateway interface."
    DEFVAL { 5 }
    ::= { tmnxWlanGwSoftGreIfEntry 20 }
    
tmnxWlanGwSoftGreIfRadProxVrtr OBJECT-TYPE
    SYNTAX      TmnxVRtrIDOrZero
    MAX-ACCESS  read-create
    STATUS      obsolete
    DESCRIPTION
        "The object tmnxWlanGwSoftGreIfRadProxVrtr is obsolete.
       
         Please use the object tmnxWlanGwVlanRadProxVrtr in the 
         tmnxWlanGwVlanTable instead, with the default VLAN
         tag range [4096-4096], to configure the default properties for
         the WLAN Gateway interface."
    DEFVAL { 0 }
    ::= { tmnxWlanGwSoftGreIfEntry 21 }

tmnxWlanGwSoftGreIfRadProxSrv OBJECT-TYPE
    SYNTAX      TNamedItemOrEmpty
    MAX-ACCESS  read-create
    STATUS      obsolete
    DESCRIPTION
        "The object tmnxWlanGwSoftGreIfRadProxSrv is obsolete.
       
         Please use the object tmnxWlanGwVlanRadProxSrv in the 
         tmnxWlanGwVlanTable instead, with the default VLAN
         tag range [4096-4096], to configure the default properties for
         the WLAN Gateway interface."
    DEFVAL { "" }
    ::= { tmnxWlanGwSoftGreIfEntry 22 }
    
tmnxWlanGwSoftGreIfRadProxMacFmt OBJECT-TYPE
    SYNTAX      TmnxMacSpecification (SIZE (2..7))
    MAX-ACCESS  read-create
    STATUS      obsolete
    DESCRIPTION
        "The object tmnxWlanGwSoftGreIfRadProxMacFmt is obsolete.
       
         Please use the object tmnxWlanGwVlanRadProxMacFmt in the 
         tmnxWlanGwVlanTable instead, with the default VLAN
         tag range [4096-4096], to configure the default properties for
         the WLAN Gateway interface."
    DEFVAL { "aa:" }
    ::= { tmnxWlanGwSoftGreIfEntry 23 }

tmnxWlanGwSoftGreIfGwV6AddrType OBJECT-TYPE
    SYNTAX      InetAddressType
    MAX-ACCESS  read-create
    STATUS      current
    DESCRIPTION
        "The value of tmnxWlanGwSoftGreIfGwAddrType specifies the type of
         address stored in tmnxWlanGwSoftGreIfGwV6Addr."
    DEFVAL { unknown }
    ::= { tmnxWlanGwSoftGreIfEntry 29 }

tmnxWlanGwSoftGreIfGwV6Addr OBJECT-TYPE
    SYNTAX      InetAddress (SIZE(0|16))
    MAX-ACCESS  read-create
    STATUS      current
    DESCRIPTION
        "The value of tmnxWlanGwSoftGreIfGwAddr specifies the IP address of
         the WLAN Gateway GRE function of this system on this group interface."
    DEFVAL { ''H }  
    ::= { tmnxWlanGwSoftGreIfEntry 30 }

tmnxWlanGwSoftGreIfMobArpAp OBJECT-TYPE
    SYNTAX      TmnxEnabledDisabled
    MAX-ACCESS  read-create
    STATUS      current
    DESCRIPTION
       "The value of tmnxWlanGwSoftGreIfMobArpAp specifies 
        if this system sends an ARP Request upon detecting mobility,
        in order to learn the MAC address of the Access Point."
    DEFVAL { disabled }
    ::= { tmnxWlanGwSoftGreIfEntry 32 }

tmnxWlanGwSoftGreIfDownIfGrpDeg  OBJECT-TYPE
    SYNTAX       TruthValue
    MAX-ACCESS   read-create
    STATUS       current
    DESCRIPTION
        "The value of tmnxWlanGwSoftGreIfDownIfGrpDeg specifies 
         if the system will bring this interface operiationally down
         when its ISA WLAN Gateway becomes degraded, that means: when
         the value of the object tmnxWlanGwGrpDegraded in the row
         where the tmnxWlanGwGrpId is equal to the value
         of tmnxWlanGwSoftGreIfGrpId is equal to 'true'."
    DEFVAL { false } 
    ::= { tmnxWlanGwSoftGreIfEntry 35 }
    
tmnxWlanGwSoftGreIfL2ApEncapType  OBJECT-TYPE
    SYNTAX       INTEGER {
                    null (1),
                    dot1q (2),
                    qinq (10)
                }
    MAX-ACCESS   read-create
    STATUS       current
    DESCRIPTION
        "The value of tmnxWlanGwSoftGreIfL2ApEncapType specifies 
         the encapsulation type of all layer 2 access points
         where the value of tmnxWlanGwL2ApEncapType is equal to 'default'."
    DEFVAL { null } 
    ::= { tmnxWlanGwSoftGreIfEntry 36 }
    
tmnxWlanGwSoftGreIfMultiTuType  OBJECT-TYPE
    SYNTAX       TruthValue
    MAX-ACCESS   read-create
    STATUS       current
    DESCRIPTION
        "The value of tmnxWlanGwSoftGreIfMultiTuType specifies 
         if this system supports multiple tunnel types terminating
         on this interface."
    DEFVAL { false } 
    ::= { tmnxWlanGwSoftGreIfEntry 37 }
    
tmnxWlanGwSoftGreIfL2tpLrnCookie  OBJECT-TYPE
    SYNTAX       INTEGER {
                    ifMatch (1),
                    never (2),
                    always (3)
                }
    MAX-ACCESS   read-create
    STATUS       current
    DESCRIPTION
        "The value of tmnxWlanGwSoftGreIfL2tpLrnCookie specifies 
         when this system will learn the cookie from L2TP tunnels
         terminating on this interface.
         
         Learning the cookie means that the value of the octets 3-8 of the cookie
         is interpreted as an access point's MAC address,
         and used as such, for example in the Called-Station-Id attribute
         of RADIUS Interim-Update messages.
         
         The value 'ifMatch' means that the cookie will be interpreted
         only if the value of the first two octets of the cookie
         is equal to the value of the object tmnxWlanGwSoftGreIfL2tpCookie."
    REFERENCE
       "RFC 3931 Layer Two Tunneling Protocol - Version 3 (L2TPv3), 
        section 4.1 L2TP Over Specific Packet-Switched Networks (PSNs).
        
        RFC 2865 Remote Authentication Dial In User Service (RADIUS), 
        section 5.30 Called-Station-Id.
        
        RFC 2866 RADIUS Accounting, 
        section 5.1.  Acct-Status-Type."
    DEFVAL { never } 
    ::= { tmnxWlanGwSoftGreIfEntry 38 }
    
tmnxWlanGwSoftGreIfL2tpCookie  OBJECT-TYPE
    SYNTAX       OCTET STRING (SIZE(2))
    MAX-ACCESS   read-create
    STATUS       current
    DESCRIPTION
        "The value of tmnxWlanGwSoftGreIfL2tpCookie specifies 
         the value to match with the first two octets of the L2TP cookie.
         
         A value other than all zeroes is only accepted while the value of
         the object tmnxWlanGwSoftGreIfL2tpLrnCookie is equal to 'ifMatch'.
         
         If the first two octets of the cookie match, 
         the system learns the value of the remainder of the cookie, in octets 3 until and including 8."
    DEFVAL { '0000'H } 
    ::= { tmnxWlanGwSoftGreIfEntry 39 }
    
tmnxWlanGwSoftGreIfNumSoftGreTu OBJECT-TYPE
    SYNTAX      Gauge32
    MAX-ACCESS  read-only
    STATUS      current
    DESCRIPTION
        "The value of tmnxWlanGwSoftGreIfNumSoftGreTu indicates 
         the number of Soft GRE tunnels terminated on this interface."
    ::= { tmnxWlanGwSoftGreIfEntry 100 }
--
--      Soft GRE Tunnel Table
--

tmnxWlanGwSoftGreTuTable   OBJECT-TYPE
    SYNTAX      SEQUENCE OF TmnxWlanGwSoftGreTuEntry
    MAX-ACCESS  not-accessible
    STATUS      current
    DESCRIPTION
       "The tmnxWlanGwSoftGreTuTable contains information about
        Soft GRE tunnels terminated by this system."
    ::= { tmnxWlanGwSoftGreObjs 2 }

tmnxWlanGwSoftGreTuEntry   OBJECT-TYPE
    SYNTAX      TmnxWlanGwSoftGreTuEntry
    MAX-ACCESS  not-accessible
    STATUS      current
    DESCRIPTION
       "Each conceptual row represents a Soft GRE tunnel.

        Entries in this table are created and destroyed by the system."
    INDEX { vRtrID,
            tmnxWlanGwSoftGreTuRemoteAddrTyp,
            tmnxWlanGwSoftGreTuRemoteAddr,
            tmnxWlanGwSoftGreTuLocalAddrType,
            tmnxWlanGwSoftGreTuLocalAddr
          }
    ::= { tmnxWlanGwSoftGreTuTable 1 }

TmnxWlanGwSoftGreTuEntry ::= 
    SEQUENCE {
        tmnxWlanGwSoftGreTuRemoteAddrTyp InetAddressType,
        tmnxWlanGwSoftGreTuRemoteAddr    InetAddress,
        tmnxWlanGwSoftGreTuLocalAddrType InetAddressType,
        tmnxWlanGwSoftGreTuLocalAddr     InetAddress,
        tmnxWlanGwSoftGreTuEstabTime     DateAndTime,
        tmnxWlanGwSoftGreTuIsaGroup      TmnxWlanGwIsaGrpIdOrZero,
        tmnxWlanGwSoftGreTuIsaMember     Unsigned32,
        tmnxWlanGwSoftGreTuNumUe         Gauge32,
        tmnxWlanGwSoftGreTuApMacAddress  MacAddress,
        tmnxWlanGwSoftGreTuApLearnFailed TruthValue,
        tmnxWlanGwSoftGreTuEncap         INTEGER,     
        tmnxWlanGwSoftGreTuEncapTag1     QTagFullRangeOrNone,     
        tmnxWlanGwSoftGreTuEncapTag2     QTagFullRangeOrNone,     
        tmnxWlanGwSoftGreTuService       TmnxServId,
        tmnxWlanGwSoftGreTuInterface     InterfaceIndex
    }
        
tmnxWlanGwSoftGreTuRemoteAddrTyp OBJECT-TYPE
    SYNTAX      InetAddressType
    MAX-ACCESS  not-accessible
    STATUS      current
    DESCRIPTION 
        "The value of tmnxWlanGwSoftGreTuRemoteAddrTyp specifies
         the address type of tmnxWlanGwSoftGreTuRemoteAddr.
         
         The only values allowed are 'ipv4' and 'ipv6'."
    ::= { tmnxWlanGwSoftGreTuEntry 1 }

tmnxWlanGwSoftGreTuRemoteAddr OBJECT-TYPE
    SYNTAX      InetAddress (SIZE(4|16))
    MAX-ACCESS  not-accessible
    STATUS      current
    DESCRIPTION
        "The value of the object tmnxWlanGwSoftGreTuRemoteAddr specifies
         the IP address of the remote endpoint of this Soft GRE tunnel,
         that is the source IP address in the tunnel header of
         received packets."
    ::= { tmnxWlanGwSoftGreTuEntry 2 }

tmnxWlanGwSoftGreTuLocalAddrType OBJECT-TYPE
    SYNTAX      InetAddressType
    MAX-ACCESS  not-accessible
    STATUS      current
    DESCRIPTION 
        "The value of tmnxWlanGwSoftGreTuLocalAddrType specifies
         the address type of tmnxWlanGwSoftGreTuLocalAddr.
         
         The only values allowed are 'ipv4' and 'ipv6'."
    ::= { tmnxWlanGwSoftGreTuEntry 3 }

tmnxWlanGwSoftGreTuLocalAddr OBJECT-TYPE
    SYNTAX      InetAddress (SIZE(4|16))
    MAX-ACCESS  not-accessible
    STATUS      current
    DESCRIPTION
        "The value of the object tmnxWlanGwSoftGreTuLocalAddr specifies
         the IP address of the local endpoint of this Soft GRE tunnel,
         that is the destination IP address in the tunnel header of
         received packets.
         
         The value of this object is equal to the value
         of the tmnxWlanGwSoftGreIfGwAddr object in the conceptual row
         corresponding to the Soft GRE Group-Interface where this tunnel
         is terminated."
    ::= { tmnxWlanGwSoftGreTuEntry 4 }

tmnxWlanGwSoftGreTuEstabTime OBJECT-TYPE
    SYNTAX      DateAndTime (SIZE (11))
    MAX-ACCESS  read-only
    STATUS      current
    DESCRIPTION 
        "The value of the object tmnxWlanGwSoftGreTuEstabTime indicates
         the value of sysUpTime when this Soft GRE tunnel was established."
    ::= { tmnxWlanGwSoftGreTuEntry 5 }

tmnxWlanGwSoftGreTuIsaGroup OBJECT-TYPE
    SYNTAX      TmnxWlanGwIsaGrpIdOrZero
    MAX-ACCESS  read-only
    STATUS      current
    DESCRIPTION 
        "The value of the object tmnxWlanGwSoftGreTuIsaGroup indicates
         the identifier of the WLAN Gateway ISA group that processes
         this Soft GRE tunnel.
         
         The value of this object is equal to the value
         of the object tmnxWlanGwGrpId in the conceptual row that
         corresponds to the WLAN Gateway ISA group."
    ::= { tmnxWlanGwSoftGreTuEntry 6 }

tmnxWlanGwSoftGreTuIsaMember OBJECT-TYPE
    SYNTAX      Unsigned32
    MAX-ACCESS  read-only
    STATUS      current
    DESCRIPTION 
        "The value of the object tmnxWlanGwSoftGreTuIsaGroup indicates
         the identifier of the ISA Group member that processes
         this Soft GRE tunnel.
         
         The value of this object is equal to the value
         of the object tmnxWlanGwIsaMemberId in the
         conceptual row in the tmnxWlanGwIsaMemberTable
         that corresponds to thsi ISA Group member."
    ::= { tmnxWlanGwSoftGreTuEntry 7 }

tmnxWlanGwSoftGreTuNumUe OBJECT-TYPE
    SYNTAX      Gauge32
    MAX-ACCESS  read-only
    STATUS      current
    DESCRIPTION 
        "The value of the object tmnxWlanGwSoftGreTuNumUe indicates
         the number of User Equipment's connected to this system through
         this Soft GRE tunnel."
    ::= { tmnxWlanGwSoftGreTuEntry 8 }

tmnxWlanGwSoftGreTuApMacAddress OBJECT-TYPE
    SYNTAX      MacAddress
    MAX-ACCESS  read-only
    STATUS      current
    DESCRIPTION
        "The value of the object tmnxWlanGwSoftGreTuApMacAddress indicates
         the MAC address of the Access Point, as learned by this system.
         
         The value all zeroes indicates that the Access Point MAC is not
         known, either because there was no attempt to learn it, or because
         an attempt failed."
    ::= { tmnxWlanGwSoftGreTuEntry 10 }

tmnxWlanGwSoftGreTuApLearnFailed OBJECT-TYPE
    SYNTAX      TruthValue
    MAX-ACCESS  read-only
    STATUS      current
    DESCRIPTION
        "The value of the object tmnxWlanGwSoftGreTuApLearnFailed indicates
         if the learning of the MAC address of the Access Point failed.
         
         When the value of tmnxWlanGwSoftGreTuApLearnFailed is equal to 'true',
         the value of tmnxWlanGwSoftGreTuApMacAddress is equal to all zeroes."
    ::= { tmnxWlanGwSoftGreTuEntry 11 }

tmnxWlanGwSoftGreTuEncap OBJECT-TYPE
    SYNTAX      INTEGER {
                   gre (1),
                   l2tp (2),
                   vlan (3)
                }
    MAX-ACCESS  read-only
    STATUS      current
    DESCRIPTION
        "The value of the object tmnxWlanGwSoftGreTuEncap indicates
         the tunnel encapsulation.
         
         The meaning of the values is
         'gre' : Soft GRE
         'l2tp': Soft L2TPv3
         'vlan': IEEE 802.1Q or IEEE 802.1ad.

         The value of tmnxWlanGwSoftGreTuEncap is learned from the latest UE 
         associated with this tunnel; when a given Access Point changes its
         encapsulation, there may be a transition period where the system
         contexts of some UE of this tunnel already have the new encapsulation,
         while some other UE still seem to have the previous encapsulation."
    ::= { tmnxWlanGwSoftGreTuEntry 12 }

tmnxWlanGwSoftGreTuEncapTag1 OBJECT-TYPE
    SYNTAX      QTagFullRangeOrNone 
    MAX-ACCESS  read-only
    STATUS      current
    DESCRIPTION
        "The value of the object tmnxWlanGwSoftGreTuEncapTag1 indicates
         the VLAN tag in case of IEEE 802.1Q encapsulation,
         or the outer tag (service tag, ethertype 0x88a8) in case of IEEE 802.1ad encapsulation.
         
         If the value of tmnxWlanGwSoftGreTuEncap is not equal to 'vlan',
         the value of tmnxWlanGwSoftGreTuEncapTag1 is minus one."
    ::= { tmnxWlanGwSoftGreTuEntry 13 }

tmnxWlanGwSoftGreTuEncapTag2 OBJECT-TYPE
    SYNTAX      QTagFullRangeOrNone 
    MAX-ACCESS  read-only
    STATUS      current
    DESCRIPTION
        "The value of the object tmnxWlanGwSoftGreTuEncapTag2 indicates
         the inner tag (customer tag, ethertype 0x8100) in case of qinq encapsulation.
         
         If the value of tmnxWlanGwSoftGreTuEncap is not equal to 'vlan',
         the value of tmnxWlanGwSoftGreTuEncapTag2 is minus one."
    ::= { tmnxWlanGwSoftGreTuEntry 14 }

tmnxWlanGwSoftGreTuService OBJECT-TYPE
    SYNTAX      TmnxServId 
    MAX-ACCESS  read-only
    STATUS      current
    DESCRIPTION
        "The value of the object tmnxWlanGwSoftGreTuService indicates
         the identifier of the service of the interface
         associated with this tunnel."
    ::= { tmnxWlanGwSoftGreTuEntry 15 }

tmnxWlanGwSoftGreTuInterface OBJECT-TYPE
    SYNTAX      InterfaceIndex 
    MAX-ACCESS  read-only
    STATUS      current
    DESCRIPTION
        "The value of the object tmnxWlanGwSoftGreTuInterface indicates
         the identifier of the interface associated with this tunnel.
         
         Together with tmnxWlanGwSoftGreTuService, it identifies a row in
         the tmnxWlanGwSoftGreIfTable."
    ::= { tmnxWlanGwSoftGreTuEntry 16 }

--
--      Soft GRE Tunnel QoS Table
--

tmnxWlanGwTuQosTable   OBJECT-TYPE
    SYNTAX      SEQUENCE OF TmnxWlanGwTuQosEntry
    MAX-ACCESS  not-accessible
    STATUS      current
    DESCRIPTION
       "The tmnxWlanGwTuQosTable contains information about
        Soft GRE tunnels' Quality of Service (QoS) infrastructure.
        
        The QoS infrastructure of a Soft GRE tunnel consists of
        one or multiple Egress Encapsulation Groups."
    ::= { tmnxWlanGwSoftGreObjs 3 }

tmnxWlanGwTuQosEntry   OBJECT-TYPE
    SYNTAX      TmnxWlanGwTuQosEntry
    MAX-ACCESS  not-accessible
    STATUS      current
    DESCRIPTION
       "Each conceptual row represents information about a WLAN Gateway 
        tunnel-QoS-infrastructure.

        Entries in this table are created and destroyed by the system."
    INDEX { vRtrID,
            tmnxWlanGwSoftGreTuRemoteAddrTyp,
            tmnxWlanGwSoftGreTuRemoteAddr,
            tmnxWlanGwSoftGreTuLocalAddrType,
            tmnxWlanGwSoftGreTuLocalAddr,
            tmnxWlanGwTuQosRetailService
          }
    ::= { tmnxWlanGwTuQosTable 1 }

TmnxWlanGwTuQosEntry ::= 
    SEQUENCE {
        tmnxWlanGwTuQosRetailService     TmnxServId,
        tmnxWlanGwTuQosEegSvcId          TmnxServId,
        tmnxWlanGwTuQosEegPortId         TmnxPortID,
        tmnxWlanGwTuQosEegEncapValue     TmnxEncapVal,
        tmnxWlanGwTuQosEegName           TNamedItemOrEmpty,
        tmnxWlanGwTuQosEegMember         SvcISID,
        tmnxWlanGwTuQosState             TmnxWlanGwQoSOperState,     
        tmnxWlanGwTuQosNumUe             Gauge32,
        tmnxWlanGwTuQosRemainingHoldTime Gauge32     
    }
        
tmnxWlanGwTuQosRetailService OBJECT-TYPE
    SYNTAX      TmnxServId
    MAX-ACCESS  not-accessible
    STATUS      current
    DESCRIPTION     
        "The value of the object tmnxWlanGwTuQosRetailService indicates
         the identifier of the retail service.
         
         The value zero indicates that this tunnel has per-tunnel QoS."
    ::= { tmnxWlanGwTuQosEntry 1 }

tmnxWlanGwTuQosEegSvcId OBJECT-TYPE
    SYNTAX      TmnxServId
    MAX-ACCESS  read-only
    STATUS      current
    DESCRIPTION     
        "The value of the object tmnxWlanGwTuQosEegSvcId indicates
         the service identifier of the B-Component instance 
         of the Egress Encapsulation Group member of 
         this tunnel-QoS-infrastructure.
         
         The value zero indicates that there is no
         egress encapsulation group member."
    ::= { tmnxWlanGwTuQosEntry 2 }

tmnxWlanGwTuQosEegPortId OBJECT-TYPE
    SYNTAX      TmnxPortID
    MAX-ACCESS  read-only
    STATUS      current
    DESCRIPTION     
        "The value of the object tmnxWlanGwTuQosEegPortId indicates 
         the ID of the access port in the B-Component instance 
         of the Egress Encapsulation Group member of  
         this tunnel-QoS-infrastructure.
         
         The value zero indicates that there is no
         egress encapsulation group member."
    ::= { tmnxWlanGwTuQosEntry 3 }

tmnxWlanGwTuQosEegEncapValue OBJECT-TYPE
    SYNTAX      TmnxEncapVal
    MAX-ACCESS  read-only
    STATUS      current
    DESCRIPTION     
        "The value of the object tmnxWlanGwTuQosEegEncapValue indicates 
         the value of the label used to identify this SAP access port 
         in the B-Component instance of the Egress Encapsulation Group 
         member of this tunnel-QoS-infrastructure.
         
         The value zero indicates that there is no
         egress encapsulation group member."
    ::= { tmnxWlanGwTuQosEntry 4 }

tmnxWlanGwTuQosEegName OBJECT-TYPE
    SYNTAX      TNamedItemOrEmpty
    MAX-ACCESS  read-only
    STATUS      current
    DESCRIPTION     
        "The value of the object tmnxWlanGwTuQosEegName indicates 
         the name of the Egress Encapsulation Group of  
         this tunnel-QoS-infrastructure.
         
         An empty string indicates that there is no
         egress encapsulation group member."
    ::= { tmnxWlanGwTuQosEntry 5 }
    
tmnxWlanGwTuQosEegMember OBJECT-TYPE
    SYNTAX      SvcISID
    MAX-ACCESS  read-only
    STATUS      current
    DESCRIPTION
        "The value of tmnxWlanGwTuQosEegMember indicates 
         the identifier of the Egress Encapsulation Group 
         member of this tunnel-QoS-infrastructure.
         
         The value minus one indicates that there is no
         egress encapsulation group member." 
    ::= { tmnxWlanGwTuQosEntry 6 }

tmnxWlanGwTuQosState OBJECT-TYPE
    SYNTAX  TmnxWlanGwQoSOperState
    MAX-ACCESS  read-only
    STATUS      current
    DESCRIPTION
       "The value of tmnxWlanGwTuQosState indicates the
        operational state of this tunnel-QoS-infrastructure."
    ::= { tmnxWlanGwTuQosEntry 7 }

tmnxWlanGwTuQosNumUe OBJECT-TYPE
    SYNTAX      Gauge32
    MAX-ACCESS  read-only
    STATUS      current
    DESCRIPTION 
        "The value of the object tmnxWlanGwTuQosNumUe indicates
         the number of User Equipment's using this tunnel-QoS-infrastructure."
    ::= { tmnxWlanGwTuQosEntry 8 }

tmnxWlanGwTuQosRemainingHoldTime OBJECT-TYPE
    SYNTAX      Gauge32
    UNITS       "seconds"
    MAX-ACCESS  read-only
    STATUS      current
    DESCRIPTION 
        "The value of the object tmnxWlanGwTuQosRemainingHoldTime indicates
         the time remaining before this tunnel-QoS-infrastructure is released because
         there are no UE's using it.
         
         The value zero indicates that the hold timer is not running because there are still
         UE's using this tunnel-QoS-infrastructure.
         
         The value all ones indicates that this tunnel-QoS infrastructure is held infinitely."
    ::= { tmnxWlanGwTuQosEntry 9 }

--
--      Soft GRE Tunnel User Equipment Table
--

tmnxWlanGwSoftGreTuUeTable   OBJECT-TYPE
    SYNTAX      SEQUENCE OF TmnxWlanGwSoftGreTuUeEntry
    MAX-ACCESS  not-accessible
    STATUS      current
    DESCRIPTION
       "The tmnxWlanGwSoftGreTuUeTable contains the 
        WLAN Gateway User Equipment's (UE) connected to this system
        by means of Soft GRE tunnels, ordered by tunnel."
    ::= { tmnxWlanGwSoftGreObjs 4 }

tmnxWlanGwSoftGreTuUeEntry   OBJECT-TYPE
    SYNTAX      TmnxWlanGwSoftGreTuUeEntry
    MAX-ACCESS  not-accessible
    STATUS      current
    DESCRIPTION
       "Each conceptual row represents a WLAN Gateway User Equipment.

        Entries in this table are created and destroyed by the system."
    INDEX { vRtrID,
            tmnxWlanGwSoftGreTuRemoteAddrTyp,
            tmnxWlanGwSoftGreTuRemoteAddr,
            tmnxWlanGwSoftGreTuLocalAddrType,
            tmnxWlanGwSoftGreTuLocalAddr,
            tmnxWlanGwUeMacAddress
          }
    ::= { tmnxWlanGwSoftGreTuUeTable 1 }

TmnxWlanGwSoftGreTuUeEntry ::= 
    SEQUENCE {
        tmnxWlanGwSoftGreTuUeSsid        TNamedItemOrEmpty     
    }
        
tmnxWlanGwSoftGreTuUeSsid OBJECT-TYPE
    SYNTAX  TNamedItemOrEmpty
    MAX-ACCESS  read-only
    STATUS      current
    DESCRIPTION
       "The value of tmnxWlanGwUeSsid indicates 
        the Service Set ID (SSID) of this UE.
        
        This object refers to a conceptual row in the tmnxWlanGwSsidTable."
    ::= { tmnxWlanGwSoftGreTuUeEntry 1 }
    
--
--      Soft GRE Group Interface Extended Configuration Table
--
tmnxWlanGwSoftGreXtTable   OBJECT-TYPE
    SYNTAX      SEQUENCE OF TmnxWlanGwSoftGreXtEntry
    MAX-ACCESS  not-accessible
    STATUS      obsolete
    DESCRIPTION
       "The tmnxWlanGwSoftGreXtTable is obsolete.
       
        Please use the tmnxWlanGwVlanTable instead, with the default VLAN
        tag range [4096-4096], to configure the default properties for
        the WLAN Gateway interface."
    ::= { tmnxWlanGwSoftGreObjs 5 }

tmnxWlanGwSoftGreXtEntry OBJECT-TYPE
    SYNTAX      TmnxWlanGwSoftGreXtEntry
    MAX-ACCESS  not-accessible
    STATUS      obsolete
    DESCRIPTION
        "The tmnxWlanGwSoftGreXtTable is obsolete.
       
        Please use the tmnxWlanGwVlanTable instead, with the default VLAN
        tag range [4096-4096], to configure the default properties for
        the WLAN Gateway interface."
    AUGMENTS { tmnxWlanGwSoftGreIfEntry }
    ::= { tmnxWlanGwSoftGreXtTable 1 }

TmnxWlanGwSoftGreXtEntry ::=
    SEQUENCE {
        tmnxWlanGwSoftGreXtLastCh        TimeStamp,
        tmnxWlanGwSoftGreXtDhcp          TmnxEnabledDisabled,
        tmnxWlanGwSoftGreXtAddrType      InetAddressType,
        tmnxWlanGwSoftGreXtAddr          InetAddress,
        tmnxWlanGwSoftGreXtLeaseTime     Unsigned32,
        tmnxWlanGwSoftGreXtActLeaseTime  Unsigned32,
        tmnxWlanGwSoftGreXtDns1AddrType  InetAddressType,
        tmnxWlanGwSoftGreXtDns1Addr      InetAddress,
        tmnxWlanGwSoftGreXtDns2AddrType  InetAddressType,
        tmnxWlanGwSoftGreXtDns2Addr      InetAddress,
        tmnxWlanGwSoftGreXtNb1AddrType   InetAddressType,
        tmnxWlanGwSoftGreXtNb1Addr       InetAddress,
        tmnxWlanGwSoftGreXtNb2AddrType   InetAddressType,
        tmnxWlanGwSoftGreXtNb2Addr       InetAddress,
        tmnxWlanGwSoftGreXtHttpRdrPlcy   TNamedItemOrEmpty,
        tmnxWlanGwSoftGreXtNatPlcy       TNamedItemOrEmpty
    }

tmnxWlanGwSoftGreXtLastCh OBJECT-TYPE
    SYNTAX      TimeStamp
    MAX-ACCESS  read-only
    STATUS      obsolete
    DESCRIPTION
        "The value of tmnxWlanGwSoftGreXtLastCh indicates the sysUpTime at
         the time of the most recent management-initiated change to this
         table row."
    ::= { tmnxWlanGwSoftGreXtEntry 1 }

tmnxWlanGwSoftGreXtDhcp OBJECT-TYPE
    SYNTAX      TmnxEnabledDisabled
    MAX-ACCESS  read-create
    STATUS      obsolete
    DESCRIPTION
        "The value of tmnxWlanGwSoftGreXtDhcp specifies
         the administrative state of the DHCP protocol distributed
         on the ISA cards for the UE.
         
         While the value of the object tmnxWlanGwSoftGreXtDhcp is 
         equal to 'enabled', the distributed DHCP will reply to DHCP Request messages
         coming from UE without a corresponding subscriber known to this system." 
    DEFVAL { disabled } 
    ::= { tmnxWlanGwSoftGreXtEntry 2 }

tmnxWlanGwSoftGreXtAddrType OBJECT-TYPE
    SYNTAX      InetAddressType
    MAX-ACCESS  read-create
    STATUS      obsolete
    DESCRIPTION
        "The value of tmnxWlanGwSoftGreXtAddrType specifies the type of
         address stored in tmnxWlanGwSoftGreXtAddr."
    DEFVAL { unknown }
    ::= { tmnxWlanGwSoftGreXtEntry 3 }

tmnxWlanGwSoftGreXtAddr OBJECT-TYPE
    SYNTAX      InetAddress (SIZE(0|4|16))
    MAX-ACCESS  read-create
    STATUS      obsolete
    DESCRIPTION
        "The value of tmnxWlanGwSoftGreXtAddr specifies the IP address
         to be given to the User Equipment as 'yiaddr' in DHCP OFFER 
         and DHCP ACK messages.
         
         The same IP address can be given to multiple UE because the user traffic
         is tunneled and this WLAN Gateway is layer-2-aware.
         
         The virtual router instance corresponding to the service with ID 'svcId'
         must have a row in the TIMETRA-NAT-MIB::tmnxNatL2AwAddrTable,
         such that the value of tmnxWlanGwVlanAddr matches that address prefix
         but is not equal to the value of TIMETRA-NAT-MIB::tmnxNatL2AwAddr."
    DEFVAL { ''H }  
    ::= { tmnxWlanGwSoftGreXtEntry 4 }

tmnxWlanGwSoftGreXtLeaseTime OBJECT-TYPE
    SYNTAX      Unsigned32 (300..3600)
    UNITS       "seconds"
    MAX-ACCESS  read-create
    STATUS      obsolete
    DESCRIPTION
        "The value of tmnxWlanGwSoftGreXtLeaseTime specifies the IP address lease time
         to be given to the User Equipment in DHCP OFFER 
         and DHCP ACK messages, before authentication."
    DEFVAL { 600 }  
    ::= { tmnxWlanGwSoftGreXtEntry 5 }

tmnxWlanGwSoftGreXtActLeaseTime OBJECT-TYPE
    SYNTAX      Unsigned32 (300..3600)
    UNITS       "seconds"
    MAX-ACCESS  read-create
    STATUS      obsolete
    DESCRIPTION
        "The value of tmnxWlanGwSoftGreXtActLeaseTime specifies the IP address lease time
         to be given to the User Equipment in DHCP OFFER 
         and DHCP ACK messages, while the UE is active."
    DEFVAL { 600 }  
    ::= { tmnxWlanGwSoftGreXtEntry 6 }

tmnxWlanGwSoftGreXtDns1AddrType OBJECT-TYPE
    SYNTAX      InetAddressType
    MAX-ACCESS  read-create
    STATUS      obsolete
    DESCRIPTION
        "The value of tmnxWlanGwSoftGreXtDns1AddrType specifies
         the address type of tmnxWlanGwSoftGreXtDns1Addr."
    DEFVAL { unknown }
    ::= { tmnxWlanGwSoftGreXtEntry 7 }

tmnxWlanGwSoftGreXtDns1Addr OBJECT-TYPE
    SYNTAX      InetAddress (SIZE(0|4|16))
    MAX-ACCESS  read-create
    STATUS      obsolete
    DESCRIPTION
        "The value of tmnxWlanGwSoftGreXtDns1Addr specifies
         the address of the primary DNS server to be given to the 
         User Equipment in Option 6 of DHCP OFFER and DHCP ACK messages."
    REFERENCE
       "RFC 2132 DHCP Options and BOOTP Vendor Extensions, 
        section 3.8 Domain Name Server Option."
    DEFVAL { ''H }  
    ::= { tmnxWlanGwSoftGreXtEntry 8 }

tmnxWlanGwSoftGreXtDns2AddrType OBJECT-TYPE
    SYNTAX      InetAddressType
    MAX-ACCESS  read-create
    STATUS      obsolete
    DESCRIPTION
        "The value of tmnxWlanGwSoftGreXtDns2AddrType specifies
         the address type of tmnxWlanGwSoftGreXtDns2Addr."
    DEFVAL { unknown }
    ::= { tmnxWlanGwSoftGreXtEntry 9 }

tmnxWlanGwSoftGreXtDns2Addr OBJECT-TYPE
    SYNTAX      InetAddress (SIZE(0|4|16))
    MAX-ACCESS  read-create
    STATUS      obsolete
    DESCRIPTION
        "The value of tmnxWlanGwSoftGreXtDns2Addr specifies
         the address of the secondary DNS server  to be given to the 
         User Equipment in Option 6 of DHCP OFFER and DHCP ACK messages."
    REFERENCE
       "RFC 2132 DHCP Options and BOOTP Vendor Extensions, 
        section 3.8 Domain Name Server Option."
    DEFVAL { ''H }  
    ::= { tmnxWlanGwSoftGreXtEntry 10 }

tmnxWlanGwSoftGreXtNb1AddrType OBJECT-TYPE
    SYNTAX      InetAddressType
    MAX-ACCESS  read-create
    STATUS      obsolete
    DESCRIPTION
        "The value of tmnxWlanGwSoftGreXtNb1AddrType specifies
         the address type of tmnxWlanGwSoftGreXtNb1Addr."
    DEFVAL { unknown }
    ::= { tmnxWlanGwSoftGreXtEntry 11 }

tmnxWlanGwSoftGreXtNb1Addr OBJECT-TYPE
    SYNTAX      InetAddress (SIZE(0|4|16))
    MAX-ACCESS  read-create
    STATUS      obsolete
    DESCRIPTION
        "The value of tmnxWlanGwSoftGreXtNb1Addr specifies
         the address of the primary NBNS (Netbios Name Server) server 
         to be given to the 
         User Equipment in Option 44 of DHCP OFFER and DHCP ACK messages."
    REFERENCE
       "RFC 2132 DHCP Options and BOOTP Vendor Extensions, 
        section 8.5. Net BIOS over TCP/IP Name Server Option."
    DEFVAL { ''H }  
    ::= { tmnxWlanGwSoftGreXtEntry 12 }

tmnxWlanGwSoftGreXtNb2AddrType OBJECT-TYPE
    SYNTAX      InetAddressType
    MAX-ACCESS  read-create
    STATUS      obsolete
    DESCRIPTION
        "The value of tmnxWlanGwSoftGreXtNb2AddrType specifies
         the address type of tmnxWlanGwSoftGreXtNb2Addr."
    DEFVAL { unknown }
    ::= { tmnxWlanGwSoftGreXtEntry 13 }

tmnxWlanGwSoftGreXtNb2Addr OBJECT-TYPE
    SYNTAX      InetAddress (SIZE(0|4|16))
    MAX-ACCESS  read-create
    STATUS      obsolete
    DESCRIPTION
        "The value of tmnxWlanGwSoftGreXtNb2Addr specifies
         the address of the secondary NBNS server to be given to the 
         User Equipment in Option 44 of DHCP OFFER and DHCP ACK messages."
    REFERENCE
       "RFC 2132 DHCP Options and BOOTP Vendor Extensions, 
        section 8.5. Net BIOS over TCP/IP Name Server Option."
    DEFVAL { ''H }  
    ::= { tmnxWlanGwSoftGreXtEntry 14 }

tmnxWlanGwSoftGreXtHttpRdrPlcy OBJECT-TYPE
    SYNTAX      TNamedItemOrEmpty
    MAX-ACCESS  read-create
    STATUS      obsolete
    DESCRIPTION
        "The value of tmnxWlanGwSoftGreXtHttpRdrPlcy specifies the identifier
         of the HTTP redirect policy for UE.
         
         HTTP redirect is triggered per subscriber during
         the authentication phase, by the presence of certain vendor-
         specific attributes in the RADIUS Access-Accept message
        (Alc-Wifi-Portal-Redirect or Alc-Wifi-Portal-Url).
         
         A row with the same name must exist 
         in the TIMETRA-SUBSCRIBER-MGMT-MIB::tmnxSubHttpRdrPlcyTable."
    DEFVAL { "" }
    ::= { tmnxWlanGwSoftGreXtEntry 21 }
    
tmnxWlanGwSoftGreXtNatPlcy OBJECT-TYPE
    SYNTAX      TNamedItemOrEmpty
    MAX-ACCESS  read-create
    STATUS      obsolete
    DESCRIPTION
        "The value of tmnxWlanGwSoftGreXtNatPlcy specifies the identifier
         of the NAT policy for UE.
         
         Layer-2-Aware NAT hosts are temporarily created if UE are authenticated
         by a web portal.
         
         A row with the same name must exist in the TIMETRA-NAT-MIB::tmnxNatPlcyTable."
    DEFVAL { "" }
    ::= { tmnxWlanGwSoftGreXtEntry 22 }    

--
--      The Group Interface VLAN Range configuration Table
--

tmnxWlanGwVlanTable OBJECT-TYPE
    SYNTAX      SEQUENCE OF TmnxWlanGwVlanEntry
    MAX-ACCESS  not-accessible
    STATUS      current
    DESCRIPTION
       "The tmnxWlanGwVlanTable contains objects to configure
        WLAN Gateway behavior for Soft GRE Group-Interfaces
        and for ranges of IEEE 802.1q VLAN tags
        in Soft GRE Group-Interfaces."
    ::= { tmnxWlanGwSoftGreObjs 6 }

tmnxWlanGwVlanEntry OBJECT-TYPE
    SYNTAX      TmnxWlanGwVlanEntry
    MAX-ACCESS  not-accessible
    STATUS      current
    DESCRIPTION
        "Each conceptual row represents the set of configuration data
         for a range of VLAN Q-tags on a particular interface.
         
         Users whose traffic comes in on this interface 
         tagged with a matching VLAN Q-tag are to be processed according to
         the configuration specified in this conceptual row;
         otherwise, the default configuration specified 
         in the default range [4096-4096] must be used.

         Rows in this table are created and destroyed by means of SNMP
         operations on the tmnxWlanGwVlanRowStatus object.
         
         A row with the same values for svcId and iesIfIndex must exist
         in the tmnxWlanGwSoftGreIfTable.
         
         A single row in this table is always created by the system and 
         cannot be destroyed: the default range [4096-4096]."
    INDEX { svcId, iesIfIndex,
            tmnxWlanGwVlanTagStart,
            tmnxWlanGwVlanTagEnd }
    ::= { tmnxWlanGwVlanTable 1 }

TmnxWlanGwVlanEntry ::= 
    SEQUENCE {
        tmnxWlanGwVlanTagStart          Unsigned32,
        tmnxWlanGwVlanTagEnd            Unsigned32,
        tmnxWlanGwVlanRowStatus         RowStatus,
        tmnxWlanGwVlanLastCh            TimeStamp, 
        tmnxWlanGwVlanRetailService     TmnxServId,
        tmnxWlanGwVlanDhcp              TmnxEnabledDisabled,
        tmnxWlanGwVlanAddrType          InetAddressType,
        tmnxWlanGwVlanAddr              InetAddress,
        tmnxWlanGwVlanLeaseTime         Unsigned32,
        tmnxWlanGwVlanActLeaseTime      Unsigned32,
        tmnxWlanGwVlanDns1AddrType      InetAddressType,
        tmnxWlanGwVlanDns1Addr          InetAddress,
        tmnxWlanGwVlanDns2AddrType      InetAddressType,
        tmnxWlanGwVlanDns2Addr          InetAddress,
        tmnxWlanGwVlanNb1AddrType       InetAddressType,
        tmnxWlanGwVlanNb1Addr           InetAddress,
        tmnxWlanGwVlanNb2AddrType       InetAddressType,
        tmnxWlanGwVlanNb2Addr           InetAddress,
        tmnxWlanGwVlanHttpRdrPlcy       TNamedItemOrEmpty,
        tmnxWlanGwVlanNatPlcy           TNamedItemOrEmpty,
        tmnxWlanGwVlanDataTrigg         TmnxEnabledDisabled,
        tmnxWlanGwVlanAuthPlcy          TNamedItemOrEmpty,
        tmnxWlanGwVlanAuthHoldTime      Unsigned32,
        tmnxWlanGwVlanRadProxVrtr       TmnxVRtrIDOrZero,
        tmnxWlanGwVlanRadProxSrv        TNamedItemOrEmpty,
        tmnxWlanGwVlanRadProxMacFmt     TmnxMacSpecification,
        tmnxWlanGwVlanAuthOnDhcp        TmnxEnabledDisabled,
        tmnxWlanGwVlanL2Service          TmnxServId,
        tmnxWlanGwVlanL2AdminState       TmnxEnabledDisabled,
        tmnxWlanGwVlanL2Description      TItemDescription,
        tmnxWlanGwVlanIdleTimeoutAction  TmnxWlanGwVlanIdleTimeoutAction
    }
    
tmnxWlanGwVlanTagStart OBJECT-TYPE
    SYNTAX      Unsigned32 (0..4095|4096)
    MAX-ACCESS  not-accessible
    STATUS      current
    DESCRIPTION
        "The value of the object tmnxWlanGwVlanTagStart specifies
         the start VLAN tag of this range."
    ::= { tmnxWlanGwVlanEntry 1 }

tmnxWlanGwVlanTagEnd OBJECT-TYPE
    SYNTAX      Unsigned32 (0..4095|4096)
    MAX-ACCESS  not-accessible
    STATUS      current
    DESCRIPTION
        "The value of the object tmnxWlanGwVlanTagEnd specifies
         the end VLAN tag of this range."
    ::= { tmnxWlanGwVlanEntry 2 }

tmnxWlanGwVlanRowStatus OBJECT-TYPE
    SYNTAX      RowStatus
    MAX-ACCESS  read-create
    STATUS      current
    DESCRIPTION
       "The value of tmnxWlanGwVlanRowStatus specifies 
        the row status of this row."
    ::= { tmnxWlanGwVlanEntry 3 }

tmnxWlanGwVlanLastCh OBJECT-TYPE
    SYNTAX      TimeStamp
    MAX-ACCESS  read-only
    STATUS      current
    DESCRIPTION
        "The value of tmnxWlanGwVlanLastCh indicates the sysUpTime at
         the time of the most recent management-initiated change to this
         table row."
    ::= { tmnxWlanGwVlanEntry 4 }

tmnxWlanGwVlanRetailService OBJECT-TYPE
    SYNTAX      TmnxServId
    MAX-ACCESS  read-create
    STATUS      current
    DESCRIPTION
       "The value of tmnxWlanGwVlanRetailService specifies 
        the identifier of the retail service associated with this range.
        
        The value zero means that no retail service is associated
        with this range."
    DEFVAL { 0 }
    ::= { tmnxWlanGwVlanEntry 5 }

tmnxWlanGwVlanDhcp OBJECT-TYPE
    SYNTAX      TmnxEnabledDisabled
    MAX-ACCESS  read-create
    STATUS      current
    DESCRIPTION
        "The value of tmnxWlanGwVlanDhcp specifies
         the administrative state of the DHCP protocol distributed
         on the ISA cards for the matching UE.
         
         While the value of the object tmnxWlanGwVlanDhcp is 
         equal to 'enabled', the distributed DHCP will reply to DHCP Request messages
         coming from UE without a corresponding subscriber known to this system." 
    DEFVAL { disabled } 
    ::= { tmnxWlanGwVlanEntry 6 }

tmnxWlanGwVlanAddrType OBJECT-TYPE
    SYNTAX      InetAddressType
    MAX-ACCESS  read-create
    STATUS      current
    DESCRIPTION
        "The value of tmnxWlanGwVlanAddrType specifies the type of
         address stored in tmnxWlanGwVlanAddr."
    DEFVAL { unknown }
    ::= { tmnxWlanGwVlanEntry 7 }

tmnxWlanGwVlanAddr OBJECT-TYPE
    SYNTAX      InetAddress (SIZE(0|4|16))
    MAX-ACCESS  read-create
    STATUS      current
    DESCRIPTION
        "The value of tmnxWlanGwVlanAddr specifies the IP address
         to be given before authentication to the User Equipment as 'yiaddr'
         in DHCP OFFER and DHCP ACK messages.
         
         The same IP address can be given to multiple UE because the user traffic
         is tunneled and this WLAN Gateway is layer-2-aware.
         
         The virtual router instance corresponding to the service with ID 'svcId'
         must have a row in the TIMETRA-NAT-MIB::tmnxNatL2AwAddrTable,
         such that the value of tmnxWlanGwVlanAddr matches that address prefix
         but is not equal to the value of TIMETRA-NAT-MIB::tmnxNatL2AwAddr."
    DEFVAL { ''H }  
    ::= { tmnxWlanGwVlanEntry 8 }

tmnxWlanGwVlanLeaseTime OBJECT-TYPE
    SYNTAX      Unsigned32 (300..3600)
    UNITS       "seconds"
    MAX-ACCESS  read-create
    STATUS      current
    DESCRIPTION
        "The value of tmnxWlanGwVlanLeaseTime specifies the IP address lease time
         to be given before authentication User Equipment in DHCP OFFER 
         and DHCP ACK messages."
    DEFVAL { 600 }  
    ::= { tmnxWlanGwVlanEntry 9 }

tmnxWlanGwVlanActLeaseTime OBJECT-TYPE
    SYNTAX      Unsigned32 (300..3600)
    UNITS       "seconds"
    MAX-ACCESS  read-create
    STATUS      current
    DESCRIPTION
        "The value of tmnxWlanGwVlanActLeaseTime specifies the IP address lease time
         to be given to the User Equipment in DHCP OFFER 
         and DHCP ACK messages, while the UE is in active state."
    DEFVAL { 600 }  
    ::= { tmnxWlanGwVlanEntry 10 }

tmnxWlanGwVlanDns1AddrType OBJECT-TYPE
    SYNTAX      InetAddressType
    MAX-ACCESS  read-create
    STATUS      current
    DESCRIPTION
        "The value of tmnxWlanGwVlanDns1AddrType specifies
         the address type of tmnxWlanGwVlanDns1Addr."
    DEFVAL { unknown }
    ::= { tmnxWlanGwVlanEntry 11 }

tmnxWlanGwVlanDns1Addr OBJECT-TYPE
    SYNTAX      InetAddress (SIZE(0|4|16))
    MAX-ACCESS  read-create
    STATUS      current
    DESCRIPTION
        "The value of tmnxWlanGwVlanDns1Addr specifies
         the address of the primary DNS server to be given before authentication
         to the User Equipment in Option 6 of DHCP OFFER and DHCP ACK messages."
    REFERENCE
       "RFC 2132 DHCP Options and BOOTP Vendor Extensions, 
        section 3.8 Domain Name Server Option."
    DEFVAL { ''H }  
    ::= { tmnxWlanGwVlanEntry 12 }

tmnxWlanGwVlanDns2AddrType OBJECT-TYPE
    SYNTAX      InetAddressType
    MAX-ACCESS  read-create
    STATUS      current
    DESCRIPTION
        "The value of tmnxWlanGwVlanDns2AddrType specifies
         the address type of tmnxWlanGwVlanDns2Addr."
    DEFVAL { unknown }
    ::= { tmnxWlanGwVlanEntry 13 }

tmnxWlanGwVlanDns2Addr OBJECT-TYPE
    SYNTAX      InetAddress (SIZE(0|4|16))
    MAX-ACCESS  read-create
    STATUS      current
    DESCRIPTION
        "The value of tmnxWlanGwVlanDns2Addr specifies
         the address of the secondary DNS server to be given before authentication
         to the User Equipment in Option 6 of DHCP OFFER and DHCP ACK messages."
    REFERENCE
       "RFC 2132 DHCP Options and BOOTP Vendor Extensions, 
        section 3.8 Domain Name Server Option."
    DEFVAL { ''H }  
    ::= { tmnxWlanGwVlanEntry 14 }

tmnxWlanGwVlanNb1AddrType OBJECT-TYPE
    SYNTAX      InetAddressType
    MAX-ACCESS  read-create
    STATUS      current
    DESCRIPTION
        "The value of tmnxWlanGwVlanNb1AddrType specifies
         the address type of tmnxWlanGwVlanNb1Addr."
    DEFVAL { unknown }
    ::= { tmnxWlanGwVlanEntry 15 }

tmnxWlanGwVlanNb1Addr OBJECT-TYPE
    SYNTAX      InetAddress (SIZE(0|4|16))
    MAX-ACCESS  read-create
    STATUS      current
    DESCRIPTION
        "The value of tmnxWlanGwVlanNb1Addr specifies
         the address of the primary NBNS server to be given before authentication
         to the User Equipment in Option 44 of DHCP OFFER and DHCP ACK messages."
    REFERENCE
       "RFC 2132 DHCP Options and BOOTP Vendor Extensions, 
        section 8.5. Net BIOS over TCP/IP Name Server Option."
    DEFVAL { ''H }  
    ::= { tmnxWlanGwVlanEntry 16 }

tmnxWlanGwVlanNb2AddrType OBJECT-TYPE
    SYNTAX      InetAddressType
    MAX-ACCESS  read-create
    STATUS      current
    DESCRIPTION
        "The value of tmnxWlanGwVlanNb2AddrType specifies
         the address type of tmnxWlanGwVlanNb2Addr."
    DEFVAL { unknown }
    ::= { tmnxWlanGwVlanEntry 17 }

tmnxWlanGwVlanNb2Addr OBJECT-TYPE
    SYNTAX      InetAddress (SIZE(0|4|16))
    MAX-ACCESS  read-create
    STATUS      current
    DESCRIPTION
        "The value of tmnxWlanGwVlanNb2Addr specifies
         the address of the secondary NBNS server to be given before authentication
         to the User Equipment in Option 44 of DHCP OFFER and DHCP ACK messages."
    REFERENCE
       "RFC 2132 DHCP Options and BOOTP Vendor Extensions, 
        section 8.5. Net BIOS over TCP/IP Name Server Option."
    DEFVAL { ''H }  
    ::= { tmnxWlanGwVlanEntry 18 }
    
tmnxWlanGwVlanHttpRdrPlcy OBJECT-TYPE
    SYNTAX      TNamedItemOrEmpty
    MAX-ACCESS  read-create
    STATUS      current
    DESCRIPTION
        "The value of tmnxWlanGwVlanHttpRdrPlcy specifies the identifier
         of the HTTP redirect policy for UE before authentication.
         
         HTTP redirect is triggered per subscriber during
         the authentication phase, by the presence of certain vendor-
         specific attributes in the RADIUS Access-Accept message
        (Alc-Wifi-Portal-Redirect or Alc-Wifi-Portal-Url).
         
         A row with the same name must exist 
         in the TIMETRA-SUBSCRIBER-MGMT-MIB::tmnxSubHttpRdrPlcyTable."
    DEFVAL { "" }
    ::= { tmnxWlanGwVlanEntry 21 }
    
tmnxWlanGwVlanNatPlcy OBJECT-TYPE
    SYNTAX      TNamedItemOrEmpty
    MAX-ACCESS  read-create
    STATUS      current
    DESCRIPTION
        "The value of tmnxWlanGwVlanNatPlcy specifies the identifier
         of the NAT policy for UE before authentication.
         
         Layer-2-Aware NAT hosts are temporarily created if UE are authenticated
         by a web portal.
         
         A row with the same name must exist in the TIMETRA-NAT-MIB::tmnxNatPlcyTable."
    DEFVAL { "" }
    ::= { tmnxWlanGwVlanEntry 22 }
    
tmnxWlanGwVlanDataTrigg OBJECT-TYPE
    SYNTAX      TmnxEnabledDisabled
    MAX-ACCESS  read-create
    STATUS      current
    DESCRIPTION
        "The value of tmnxWlanGwVlanDataTrigg specifies
         the administrative state of data-triggered authentication for the UE.
         
         While the value of the object tmnxWlanGwVlanDataTrigg is 
         equal to 'enabled', the system will start the authentication procedure
         upon receiving Layer 3 messages coming from unknown UE." 
    DEFVAL { disabled } 
    ::= { tmnxWlanGwVlanEntry 30 }

tmnxWlanGwVlanAuthPlcy OBJECT-TYPE
    SYNTAX      TNamedItemOrEmpty
    MAX-ACCESS  read-create
    STATUS      current
    DESCRIPTION
        "The value of tmnxWlanGwVlanAuthPlcy specifies the identifier
         of the authentication policy for UE.
         
         The authentication procedure is triggered by any Layer 3 packet other
         than a DHCP message.
         
         An entry with the same name must exist 
         in the TIMETRA-RADIUS-MIB::tmnxRadIsaPlcyTable."
    DEFVAL { "" }
    ::= { tmnxWlanGwVlanEntry 31 }
    
tmnxWlanGwVlanAuthHoldTime OBJECT-TYPE
    SYNTAX      Unsigned32 (0..3600)
    UNITS       "seconds"
    MAX-ACCESS  read-create
    STATUS      current
    DESCRIPTION
        "The value of tmnxWlanGwVlanAuthHoldTime specifies
         the minimum time that a User Equipment will be held 
         down after a failed authentication attempt.
         
         The hold time is used to prevent overwhelming the RADIUS servers
         with access request messages."
    DEFVAL { 5 }
    ::= { tmnxWlanGwVlanEntry 32 }
    
tmnxWlanGwVlanRadProxVrtr OBJECT-TYPE
    SYNTAX      TmnxVRtrIDOrZero
    MAX-ACCESS  read-create
    STATUS      current
    DESCRIPTION
        "The value of tmnxWlanGwVlanRadProxVrtr specifies the identifier
         of the virtual router instance of the RADIUS Proxy server. 
         
         The system can learn authentication information about UE that use a closed-SSID
         from the RADIUS Proxy server.
         
         The value zero specifies that there is no RADIUS Proxy server associated
         with this VLAN range for this purpose.
                 
         Non-zero/non-empty values of tmnxWlanGwVlanRadProxVrtr 
         and tmnxWlanGwVlanRadProxSrv must refer to a row in 
         the TIMETRA-RADIUS-MIB::tmnxRadProxSrvTable."
    DEFVAL { 0 }
    ::= { tmnxWlanGwVlanEntry 34 }

tmnxWlanGwVlanRadProxSrv OBJECT-TYPE
    SYNTAX      TNamedItemOrEmpty
    MAX-ACCESS  read-create
    STATUS      current
    DESCRIPTION
        "The value of tmnxWlanGwVlanRadProxSrv specifies the name
         of the RADIUS Proxy server.
         
         The system can learn authentication information about UE that use a closed-SSID
         from the RADIUS Proxy server.
         
         The empty string specifies that there is no RADIUS Proxy server
         associated with this VLAN range for this purpose.
         
         Non-zero/non-empty values of tmnxWlanGwVlanRadProxVrtr 
         and tmnxWlanGwVlanRadProxSrv must refer to a row in 
         the TIMETRA-RADIUS-MIB::tmnxRadProxSrvTable."
    DEFVAL { "" }
    ::= { tmnxWlanGwVlanEntry 35 }
    
tmnxWlanGwVlanRadProxMacFmt OBJECT-TYPE
    SYNTAX      TmnxMacSpecification (SIZE (2..7))
    MAX-ACCESS  read-create
    STATUS      current
    DESCRIPTION
        "The value of tmnxWlanGwVlanRadProxMacFmt specifies how a MAC
         address is represented by the RADIUS Proxy server.
         
         The value of tmnxWlanGwVlanRadProxMacFmt is only relevant while
         also non-zero/non-empty values for tmnxWlanGwVlanRadProxVrtr 
         and tmnxWlanGwVlanRadProxSrv are specified.         
                     
         Examples:
         
         'ab:'               00:0c:f1:99:85:b8  Nokia SROS style
         'XY-'               00-0C-F1-99-85-B8  IEEE canonical style 
         'mmmm.'             0002.03aa.abff     Cisco style."
    DEFVAL { "aa:" }
    ::= { tmnxWlanGwVlanEntry 36 }

tmnxWlanGwVlanAuthOnDhcp OBJECT-TYPE
    SYNTAX      TmnxEnabledDisabled
    MAX-ACCESS  read-create
    STATUS      current
    DESCRIPTION
        "The value of tmnxWlanGwVlanAuthOnDhcp specifies
         the administrative state of DHCP-triggered authentication for the UE.
         
         While the value of the object tmnxWlanGwVlanAuthOnDhcp is 
         equal to 'enabled', the system will start the authentication procedure
         upon receiving DHCP messages coming from unknown UE." 
    DEFVAL { disabled } 
    ::= { tmnxWlanGwVlanEntry 40 }

tmnxWlanGwVlanL2Service OBJECT-TYPE
    SYNTAX      TmnxServId
    MAX-ACCESS  read-create
    STATUS      current
    DESCRIPTION
       "The value of tmnxWlanGwVlanL2Service specifies
        the identifier of the layer 2 service associated with this range.
        All traffic in this vlan range will terminate in the associated
        layer 2 service instead of the parent service of this group
        interface.
 
        The value zero means that no layer 2 service is associated
        with this range."
    DEFVAL { 0 }
    ::= { tmnxWlanGwVlanEntry 41 }
    
tmnxWlanGwVlanL2AdminState OBJECT-TYPE
    SYNTAX      TmnxEnabledDisabled
    MAX-ACCESS  read-create
    STATUS      current
    DESCRIPTION
       "The value of tmnxWlanGwVlanL2AdminState specifies the
        administrative state of the layer 2 service."
    DEFVAL { disabled }
    ::= { tmnxWlanGwVlanEntry 42 }
    
tmnxWlanGwVlanL2Description OBJECT-TYPE
    SYNTAX      TItemDescription
    MAX-ACCESS  read-create
    STATUS      current
    DESCRIPTION
       "The value of tmnxWlanGwVlanL2Description specifies the 
        user provided description of the layer 2 service."
    DEFVAL { "" }
    ::= { tmnxWlanGwVlanEntry 43 }    

tmnxWlanGwVlanIdleTimeoutAction OBJECT-TYPE
    SYNTAX      TmnxWlanGwVlanIdleTimeoutAction
    MAX-ACCESS  read-create
    STATUS      current
    DESCRIPTION
       "The value of tmnxWlanGwVlanIdleTimeoutAction specifies the 
        action to be performed when the idle-timeout timer goes off.
        Idle-timeout is activated by RADIUS and is on by default
        for SLAAC."
    DEFVAL { remove }
    ::= { tmnxWlanGwVlanEntry 44 }

--
--      WLAN GW VLAN Range DHCPv6 Table
--

tmnxWlanGwVlanDhcp6Table OBJECT-TYPE
    SYNTAX      SEQUENCE OF TmnxWlanGwVlanDhcp6Entry
    MAX-ACCESS  not-accessible
    STATUS      current
    DESCRIPTION
       "The tmnxWlanGwVlanDhcp6Table contains objects to configure
        the DHCPv6 configuration data for WLAN GW VLAN ranges."
    ::= { tmnxWlanGwVlanSubObjs 2 }

tmnxWlanGwVlanDhcp6Entry OBJECT-TYPE
    SYNTAX      TmnxWlanGwVlanDhcp6Entry
    MAX-ACCESS  not-accessible
    STATUS      current
    DESCRIPTION
        "Each conceptual row represents the set of DHCPv6
         configuration data for a range of VLAN Q-tags."
    AUGMENTS {tmnxWlanGwVlanEntry}
    ::= { tmnxWlanGwVlanDhcp6Table 1 }

TmnxWlanGwVlanDhcp6Entry ::= 
    SEQUENCE {
        tmnxWlanGwVlanDhcp6LastChanged    TimeStamp,
        tmnxWlanGwVlanDhcp6InitPrefLt     Unsigned32,
        tmnxWlanGwVlanDhcp6ActPrefLt      Unsigned32,
        tmnxWlanGwVlanDhcp6InitValidLt    Unsigned32,
        tmnxWlanGwVlanDhcp6ActValidLt     Unsigned32,
        tmnxWlanGwVlanDhcp6AdminState     TmnxEnabledDisabled
    }  

tmnxWlanGwVlanDhcp6LastChanged OBJECT-TYPE
    SYNTAX      TimeStamp
    MAX-ACCESS  read-only
    STATUS      current
    DESCRIPTION
        "The value of tmnxWlanGwVlanDhcp6LastChanged indicates the time
         of the most recent management-initiated change."
    ::= { tmnxWlanGwVlanDhcp6Entry 1 }
    
tmnxWlanGwVlanDhcp6InitPrefLt OBJECT-TYPE
    SYNTAX      Unsigned32 (300..3600)
    UNITS       "seconds"
    MAX-ACCESS  read-create
    STATUS      current
    DESCRIPTION
        "The value of tmnxWlanGwVlanDhcp6InitPrefLt specifies the
         signaled preferred lifetime in DHCPv6 during migrant phase."
    DEFVAL { 300 }  
    ::= { tmnxWlanGwVlanDhcp6Entry 2 }
    
tmnxWlanGwVlanDhcp6ActPrefLt OBJECT-TYPE
    SYNTAX      Unsigned32 (300..3600)
    UNITS       "seconds"
    MAX-ACCESS  read-create
    STATUS      current
    DESCRIPTION
        "The value of tmnxWlanGwVlanDhcp6ActPrefLt specifies the
         signaled preferred lifetime in DHCPv6 after full authentication.
         (DSM and/or ESM)"
    DEFVAL { 600 }  
    ::= { tmnxWlanGwVlanDhcp6Entry 3 }
    
tmnxWlanGwVlanDhcp6InitValidLt OBJECT-TYPE
    SYNTAX      Unsigned32 (300..3600)
    UNITS       "seconds"
    MAX-ACCESS  read-create
    STATUS      current
    DESCRIPTION
        "The value of tmnxWlanGwVlanDhcp6InitValidLt specifies the
         signaled valid lifetime in DHCPv6 during migrant phase."
    DEFVAL { 300 }  
    ::= { tmnxWlanGwVlanDhcp6Entry 4 }
    
tmnxWlanGwVlanDhcp6ActValidLt OBJECT-TYPE
    SYNTAX      Unsigned32 (300..3600)
    UNITS       "seconds"
    MAX-ACCESS  read-create
    STATUS      current
    DESCRIPTION
        "The value of tmnxWlanGwVlanDhcp6ActValidLt specifies the
         signaled valid lifetime in DHCPv6 after full authentication.
         (DSM and/or ESM)"
    DEFVAL { 600 }  
    ::= { tmnxWlanGwVlanDhcp6Entry 5 }
    
tmnxWlanGwVlanDhcp6AdminState OBJECT-TYPE
    SYNTAX      TmnxEnabledDisabled
    MAX-ACCESS  read-create
    STATUS      current
    DESCRIPTION
       "The value of tmnxWlanGwVlanDhcp6AdminState specifies the
        administrative state of the DHCPv6 client."
    DEFVAL { disabled }
    ::= { tmnxWlanGwVlanDhcp6Entry 6 }
    

--
--      WLAN GW VLAN Range SLAAC Table
--

tmnxWlanGwVlanSlaacTable OBJECT-TYPE
    SYNTAX      SEQUENCE OF TmnxWlanGwVlanSlaacEntry
    MAX-ACCESS  not-accessible
    STATUS      current
    DESCRIPTION
       "The tmnxWlanGwVlanSlaacTable contains objects to configure
        the SLAAC configuration data for WLAN GW VLAN ranges."
    ::= { tmnxWlanGwVlanSubObjs 3 }

tmnxWlanGwVlanSlaacEntry OBJECT-TYPE
    SYNTAX      TmnxWlanGwVlanSlaacEntry
    MAX-ACCESS  not-accessible
    STATUS      current
    DESCRIPTION
        "Each conceptual row represents the set of SLAAC
         configuration data for a range of VLAN Q-tags."
    AUGMENTS {tmnxWlanGwVlanEntry}
    ::= { tmnxWlanGwVlanSlaacTable 1 }

TmnxWlanGwVlanSlaacEntry ::= 
    SEQUENCE {
        tmnxWlanGwVlanSlaacLastChanged    TimeStamp,
        tmnxWlanGwVlanSlaacInitPrefLt     Unsigned32,
        tmnxWlanGwVlanSlaacActPrefLt      Unsigned32,
        tmnxWlanGwVlanSlaacInitValidLt    Unsigned32,
        tmnxWlanGwVlanSlaacActValidLt     Unsigned32,
        tmnxWlanGwVlanSlaacAdminState     TmnxEnabledDisabled
    }  

tmnxWlanGwVlanSlaacLastChanged OBJECT-TYPE
    SYNTAX      TimeStamp
    MAX-ACCESS  read-only
    STATUS      current
    DESCRIPTION
        "The value of tmnxWlanGwVlanSlaacLastChanged indicates the time
         of the most recent management-initiated change."
    ::= { tmnxWlanGwVlanSlaacEntry 1 }
    
tmnxWlanGwVlanSlaacInitPrefLt OBJECT-TYPE
    SYNTAX      Unsigned32 (300..3600)
    UNITS       "seconds"
    MAX-ACCESS  read-create
    STATUS      current
    DESCRIPTION
        "The value of tmnxWlanGwVlanSlaacInitPrefLt specifies the
         signaled preferred lifetime in DHCPv6 during migrant phase."
    DEFVAL { 300 }  
    ::= { tmnxWlanGwVlanSlaacEntry 2 }
    
tmnxWlanGwVlanSlaacActPrefLt OBJECT-TYPE
    SYNTAX      Unsigned32 (300..3600)
    UNITS       "seconds"
    MAX-ACCESS  read-create
    STATUS      current
    DESCRIPTION
        "The value of tmnxWlanGwVlanSlaacActPrefLt specifies the
         signaled preferred lifetime in DHCPv6 after full authentication.
         (DSM and/or ESM)"
    DEFVAL { 600 }  
    ::= { tmnxWlanGwVlanSlaacEntry 3 }
    
tmnxWlanGwVlanSlaacInitValidLt OBJECT-TYPE
    SYNTAX      Unsigned32 (300..3600)
    UNITS       "seconds"
    MAX-ACCESS  read-create
    STATUS      current
    DESCRIPTION
        "The value of tmnxWlanGwVlanSlaacInitValidLt specifies the
         signaled valid lifetime in DHCPv6 during migrant phase."
    DEFVAL { 300 }  
    ::= { tmnxWlanGwVlanSlaacEntry 4 }
    
tmnxWlanGwVlanSlaacActValidLt OBJECT-TYPE
    SYNTAX      Unsigned32 (300..3600)
    UNITS       "seconds"
    MAX-ACCESS  read-create
    STATUS      current
    DESCRIPTION
        "The value of tmnxWlanGwVlanSlaacActValidLt specifies the
         signaled valid lifetime in DHCPv6 after full authentication.
         (DSM and/or ESM)"
    DEFVAL { 600 }  
    ::= { tmnxWlanGwVlanSlaacEntry 5 }
    
tmnxWlanGwVlanSlaacAdminState OBJECT-TYPE
    SYNTAX      TmnxEnabledDisabled
    MAX-ACCESS  read-create
    STATUS      current
    DESCRIPTION
       "The value of tmnxWlanGwVlanSlaacAdminState specifies the
        administrative state of the SLAAC client."
    DEFVAL { disabled }
    ::= { tmnxWlanGwVlanSlaacEntry 6 }
    

--
--      Subscriber Interface WLAN GW Table
--
--      A very sparse extension the TIMETRA-SERV-MIB::iesIfTable

tmnxWlanGwSubIfTable   OBJECT-TYPE
    SYNTAX      SEQUENCE OF TmnxWlanGwSubIfEntry
    MAX-ACCESS  not-accessible
    STATUS      current
    DESCRIPTION
       "The tmnxWlanGwSubIfTable contains objects to configure 
        WLAN Gateway functions for subscriber interfaces.
        
        These objects are useful only while the subscriber interface
        has Soft GRE Group-Interfaces configured.
        
        Entries in this table can be created and deleted via SNMP SET
        operations to tmnxWlanGwSubIfRowStatus."
    ::= { tmnxWlanGwSoftGreObjs 7 }

tmnxWlanGwSubIfEntry OBJECT-TYPE
    SYNTAX      TmnxWlanGwSubIfEntry
    MAX-ACCESS  not-accessible
    STATUS      current
    DESCRIPTION
       "Each conceptual row contains WLAN Gateway information 
        of a specific subscriber interface.
       
        Objects in this row are effective only while this subscriber interface
        has Soft GRE Group-Interfaces configured.
        
        Entries in this table can be created and deleted via SNMP SET
        operations to tmnxWlanGwSubIfRowStatus.
         
        A corresponding row in the TIMETRA-SERV-MIB::iesIfTable must exist
        in order to create a row in this table."
    INDEX { svcId, iesIfIndex }
    ::= { tmnxWlanGwSubIfTable 1 }

TmnxWlanGwSubIfEntry ::=
    SEQUENCE {
        tmnxWlanGwSubIfRowStatus         RowStatus,
        tmnxWlanGwSubIfLastCh            TimeStamp,
        tmnxWlanGwSubIfRedExpPrefixType  InetAddressType,
        tmnxWlanGwSubIfRedExpPrefix      InetAddress,
        tmnxWlanGwSubIfRedExpPrefixLen   InetAddressPrefixLength,
        tmnxWlanGwSubIfRedMonPrefixType  InetAddressType,
        tmnxWlanGwSubIfRedMonPrefix      InetAddress,
        tmnxWlanGwSubIfRedMonPrefixLen   InetAddressPrefixLength,
        tmnxWlanGwSubIfRedAdminState     TmnxEnabledDisabled,
        tmnxWlanGwSubIfRedActive         TruthValue,
        tmnxWlanGwSubIfRedSwitch         TmnxActionType        
    }

tmnxWlanGwSubIfRowStatus OBJECT-TYPE
    SYNTAX      RowStatus
    MAX-ACCESS  read-create
    STATUS      current
    DESCRIPTION
       "The value of tmnxWlanGwSubIfRowStatus specifies 
        the row status of this row."
    ::= { tmnxWlanGwSubIfEntry 1 }
    
tmnxWlanGwSubIfLastCh OBJECT-TYPE
    SYNTAX      TimeStamp
    MAX-ACCESS  read-only
    STATUS      current
    DESCRIPTION
        "The value of tmnxWlanGwSubIfLastCh indicates the sysUpTime at
         the time of the most recent management-initiated change to this
         table row."
    ::= { tmnxWlanGwSubIfEntry 2 }

tmnxWlanGwSubIfRedExpPrefixType OBJECT-TYPE
    SYNTAX      InetAddressType
    MAX-ACCESS  read-create
    STATUS      current
    DESCRIPTION 
        "The value of tmnxWlanGwSubIfRedExpPrefixType specifies
         the address type of tmnxWlanGwSubIfRedExpPrefix."
    DEFVAL { unknown }
    ::= { tmnxWlanGwSubIfEntry 3 }

tmnxWlanGwSubIfRedExpPrefix OBJECT-TYPE
    SYNTAX      InetAddress (SIZE(0|4|16))
    MAX-ACCESS  read-create
    STATUS      current
    DESCRIPTION 
        "The value of tmnxWlanGwSubIfRedExpPrefix specifies
         the IP address of the prefix to be exported.
         
         While the export prefix is configured and the value of the object
         tmnxWlanGwSubIfRedActive is equal to 'true', the system exports
         this prefix in the realm of the virtual router instance associated
         with this service; to the WLAN Gateway redundancy peer, 
         the presence of this prefix is an indication that the WLAN Gateway function 
         in this virtual router instance is active; hence, 
         the export prefix of this system 
         is the monitor prefix of the peer.
         
         The export prefix must be different from the monitor prefix."
    DEFVAL { ''H }  
    ::= { tmnxWlanGwSubIfEntry 4 }

tmnxWlanGwSubIfRedExpPrefixLen OBJECT-TYPE
    SYNTAX      InetAddressPrefixLength (0..128)
    MAX-ACCESS  read-create
    STATUS      current
    DESCRIPTION 
        "The value of tmnxWlanGwSubIfRedExpPrefixLen specifies
         the prefix length of the prefix to be exported."
    DEFVAL { 0 }
    ::= { tmnxWlanGwSubIfEntry 5 }

tmnxWlanGwSubIfRedMonPrefixType OBJECT-TYPE
    SYNTAX      InetAddressType
    MAX-ACCESS  read-create
    STATUS      current
    DESCRIPTION 
        "The value of tmnxWlanGwSubIfRedMonPrefixType specifies
         the address type of tmnxWlanGwSubIfRedMonPrefix."
    DEFVAL { unknown }
    ::= { tmnxWlanGwSubIfEntry 6 }

tmnxWlanGwSubIfRedMonPrefix OBJECT-TYPE
    SYNTAX      InetAddress (SIZE(0|4|16))
    MAX-ACCESS  read-create
    STATUS      current
    DESCRIPTION 
        "The value of tmnxWlanGwSubIfRedMonPrefix specifies
         the IP address of the prefix to be monitored.
         
         While the monitor prefix is configured, the system monitors the
         presence of this prefix in the routing table of the virtual router
         instance associated with this service; the presence of this prefix 
         is an indication that the WLAN Gateway redundancy peer is active; 
         the monitor prefix of this system is the export prefix of the peer.
         
         The monitor prefix must be different from the export prefix."
    DEFVAL { ''H }  
    ::= { tmnxWlanGwSubIfEntry 7 }

tmnxWlanGwSubIfRedMonPrefixLen OBJECT-TYPE
    SYNTAX      InetAddressPrefixLength (0..128)
    MAX-ACCESS  read-create
    STATUS      current
    DESCRIPTION 
        "The value of tmnxWlanGwSubIfRedMonPrefixLen specifies
         the prefix length of the prefix to be monitored."
    DEFVAL { 0 }
    ::= { tmnxWlanGwSubIfEntry 8 }

tmnxWlanGwSubIfRedAdminState  OBJECT-TYPE
    SYNTAX      TmnxEnabledDisabled 
    MAX-ACCESS  read-create
    STATUS      current
    DESCRIPTION
        "The value of tmnxWlanGwSubIfRedAdminState specifies 
         the administrative state of dual homing redundancy
         for this subscriber interface."
    DEFVAL { disabled }
        ::= { tmnxWlanGwSubIfEntry 9 }

tmnxWlanGwSubIfRedActive  OBJECT-TYPE
    SYNTAX      TruthValue 
    MAX-ACCESS  read-only
    STATUS      current
    DESCRIPTION
        "The value of tmnxWlanGwSubIfRedActive indicates 
         if this system is actively performing the WLAN Gateway function
         for this subscriber interface."
    ::= { tmnxWlanGwSubIfEntry 10 }

tmnxWlanGwSubIfRedSwitch  OBJECT-TYPE
    SYNTAX      TmnxActionType 
    MAX-ACCESS  read-create
    STATUS      current
    DESCRIPTION
        "Setting this object to 'doAction' triggers an attempt to
         switch WLAN Gateway service to the standby system for the
         UE associated with this subscriber interface.
         
         This is only allowed while the value of tmnxWlanGwSubIfRedActive
         is equal to 'true'.
                 
         An SNMP GET request on this object returns 'notApplicable'."
    DEFVAL { notApplicable }
    ::= { tmnxWlanGwSubIfEntry 11 }


--
-- The Layer 2 Access Point Table
--

tmnxWlanGwL2ApTable OBJECT-TYPE
    SYNTAX      SEQUENCE OF TmnxWlanGwL2ApEntry
    MAX-ACCESS  not-accessible
    STATUS      current
    DESCRIPTION
       "The tmnxWlanGwL2ApTable contains objects to configure
        Layer 2 Access Points in WLAN Gateway Group-Interfaces."
    ::= { tmnxWlanGwSoftGreObjs 8 }

tmnxWlanGwL2ApEntry OBJECT-TYPE
    SYNTAX      TmnxWlanGwL2ApEntry
    MAX-ACCESS  not-accessible
    STATUS      current
    DESCRIPTION
        "Each conceptual row represents the set of configuration data
         for a Layer 2 Access Point on a particular WLAN Gateway Group-Interface.
         
         Rows in this table are created and destroyed by means of SNMP
         operations on the tmnxWlanGwVlanRowStatus object.
         
         A row with the same values for svcId and iesIfIndex must exist
         in the tmnxWlanGwSoftGreIfTable.

         While a conceptual row in this table exists, a row with the same values 
         for sapPortId and sapEncapValue can not be created in the TIMETRA-SAP-MIB::sapBaseInfoTable."
    INDEX { svcId, iesIfIndex,
            sapPortId, sapEncapValue
          }
    ::= { tmnxWlanGwL2ApTable 1 }

TmnxWlanGwL2ApEntry ::= 
    SEQUENCE {
        tmnxWlanGwL2ApRowStatus          RowStatus,
        tmnxWlanGwL2ApLastCh             TimeStamp,
        tmnxWlanGwL2ApAdminState         TmnxEnabledDisabled,
        tmnxWlanGwL2ApEncapType          INTEGER,
        tmnxWlanGwL2ApEpipeSapTemplate   TNamedItemOrEmpty,
        tmnxWlanGwL2ApId                 Unsigned32 
    }
    
tmnxWlanGwL2ApRowStatus OBJECT-TYPE
    SYNTAX      RowStatus
    MAX-ACCESS  read-create
    STATUS      current
    DESCRIPTION
       "The value of tmnxWlanGwL2ApRowStatus specifies 
        the row status of this row."
    ::= { tmnxWlanGwL2ApEntry 1 }

tmnxWlanGwL2ApLastCh OBJECT-TYPE
    SYNTAX      TimeStamp
    MAX-ACCESS  read-only
    STATUS      current
    DESCRIPTION
        "The value of tmnxWlanGwL2ApLastCh indicates the sysUpTime at
         the time of the most recent management-initiated change to this
         table row."
    ::= { tmnxWlanGwL2ApEntry 2 }
   
tmnxWlanGwL2ApAdminState OBJECT-TYPE
    SYNTAX      TmnxEnabledDisabled
    MAX-ACCESS  read-create
    STATUS      current
    DESCRIPTION
        "The value of tmnxWlanGwL2ApAdminState specifies 
         the administrative status of this row.

         While the value of tmnxWlanGwL2ApAdminState is equal to 'enabled', a row with the same values 
         for sapPortId and sapEncapValue is present in the TIMETRA-SAP-MIB::sapBaseInfoTable."
    DEFVAL { disabled }
::= { tmnxWlanGwL2ApEntry 3 }

tmnxWlanGwL2ApEncapType OBJECT-TYPE
    SYNTAX      INTEGER {
                    default (0),
                    null (1),
                    dot1q (2),
                    qinq (10)
                }
    MAX-ACCESS  read-create
    STATUS      current
    DESCRIPTION     
        "The value of tmnxWlanGwL2ApEncapType specifies
         the service encapsulation type of this access point.
         
         The value 'default' specifies that the default value
         for this interface be used: tmnxWlanGwSoftGreIfL2ApEncapType."
    DEFVAL { default }
    ::= { tmnxWlanGwL2ApEntry 4 }

tmnxWlanGwL2ApEpipeSapTemplate OBJECT-TYPE
    SYNTAX      TNamedItemOrEmpty
    MAX-ACCESS  read-create
    STATUS      current
    DESCRIPTION     
        "The value of tmnxWlanGwL2ApEpipeSapTemplate specifies
         the template to configure the parameters of
         the internal connections with the ISA cards.
         
         A non empty value must correspond to a row in the
         TIMETRA-SERV-MIB::sapTmplTable where the value of
         the object sapTmplType is equal to 'epipe'."
    DEFVAL { "" }
    ::= { tmnxWlanGwL2ApEntry 5 }

tmnxWlanGwL2ApId OBJECT-TYPE
    SYNTAX      Unsigned32
    MAX-ACCESS  read-only
    STATUS      current
    DESCRIPTION     
        "The value of tmnxWlanGwL2ApId indicates
         the unique identifier of this conceptual row.
         
         It may be used as NAS-Port-Id."
    ::= { tmnxWlanGwL2ApEntry 6 }

--
--      WLAN GW Subscriber Interface Pool Manager Table
--

tmnxWlanGwSubIfPmTable OBJECT-TYPE
    SYNTAX      SEQUENCE OF TmnxWlanGwSubIfPmEntry
    MAX-ACCESS  not-accessible
    STATUS      current
    DESCRIPTION
       "The tmnxWlanGwSubIfPmTable contains objects to configure
        the pool manager for WLAN GW subscriber interfaces."
    ::= { tmnxWlanGwSoftGreObjs 9 }

tmnxWlanGwSubIfPmEntry OBJECT-TYPE
    SYNTAX      TmnxWlanGwSubIfPmEntry
    MAX-ACCESS  not-accessible
    STATUS      current
    DESCRIPTION
        "Each conceptual row represents the set of pool manager
         configuration data for a WLAN GW subscriber interface."
    AUGMENTS { tmnxWlanGwSubIfEntry }
    ::= { tmnxWlanGwSubIfPmTable 1 }

TmnxWlanGwSubIfPmEntry ::= 
    SEQUENCE {
        tmnxWlanGwSubIfPmLastChanged      TimeStamp,
        tmnxWlanGwSubIfPmWatermarkHigh    Unsigned32,
        tmnxWlanGwSubIfPmWatermarkLow     Unsigned32,
        tmnxWlanGwSubIfPmWlanGwGroup      TmnxWlanGwIsaGrpIdOrZero,
        tmnxWlanGwSubIfPmD6cServer1       InetAddressIPv6,
        tmnxWlanGwSubIfPmD6cServer2       InetAddressIPv6,
        tmnxWlanGwSubIfPmD6cServer3       InetAddressIPv6,
        tmnxWlanGwSubIfPmD6cServer4       InetAddressIPv6,
        tmnxWlanGwSubIfPmD6cServer5       InetAddressIPv6,
        tmnxWlanGwSubIfPmD6cServer6       InetAddressIPv6,
        tmnxWlanGwSubIfPmD6cServer7       InetAddressIPv6,
        tmnxWlanGwSubIfPmD6cServer8       InetAddressIPv6,
        tmnxWlanGwSubIfPmD6cLeaseQuery    TmnxEnabledDisabled,
        tmnxWlanGwSubIfPmD6cLeaseQueryMR  Unsigned32,
        tmnxWlanGwSubIfPmD6cSourceIp      InetAddressIPv6,
        tmnxWlanGwSubIfPmD6cSlaacPoolNm   TNamedItemOrEmpty,
        tmnxWlanGwSubIfPmD6cSlaacLinkAdd  InetAddressIPv6,
        tmnxWlanGwSubIfPmD6cSlaacAdminSt  TmnxAdminState,
        tmnxWlanGwSubIfPmD6cIaNaPoolNm    TNamedItemOrEmpty,
        tmnxWlanGwSubIfPmD6cIaNaLinkAdd   InetAddressIPv6,
        tmnxWlanGwSubIfPmD6cIaNaAdminSt   TmnxAdminState
    }  

tmnxWlanGwSubIfPmLastChanged OBJECT-TYPE
    SYNTAX      TimeStamp
    MAX-ACCESS  read-only
    STATUS      current
    DESCRIPTION
        "The value of tmnxWlanGwSubIfPmLastChanged indicates the time
         of the most recent management-initiated change."
    ::= { tmnxWlanGwSubIfPmEntry 1 }

tmnxWlanGwSubIfPmWatermarkHigh OBJECT-TYPE
    SYNTAX      Unsigned32 (51..99)
    MAX-ACCESS  read-create
    STATUS      current
    DESCRIPTION
        "The value of tmnxWlanGwSubIfPmWatermarkHigh specifies the
         high value of the watermarks used to determine if a new prefix
         should be allocated or an old prefix should be removed.
        
         A new prefix will be allocated when the total usage level
         for the ISA reaches the high watermark.
         
         A prefix will be freed if no addresses are currently in use
         and the usage level without this prefix would be below the
         low watermark.
         
         Values allowed for high watermark are [51..99].
         
         The 'no'-form of the corresponding CLI command resets the
         watermarks to its default values of 95% high and 90% low."
    DEFVAL { 95 }
    ::= { tmnxWlanGwSubIfPmEntry 2 }

tmnxWlanGwSubIfPmWatermarkLow OBJECT-TYPE
    SYNTAX      Unsigned32 (50..98)
    MAX-ACCESS  read-create
    STATUS      current
    DESCRIPTION
        "The value of tmnxWlanGwSubIfPmWatermarkLow specifies the
         low value of the watermarks used to determine if a new prefix
         should be allocated or an old prefix should be removed.
        
         A new prefix will be allocated when the total usage level
         for the ISA reaches the high watermark.
         
         A prefix will be freed if no addresses are currently in use
         and the usage level without this prefix would be below the
         low watermark. 

         Values allowed for low watermark are [50..98].

         The 'no'-form of the corresponding CLI command resets the
         watermarks to its default values of 95% high and 90% low."
    DEFVAL { 90 }
    ::= { tmnxWlanGwSubIfPmEntry 3 }
    
tmnxWlanGwSubIfPmWlanGwGroup OBJECT-TYPE
    SYNTAX      TmnxWlanGwIsaGrpIdOrZero
    MAX-ACCESS  read-create
    STATUS      current
    DESCRIPTION
        "The value of tmnxWlanGwSubIfPmWlanGwGroup specifies the identifier
         of the WLAN Gateway ISA group that terminates GRE for this group interface."
    DEFVAL { 0 }
    ::= { tmnxWlanGwSubIfPmEntry 4 }

tmnxWlanGwSubIfPmD6cServer1 OBJECT-TYPE
    SYNTAX      InetAddressIPv6
    MAX-ACCESS  read-create
    STATUS      current
    DESCRIPTION
        "The value of tmnxWlanGwSubIfPmD6cServer1 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 5 }

tmnxWlanGwSubIfPmD6cServer2 OBJECT-TYPE
    SYNTAX      InetAddressIPv6
    MAX-ACCESS  read-create
    STATUS      current
    DESCRIPTION
        "The value of tmnxWlanGwSubIfPmD6cServer2 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 6 }

tmnxWlanGwSubIfPmD6cServer3 OBJECT-TYPE
    SYNTAX      InetAddressIPv6
    MAX-ACCESS  read-create
    STATUS      current
    DESCRIPTION
        "The value of tmnxWlanGwSubIfPmD6cServer3 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 7 }

tmnxWlanGwSubIfPmD6cServer4 OBJECT-TYPE
    SYNTAX      InetAddressIPv6
    MAX-ACCESS  read-create
    STATUS      current
    DESCRIPTION
        "The value of tmnxWlanGwSubIfPmD6cServer4 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 8 }

tmnxWlanGwSubIfPmD6cServer5 OBJECT-TYPE
    SYNTAX      InetAddressIPv6
    MAX-ACCESS  read-create
    STATUS      current
    DESCRIPTION
        "The value of tmnxWlanGwSubIfPmD6cServer5 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 9 }

tmnxWlanGwSubIfPmD6cServer6 OBJECT-TYPE
    SYNTAX      InetAddressIPv6
    MAX-ACCESS  read-create
    STATUS      current
    DESCRIPTION
        "The value of tmnxWlanGwSubIfPmD6cServer6 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 10 }

tmnxWlanGwSubIfPmD6cServer7 OBJECT-TYPE
    SYNTAX      InetAddressIPv6
    MAX-ACCESS  read-create
    STATUS      current
    DESCRIPTION
        "The value of tmnxWlanGwSubIfPmD6cServer7 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 11 }

tmnxWlanGwSubIfPmD6cServer8 OBJECT-TYPE
    SYNTAX      InetAddressIPv6
    MAX-ACCESS  read-create
    STATUS      current
    DESCRIPTION
        "The value of tmnxWlanGwSubIfPmD6cServer8 specifies one fo the
         DHCPv6 servers that are used for requesting addresses.  Up to
         8 servers can be used simultaneously.
         
         The 'no'-form of the corresponding CLI command removes the server.
         This cannot be executed while the DHCPv6 server is not shutdown."
    DEFVAL { '00000000000000000000000000000000'H }
    ::= { tmnxWlanGwSubIfPmEntry 12 }

tmnxWlanGwSubIfPmD6cLeaseQuery OBJECT-TYPE
    SYNTAX      TmnxEnabledDisabled
    MAX-ACCESS  read-create
    STATUS      current
    DESCRIPTION
        "The value of tmnxWlanGwSubIfPmD6cLeaseQuery enables or
         disables lease-query.  If it is specified, the DHCPv6 client
         will retrieve any existing addresses when becoming active.
         The lease-query is performed for all of the configured servers.

         The 'no'-form of the corresponding CLI command disables lease-query."
    DEFVAL { disabled }
    ::= { tmnxWlanGwSubIfPmEntry 13 }

tmnxWlanGwSubIfPmD6cLeaseQueryMR OBJECT-TYPE
    SYNTAX      Unsigned32 (0..10)
    MAX-ACCESS  read-create
    STATUS      current
    DESCRIPTION
        "The value of tmnxWlanGwSubIfPmD6cLeaseQueryMR specifies
         the maximum number of retries before the lease query assumes
         no existing subnets were allocated.
         
         The maximum number of retries is 10 and the default value is 2."
    DEFVAL { 2 }
    ::= { tmnxWlanGwSubIfPmEntry 14 }

tmnxWlanGwSubIfPmD6cSourceIp OBJECT-TYPE
    SYNTAX      InetAddressIPv6
    MAX-ACCESS  read-create
    STATUS      current
    DESCRIPTION
        "The value of tmnxWlanGwSubIfPmD6cSourceIp specifies the source
         IP address to be used by the DHCPv6 client.

         The 'no'-form of the corresponding CLI command removes the specific
         source IP address. In this case, the DHCPv6 client will fall back
         to the IP address configured on the outgoing interface."
    DEFVAL { '00000000000000000000000000000000'H }
    ::= { tmnxWlanGwSubIfPmEntry 15 }

tmnxWlanGwSubIfPmD6cSlaacPoolNm OBJECT-TYPE
    SYNTAX      TNamedItemOrEmpty
    MAX-ACCESS  read-create
    STATUS      current
    DESCRIPTION
        "The value of tmnxWlanGwSubIfPmD6cSlaacPoolNm specifies the pool name
         for SLAAC that should be sent in the DHCPv6 messages. This will be
         reflected in the Nokia vendor specific pool option.
         (vendor-id 6527, option-id 0x02).

         The 'no'-form of the corresponding CLI command removes the pool-name
         and the option will not be sent in DHCPv6."
    DEFVAL { "" }
    ::= { tmnxWlanGwSubIfPmEntry 16 }
    
tmnxWlanGwSubIfPmD6cSlaacLinkAdd OBJECT-TYPE
    SYNTAX      InetAddressIPv6
    MAX-ACCESS  read-create
    STATUS      current
    DESCRIPTION
        "The value of tmnxWlanGwSubIfPmD6cSlaacLinkAdd specifies the IPv6-address
         for SLAAC that should be included in the link-address field of the relay
         header. This can be used for pool-selection by the DHCPv6 server.

         The 'no'-form of the corresponding CLI command sets the link-address to
         its default value '0::0'."
    DEFVAL { '00000000000000000000000000000000'H }
    ::= { tmnxWlanGwSubIfPmEntry 17 }

tmnxWlanGwSubIfPmD6cSlaacAdminSt  OBJECT-TYPE
    SYNTAX      TmnxAdminState 
    MAX-ACCESS  read-create
    STATUS      current
    DESCRIPTION
        "The value of tmnxWlanGwSubIfPmD6cSlaacAdminSt specifies the administrative
         state of the considered DHCPv6 client for SLAAC."
    DEFVAL { outOfService }
    ::= { tmnxWlanGwSubIfPmEntry 18 }

tmnxWlanGwSubIfPmD6cIaNaPoolNm OBJECT-TYPE
    SYNTAX      TNamedItemOrEmpty
    MAX-ACCESS  read-create
    STATUS      current
    DESCRIPTION
        "The value of tmnxWlanGwSubIfPmD6cIaNaPoolNm specifies the pool name
         for IA-NA that should be sent in the DHCPv6 messages. This will be
         reflected in the Nokia vendor specific pool option.
         (vendor-id 6527, option-id 0x02).

         The 'no'-form of of the corresponding CLI command removes pool-name
         and the option will not be sent in DHCPv6."
    DEFVAL { "" }
    ::= { tmnxWlanGwSubIfPmEntry 19 }
    
tmnxWlanGwSubIfPmD6cIaNaLinkAdd OBJECT-TYPE
    SYNTAX      InetAddressIPv6
    MAX-ACCESS  read-create
    STATUS      current
    DESCRIPTION
        "The value of tmnxWlanGwSubIfPmD6cIaNaLinkAdd specifies the IPv6-address
         for IA-NA that should be included in the link-address field of the relay
         header. This can be used for pool-selection by the DHCPv6 server.

         The 'no'-form of the corresponding CLI command sets the link-address to
         its default value '0::0'."
    DEFVAL { '00000000000000000000000000000000'H }
    ::= { tmnxWlanGwSubIfPmEntry 20 }

tmnxWlanGwSubIfPmD6cIaNaAdminSt  OBJECT-TYPE
    SYNTAX      TmnxAdminState 
    MAX-ACCESS  read-create
    STATUS      current
    DESCRIPTION
        "The value of tmnxWlanGwSubIfPmD6cIaNaAdminSt specifies the administrative
         state of the considered DHCPv6 client for IA-NA."
    DEFVAL { outOfService }
    ::= { tmnxWlanGwSubIfPmEntry 21 }
        
--
--      WLAN GW Subscriber Interface ISA Pool State
--
        
tmnxWlanGwSubIfIpsTable OBJECT-TYPE
    SYNTAX      SEQUENCE OF TmnxWlanGwSubIfIpsEntry
    MAX-ACCESS  not-accessible
    STATUS      current
    DESCRIPTION
       "The tmnxWlanGwSubIfIpsTable contains objects giving
        the states of the pools on the ISA."
    ::= { tmnxWlanGwSoftGreObjs 10 }

tmnxWlanGwSubIfIpsEntry OBJECT-TYPE
    SYNTAX      TmnxWlanGwSubIfIpsEntry
    MAX-ACCESS  not-accessible
    STATUS      current
    DESCRIPTION
        "Each conceptual row represents a set of states
         of a pool on the ISA."
    INDEX { vRtrID,
            tmnxWlanGwSubIfIpsSubnetAddrType,
            tmnxWlanGwSubIfIpsSubnetAddr,
            tmnxWlanGwSubIfIpsSubnetPrefLen }
    ::= { tmnxWlanGwSubIfIpsTable 1 }

TmnxWlanGwSubIfIpsEntry ::= 
    SEQUENCE {
        tmnxWlanGwSubIfIpsSubIfIndex     InterfaceIndex,
        tmnxWlanGwSubIfIpsSubnetAddrType InetAddressType,
        tmnxWlanGwSubIfIpsSubnetAddr     InetAddress,
        tmnxWlanGwSubIfIpsSubnetPrefLen  InetAddressPrefixLength,
        tmnxWlanGwSubIfIpsAddrFamily     TmnxWlanGwSubIfIpsAddrFamily,
        tmnxWlanGwSubIfIpsPoolIsOld      TruthValue,
        tmnxWlanGwSubIfIpsUsageLevelPct  Unsigned32,
        tmnxWlanGwSubIfIpsDHCPv6Options  OCTET STRING,
        tmnxWlanGwSubIfIpsRemLeaseTime   Unsigned32,
        tmnxWlanGwSubIfIpsIsaGrpId       TmnxWlanGwIsaGrpIdOrZero,
        tmnxWlanGwSubIfIpsIsaMemberId    Unsigned32,
        tmnxWlanGwSubIfIpsServiceId      TmnxServId
    }

tmnxWlanGwSubIfIpsSubIfIndex OBJECT-TYPE
    SYNTAX      InterfaceIndex
    MAX-ACCESS  read-only
    STATUS      current
    DESCRIPTION
        "The value of tmnxWlanGwSubIfIpsSubIfIndex indicates the index
         of the subscriber interface."
    ::= { tmnxWlanGwSubIfIpsEntry 1 }
 
tmnxWlanGwSubIfIpsSubnetAddrType OBJECT-TYPE
    SYNTAX      InetAddressType
    MAX-ACCESS  read-only
    STATUS      current
    DESCRIPTION
        "The value of tmnxWlanGwSubIfIpsSubnetAddrType indicates the type
         of the address stored in tmnxWlanGwSubIfIpsSubnetAddr."
    DEFVAL { unknown } 
    ::= { tmnxWlanGwSubIfIpsEntry 2 }
 
tmnxWlanGwSubIfIpsSubnetAddr OBJECT-TYPE
    SYNTAX      InetAddress (SIZE(0|4|16))
    MAX-ACCESS  read-only
    STATUS      current
    DESCRIPTION
        "The value of tmnxWlanGwSubIfIpsSubnetAddr indicates the subnet address
         of the pool."
    ::= { tmnxWlanGwSubIfIpsEntry 3 }
 
tmnxWlanGwSubIfIpsSubnetPrefLen OBJECT-TYPE
    SYNTAX      InetAddressPrefixLength
    MAX-ACCESS  read-only
    STATUS      current
    DESCRIPTION
        "The value of tmnxWlanGwSubIfIpsSubnetPrefLen indicates the prefix length
         of the subnet of the pool."
    ::= { tmnxWlanGwSubIfIpsEntry 4 }
    
tmnxWlanGwSubIfIpsAddrFamily OBJECT-TYPE
    SYNTAX      TmnxWlanGwSubIfIpsAddrFamily
    MAX-ACCESS  read-only
    STATUS      current
    DESCRIPTION
        "The value of tmnxWlanGwSubIfIpsAddrFamily indicates the address family
         of the pool as defined in the textual convention TmnxWlanGwSubIfIpsAddrFamily."
    ::= { tmnxWlanGwSubIfIpsEntry 5 }
    
tmnxWlanGwSubIfIpsPoolIsOld  OBJECT-TYPE
    SYNTAX      TruthValue
    MAX-ACCESS  read-only
    STATUS      current
    DESCRIPTION
        "The value of tmnxWlanGwSubIfIpsPoolIsOld is 'true' if the data
         in the pool entry is coming from another ISA.
         The value is 'false' if the pool has been requested for the ISA."
    DEFVAL { false }
    ::= { tmnxWlanGwSubIfIpsEntry 6 }
    
tmnxWlanGwSubIfIpsUsageLevelPct OBJECT-TYPE
    SYNTAX      Unsigned32 (0..100)
    MAX-ACCESS  read-only
    STATUS      current
    DESCRIPTION
        "The value of tmnxWlanGwSubIfIpsUsageLevelPct indicates the percentage
         of addresses in use for the prefix."
    DEFVAL { 0 }
    ::= { tmnxWlanGwSubIfIpsEntry 7 }
    
tmnxWlanGwSubIfIpsDHCPv6Options OBJECT-TYPE
    SYNTAX      OCTET STRING (SIZE (512))
    MAX-ACCESS  read-only
    STATUS      current
    DESCRIPTION
        "The value of tmnxWlanGwSubIfIpsDHCPv6Options indicates the DHCPv6
         options as defined in RFC 3315 section 22."
    ::= { tmnxWlanGwSubIfIpsEntry 8 }
    
tmnxWlanGwSubIfIpsRemLeaseTime OBJECT-TYPE
    SYNTAX      Unsigned32
    UNITS       "seconds"
    MAX-ACCESS  read-only
    STATUS      current
    DESCRIPTION
        "The value of tmnxWlanGwSubIfIpsRemLeaseTime indicates the remaining
         lease time of the pool."
    DEFVAL { 0 }
    ::= { tmnxWlanGwSubIfIpsEntry 9 }
    
tmnxWlanGwSubIfIpsIsaGrpId OBJECT-TYPE
    SYNTAX      TmnxWlanGwIsaGrpIdOrZero
    MAX-ACCESS  read-only
    STATUS      current
    DESCRIPTION
       "The value of the object tmnxWlanGwSubIfIpsIsaGrpId indicates
        the group identifier of the ISA for the given prefix."
    ::= { tmnxWlanGwSubIfIpsEntry 10 }
    
tmnxWlanGwSubIfIpsIsaMemberId OBJECT-TYPE
    SYNTAX      Unsigned32
    MAX-ACCESS  read-only
    STATUS      current
    DESCRIPTION
       "The value of the object tmnxWlanGwSubIfIpsIsaMemberId indicates
        the member identifier of the ISA for the given prefix."
    ::= { tmnxWlanGwSubIfIpsEntry 11 }

tmnxWlanGwSubIfIpsServiceId OBJECT-TYPE
    SYNTAX      TmnxServId
    MAX-ACCESS  read-only
    STATUS      current
    DESCRIPTION
        "The value of tmnxWlanGwSubIfIpsServiceId indicates the
         service identifier."
    ::= { tmnxWlanGwSubIfIpsEntry 12 }
            
--
--      The Group Interface Retail-Service Map Table
--

tmnxWlanGwIfRetailTable OBJECT-TYPE
    SYNTAX      SEQUENCE OF TmnxWlanGwIfRetailEntry
    MAX-ACCESS  not-accessible
    STATUS      obsolete
    DESCRIPTION
       "The tmnxWlanGwIfRetailTable contains objects to configure
        the association between IEEE 802.1q VLAN tags and retail services
        for WLAN Gateway interfaces.
        
        This table is replaced with the tmnxWlanGwVlanTable."
    ::= { tmnxWlanGwObjs 3 }

tmnxWlanGwIfRetailEntry OBJECT-TYPE
    SYNTAX      TmnxWlanGwIfRetailEntry
    MAX-ACCESS  not-accessible
    STATUS      obsolete
    DESCRIPTION
        "Each conceptual row represents a range of VLAN Q-tags 
         on a particular interface, and its association with a Retail Service.
         
         WLAN Gateway traffic on this interface 
         tagged with a matching VLAN Q-tag is to be processed
         in the specified retailer service, unless a RADIUS server provided
         a retail service for the traffic from this User Equipment.

         Rows in this table can be created or deleted via SNMP operations.
         
         A row with the same values for svcId and iesIfIndex must exist
         in the tmnxWlanGwSoftGreIfTable."
    INDEX { svcId, iesIfIndex,
            tmnxWlanGwIfRetailTagStart,
            tmnxWlanGwIfRetailTagEnd
           }
    ::= { tmnxWlanGwIfRetailTable 1 }

TmnxWlanGwIfRetailEntry ::= 
    SEQUENCE {
        tmnxWlanGwIfRetailTagStart         QTagFullRange,
        tmnxWlanGwIfRetailTagEnd           QTagFullRange,
        tmnxWlanGwIfRetailRowStatus        RowStatus,
        tmnxWlanGwIfRetailLastCh           TimeStamp,
        tmnxWlanGwIfRetailService          TmnxServId
    }
tmnxWlanGwIfRetailTagStart OBJECT-TYPE
    SYNTAX      QTagFullRange
    MAX-ACCESS  not-accessible
    STATUS      obsolete
    DESCRIPTION
        "The value of the object tmnxWlanGwIfRetailTagStart specifies
         the start VLAN tag of this range."
    ::= { tmnxWlanGwIfRetailEntry 1 }

tmnxWlanGwIfRetailTagEnd OBJECT-TYPE
    SYNTAX      QTagFullRange
    MAX-ACCESS  not-accessible
    STATUS      obsolete
    DESCRIPTION
        "The value of the object tmnxWlanGwIfRetailTagEnd specifies
         the end VLAN tag of this range."
    ::= { tmnxWlanGwIfRetailEntry 2 }

tmnxWlanGwIfRetailRowStatus OBJECT-TYPE
    SYNTAX      RowStatus
    MAX-ACCESS  read-create
    STATUS      obsolete
    DESCRIPTION
       "The value of tmnxWlanGwIfRetailRowStatus specifies 
        the row status of this row."
    ::= { tmnxWlanGwIfRetailEntry 3 }

tmnxWlanGwIfRetailLastCh OBJECT-TYPE
    SYNTAX      TimeStamp
    MAX-ACCESS  read-only
    STATUS      obsolete
    DESCRIPTION
        "The value of tmnxWlanGwIfRetailLastCh indicates the sysUpTime at
         the time of the most recent management-initiated change to this
         table row."
    ::= { tmnxWlanGwIfRetailEntry 4 }

tmnxWlanGwIfRetailService OBJECT-TYPE
    SYNTAX      TmnxServId
    MAX-ACCESS  read-create
    STATUS      obsolete
    DESCRIPTION
       "The value of tmnxWlanGwIfRetailService specifies 
        the identifier of the retail service associated with this range.
        
        A nonzero value for this object must be specified when a row is
        created."
    ::= { tmnxWlanGwIfRetailEntry 5 }

--
--      The WLAN Gateway User Equipment Table
--

tmnxWlanGwUeTable OBJECT-TYPE
    SYNTAX      SEQUENCE OF TmnxWlanGwUeEntry
    MAX-ACCESS  not-accessible
    STATUS      current
    DESCRIPTION
       "The tmnxWlanGwUeTable contains information about 
        WLAN Gateway User Equipment's (UE)."
    ::= { tmnxWlanGwObjs 4 }

tmnxWlanGwUeEntry OBJECT-TYPE
    SYNTAX      TmnxWlanGwUeEntry
    MAX-ACCESS  not-accessible
    STATUS      current
    DESCRIPTION
        "Each conceptual row represents information about
         a WLAN Gateway User Equipment.

         Entries in this table are created and destroyed automatically
         by the system."
    INDEX { tmnxWlanGwUeMacAddress }
    ::= { tmnxWlanGwUeTable 1 }

TmnxWlanGwUeEntry ::= 
    SEQUENCE {
        tmnxWlanGwUeMacAddress           MacAddress,
        tmnxWlanGwUeQTag                 QTagFullRangeOrNone,
        tmnxWlanGwUeMplsLabel            MplsLabel,
        tmnxWlanGwUeTuRouter             TmnxVRtrID,
        tmnxWlanGwUeTuAddrType           InetAddressType,
        tmnxWlanGwUeTuRemoteAddr         InetAddress,
        tmnxWlanGwUeTuLocalAddr          InetAddress,
        tmnxWlanGwUeTuQosRetailService   TmnxServId,
        tmnxWlanGwUeSsid                 TNamedItemOrEmpty,
        tmnxWlanGwUePrevApAddrType       InetAddressType,
        tmnxWlanGwUePrevApAddr           InetAddress,
        tmnxWlanGwUeLastMoveTime         DateAndTime,
        tmnxWlanGwUeImsi                 TmnxMobImsiStr,
        tmnxWlanGwUeService              TmnxServId,
        tmnxWlanGwUeSapPortId            TmnxPortID,            
        tmnxWlanGwUeSapPortEncapValue    TmnxEncapVal,            
        tmnxWlanGwUeEncapsulation        TmnxWlanGwUeEncapsulation
    }
    
tmnxWlanGwUeMacAddress OBJECT-TYPE
    SYNTAX      MacAddress
    MAX-ACCESS  not-accessible
    STATUS      current
    DESCRIPTION
        "The value of the object tmnxWlanGwUeMacAddress indicates
         the MAC address of this UE."
    ::= { tmnxWlanGwUeEntry 1 }

tmnxWlanGwUeQTag OBJECT-TYPE
    SYNTAX      QTagFullRangeOrNone
    MAX-ACCESS  read-only
    STATUS      current
    DESCRIPTION     
        "The value of the object tmnxWlanGwUeQTag indicates
         the VLAN Q-tag present in the traffic received from this UE.
         
         The value of this object can be used to identify the retailer
         service, by means of the tmnxWlanGwIfRetailTable.
         
         The value minus one indicates that the traffic received from this UE
         does not have a VLAN Q-tag."
    ::= { tmnxWlanGwUeEntry 3 }

tmnxWlanGwUeMplsLabel OBJECT-TYPE
    SYNTAX      MplsLabel
    MAX-ACCESS  read-only
    STATUS      current
    DESCRIPTION     
        "The value of the object tmnxWlanGwUeMplsLabel indicates
         the MPLS label present in the traffic received from this UE.
         
         The value zero indicates that the traffic received from this UE
         does not have an MPLS label."
    ::= { tmnxWlanGwUeEntry 4 }

tmnxWlanGwUeTuRouter OBJECT-TYPE
    SYNTAX      TmnxVRtrID
    MAX-ACCESS  read-only
    STATUS      current
    DESCRIPTION
        "The value of tmnxWlanGwUeTuRouter indicates 
         the identifier of the virtual router instance 
         where the tunneled User Equipment traffic is routed." 
    ::= { tmnxWlanGwUeEntry 5 }
    
tmnxWlanGwUeTuAddrType OBJECT-TYPE
    SYNTAX      InetAddressType
    MAX-ACCESS  read-only
    STATUS      current
    DESCRIPTION 
        "The value of tmnxWlanGwUeTuAddrType specifies
         the address type of tmnxWlanGwUeTuRemoteAddr 
         and tmnxWlanGwUeTuLocalAddr.
         
         The only values allowed are 'ipv4' and 'ipv6'."
    ::= { tmnxWlanGwUeEntry 6 }

tmnxWlanGwUeTuRemoteAddr OBJECT-TYPE
    SYNTAX      InetAddress (SIZE(4|16))
    MAX-ACCESS  read-only
    STATUS      current
    DESCRIPTION
        "The value of the object tmnxWlanGwUeTuRemoteAddr specifies
         the IP address of the remote endpoint of this UE's tunnel,
         that is the source IP address in the tunnel header of
         received packets."
    ::= { tmnxWlanGwUeEntry 7 }

tmnxWlanGwUeTuLocalAddr OBJECT-TYPE
    SYNTAX      InetAddress (SIZE(4|16))
    MAX-ACCESS  read-only
    STATUS      current
    DESCRIPTION
        "The value of the object tmnxWlanGwUeTuLocalAddr specifies
         the IP address of the local endpoint of this UE's tunnel,
         that is the destination IP address in the tunnel header of
         received packets."
    ::= { tmnxWlanGwUeEntry 8 }

tmnxWlanGwUeTuQosRetailService OBJECT-TYPE
    SYNTAX      TmnxServId
    MAX-ACCESS  read-only
    STATUS      current
    DESCRIPTION     
        "The value of the object tmnxWlanGwUeTuQosRetailService indicates
         the identifier of the retail service.
         
         The value zero indicates that this UE's tunnel has per-tunnel QoS."
    ::= { tmnxWlanGwUeEntry 9 }

tmnxWlanGwUeSsid OBJECT-TYPE
    SYNTAX      TNamedItemOrEmpty
    MAX-ACCESS  read-only
    STATUS      current
    DESCRIPTION 
       "The value of tmnxWlanGwUeSsid indicates 
        the Service Set ID (SSID) of this UE.
        
        This object refers to a conceptual row in the tmnxWlanGwSsidTable."
    ::= { tmnxWlanGwUeEntry 10 }
    
tmnxWlanGwUePrevApAddrType OBJECT-TYPE
    SYNTAX      InetAddressType
    MAX-ACCESS  read-only
    STATUS      current
    DESCRIPTION 
       "The value of tmnxWlanGwUePrevApAddrType indicates the
        address type of tmnxWlanGwUePrevApAddr."
    ::= { tmnxWlanGwUeEntry 11 }

tmnxWlanGwUePrevApAddr OBJECT-TYPE
    SYNTAX      InetAddress (SIZE(0|4|16))
    MAX-ACCESS  read-only
    STATUS      current
    DESCRIPTION 
       "The value of tmnxWlanGwUePrevApAddr indicates the IP
        address of the previous Access Point (AP) of this UE.
        
        Note that the address of the current AP of this UE is the
        value of the object tmnxWlanGwUeTuRemoteAddr."
    ::= { tmnxWlanGwUeEntry 12 }
    
tmnxWlanGwUeLastMoveTime OBJECT-TYPE
    SYNTAX      DateAndTime (SIZE (11))
    MAX-ACCESS  read-only
    STATUS      current
    DESCRIPTION
        "The value of tmnxWlanGwUeLastMoveTime indicates
         the time of the most recent Access Point move of this UE."
    ::= { tmnxWlanGwUeEntry 13 }

tmnxWlanGwUeImsi OBJECT-TYPE
    SYNTAX      TmnxMobImsiStr
    MAX-ACCESS  read-only
    STATUS      current
    DESCRIPTION
        "The value of tmnxWlanGwUeImsi indicates
         the IMSI (International Mobile Subscriber Identity) of this UE."
    ::= { tmnxWlanGwUeEntry 15 }
    
tmnxWlanGwUeService OBJECT-TYPE
    SYNTAX      TmnxServId
    MAX-ACCESS  read-only
    STATUS      current
    DESCRIPTION     
        "The value of the object tmnxWlanGwUeService indicates
         the service identifier of the (internal) SAP associated
         with this UE.

         While a subscriber is associated with this UE, that SAP is where
         its subscriber hosts can be found in the TIMETRA-SUBSCRIBER-MGMT-MIB::tmnxSubHostInfoV2Table.

         While no subscriber is associated with this UE, the value of tmnxWlanGwUeService is equal to zero."
    ::= { tmnxWlanGwUeEntry 16 }

tmnxWlanGwUeSapPortId OBJECT-TYPE
    SYNTAX      TmnxPortID
    MAX-ACCESS  read-only
    STATUS      current
    DESCRIPTION     
        "The value of the object tmnxWlanGwUeSapPortId indicates 
         the port ID of the (internal) SAP associated
         with this UE.

         While no subscriber is associated with this UE, the value of tmnxWlanGwUeSapPortId is equal 
         to '1E000000'H, the identifier of the 'invalid port'."
    ::= { tmnxWlanGwUeEntry 17 }

tmnxWlanGwUeSapPortEncapValue OBJECT-TYPE
    SYNTAX      TmnxEncapVal
    MAX-ACCESS  read-only
    STATUS      current
    DESCRIPTION     
        "The value of the object tmnxWlanGwUeSapPortEncapValue indicates 
         the value of the encapsulation of the (internal) SAP associated
         with this UE.

         While no subscriber is associated with this UE, the value of tmnxWlanGwUeSapPortEncapValue
         is equal to zero."
    ::= { tmnxWlanGwUeEntry 18 }
    
tmnxWlanGwUeEncapsulation OBJECT-TYPE
    SYNTAX      TmnxWlanGwUeEncapsulation
    MAX-ACCESS  read-only
    STATUS      current
    DESCRIPTION
        "The value of the object tmnxWlanGwUeEncapsulation indicates
         the encapsulation used in this UE's tunnel."
    ::= { tmnxWlanGwUeEntry 19 }
    
--
--      The WLAN Gateway Service Set ID (SSID) Table
--

tmnxWlanGwSsidTable OBJECT-TYPE
    SYNTAX      SEQUENCE OF TmnxWlanGwSsidEntry
    MAX-ACCESS  not-accessible
    STATUS      current
    DESCRIPTION
       "The tmnxWlanGwSsidTable contains information about 
        WLAN Gateway Service Set ID's (SSID) learned by this system."
    ::= { tmnxWlanGwObjs 5 }

tmnxWlanGwSsidEntry OBJECT-TYPE
    SYNTAX      TmnxWlanGwSsidEntry
    MAX-ACCESS  not-accessible
    STATUS      current
    DESCRIPTION
        "Each conceptual row represents information about
         a specific WLAN Gateway Service Set ID (SSID).

         Entries in this table are created and destroyed automatically
         by the system."
    INDEX { IMPLIED tmnxWlanGwSsid }
    ::= { tmnxWlanGwSsidTable 1 }

TmnxWlanGwSsidEntry ::= 
    SEQUENCE {
        tmnxWlanGwSsid                 TNamedItem,
        tmnxWlanGwSsidNumUe            Gauge32
    }
    
tmnxWlanGwSsid OBJECT-TYPE
    SYNTAX      TNamedItem
    MAX-ACCESS  not-accessible
    STATUS      current
    DESCRIPTION 
       "The value of tmnxWlanGwSsid indicates 
        a Service Set ID (SSID) learned by this system."
    ::= { tmnxWlanGwSsidEntry 1 }
    
tmnxWlanGwSsidNumUe OBJECT-TYPE
    SYNTAX      Gauge32
    MAX-ACCESS  read-only
    STATUS      current
    DESCRIPTION 
        "The value of the object tmnxWlanGwSsidNumUe indicates
         the number of User Equipment's connected to this system 
         using this SSID."
    ::= { tmnxWlanGwSsidEntry 2 }

-- --------------------------------------------------------
--      Mobile Gateway Profile 
-- --------------------------------------------------------
--
--      Mobile Gateway Profile Table
--
tmnxWlanGwMgwProfTable OBJECT-TYPE
    SYNTAX      SEQUENCE OF TmnxWlanGwMgwProfEntry
    MAX-ACCESS  not-accessible
    STATUS      current
    DESCRIPTION
        "The tmnxWlanGwMgwProfTable allows configuration of 
         how to communicate with a Mobile Gateway.
         
         A Mobile Gateway can be a Packet Data Network Gateway (PGW) or a
         Gateway GPRS Support Node (GGSN)."
    ::= { tmnxWlanGwMgwObjs 1 }

tmnxWlanGwMgwProfEntry OBJECT-TYPE
    SYNTAX      TmnxWlanGwMgwProfEntry
    MAX-ACCESS  not-accessible
    STATUS      current
    DESCRIPTION
        "Each entry represents the configuration
         for a specific Mobile Gateway Profile.
        
         Entries in this table can be created and deleted via SNMP SET
         operations to tmnxWlanGwMgwProfRowStatus."
    INDEX { IMPLIED tmnxWlanGwMgwProfName }
    ::= { tmnxWlanGwMgwProfTable 1 }

TmnxWlanGwMgwProfEntry ::=
    SEQUENCE {
        tmnxWlanGwMgwProfName            TNamedItem,
        tmnxWlanGwMgwProfRowStatus       RowStatus,
        tmnxWlanGwMgwProfLastChanged     TimeStamp,
        tmnxWlanGwMgwProfDescription     TItemDescription,
        tmnxWlanGwMgwProfMsgReTxTimeout  TmnxMobProfMsgReTxTimeout,
        tmnxWlanGwMgwProfMsgReTxRetryCnt TmnxMobProfMsgReTxRetryCount,
        tmnxWlanGwMgwProfKeepAlvTimeout  TmnxMobProfKeepAliveTimeout,
        tmnxWlanGwMgwProfKeepAlvRetryCnt TmnxMobProfKeepAliveRetryCount,
        tmnxWlanGwMgwProfKeepAlvResp     TmnxMobProfKeepAliveResponse,
        tmnxWlanGwMgwProfTtl             TmnxMobProfIpTtl,
        tmnxWlanGwMgwProfInterfaceType   TmnxWlanGwMgwInterfaceType,
        tmnxWlanGwMgwProfChrgCharHome    TmnxWlanGwChargingCharBits,
        tmnxWlanGwMgwProfChrgCharRoam    TmnxWlanGwChargingCharBits,
        tmnxWlanGwMgwProfSeHoldTime      Integer32,
        tmnxWlanGwMgwProfReportWlanLoc   TmnxEnabledDisabled,       
        tmnxWlanGwMgwProfProtocolCfgOpt  INTEGER
    }

tmnxWlanGwMgwProfName OBJECT-TYPE
    SYNTAX      TNamedItem
    MAX-ACCESS  not-accessible
    STATUS      current
    DESCRIPTION
        "The value of tmnxWlanGwMgwProfName specifies
         the name that identifies this profile."
    ::= { tmnxWlanGwMgwProfEntry 1 }

tmnxWlanGwMgwProfRowStatus OBJECT-TYPE
    SYNTAX      RowStatus
    MAX-ACCESS  read-create
    STATUS      current
    DESCRIPTION
        "The value of tmnxWlanGwMgwProfRowStatus controls the creation and
         deletion of rows in the table."
    ::= { tmnxWlanGwMgwProfEntry 2 }

tmnxWlanGwMgwProfLastChanged OBJECT-TYPE
    SYNTAX      TimeStamp
    MAX-ACCESS  read-only
    STATUS      current
    DESCRIPTION
        "The value of tmnxWlanGwMgwProfLastChanged indicates the sysUpTime at
         the time of the most recent management-initiated change to this
         profile."
    ::= { tmnxWlanGwMgwProfEntry 3 }

tmnxWlanGwMgwProfDescription OBJECT-TYPE
    SYNTAX      TItemDescription
    MAX-ACCESS  read-create
    STATUS      current
    DESCRIPTION
        "The value of tmnxWlanGwMgwProfDescription specifies the user provided
         description of this profile."
    DEFVAL { "" }
    ::= { tmnxWlanGwMgwProfEntry 4 }

tmnxWlanGwMgwProfMsgReTxTimeout OBJECT-TYPE
    SYNTAX      TmnxMobProfMsgReTxTimeout
    UNITS       "seconds"
    MAX-ACCESS  read-create
    STATUS      current
    DESCRIPTION
        "The value of tmnxWlanGwMgwProfMsgReTxTimeout specifies, in seconds, the
         interval between retransmission of signalling request messages 
         towards the same peer Mobile Gateway."
    REFERENCE
       "3GPP TS 29.060, 
        section 7.6 Reliable Delivery of Signalling Messages."
    DEFVAL { 5 }
    ::= { tmnxWlanGwMgwProfEntry 5 }

tmnxWlanGwMgwProfMsgReTxRetryCnt OBJECT-TYPE
    SYNTAX      TmnxMobProfMsgReTxRetryCount
    MAX-ACCESS  read-create
    STATUS      current
    DESCRIPTION
        "The value of tmnxWlanGwMgwProfMsgReTxRetryCnt specifies the number of
         times a signalling request message is transmitted 
         towards the same peer."
    REFERENCE
       "3GPP TS 29.060, 
        section 7.6 Reliable Delivery of Signalling Messages."
    DEFVAL { 3 }
    ::= { tmnxWlanGwMgwProfEntry 6 }
    
tmnxWlanGwMgwProfKeepAlvTimeout OBJECT-TYPE
    SYNTAX      TmnxMobProfKeepAliveTimeout
    UNITS       "seconds"
    MAX-ACCESS  read-create
    STATUS      current
    DESCRIPTION
        "The value of tmnxWlanGwMgwProfKeepAlvTimeout specifies, in seconds, the
         interval between keep-alive Echo-Request messages towards the same peer.
         
         The value zero specifies that no Echo-Request messages be sent."
    REFERENCE
       "3GPP TS 29.060, 
        section 7.2.1 Echo Request."
    DEFVAL { 60 }
    ::= { tmnxWlanGwMgwProfEntry 7 }

tmnxWlanGwMgwProfKeepAlvRetryCnt OBJECT-TYPE
    SYNTAX      TmnxMobProfKeepAliveRetryCount
    MAX-ACCESS  read-create
    STATUS      current
    DESCRIPTION
        "The value of tmnxWlanGwMgwProfKeepAlvRetryCnt specifies the number of
         Echo-Request messages towards the same peer."
    REFERENCE
       "3GPP TS 29.060, 
        section 7.2.1 Echo Request."
    DEFVAL { 4 }
    ::= { tmnxWlanGwMgwProfEntry 8 }

tmnxWlanGwMgwProfKeepAlvResp OBJECT-TYPE
    SYNTAX      TmnxMobProfKeepAliveResponse
    UNITS       "seconds"
    MAX-ACCESS  read-create
    STATUS      current
    DESCRIPTION
        "The value of tmnxWlanGwMgwProfKeepAlvResp specifies, in seconds, the
         time between Echo-Request message retries towards the same peer."
    REFERENCE
       "3GPP TS 29.060, 
        section 7.2.1 Echo Request."
    DEFVAL { 5 }
    ::= { tmnxWlanGwMgwProfEntry 9 }

tmnxWlanGwMgwProfTtl OBJECT-TYPE
    SYNTAX      TmnxMobProfIpTtl
    UNITS       "hops"
    MAX-ACCESS  read-create
    STATUS      current
    DESCRIPTION
        "The value of tmnxWlanGwMgwProfTtl specifies
         the value to put in the IP header's TTL field for
         GTP (GPRS Tunnel Protocol) control messages."
    DEFVAL { 255 }
    ::= { tmnxWlanGwMgwProfEntry 10 }

tmnxWlanGwMgwProfInterfaceType OBJECT-TYPE
    SYNTAX      TmnxWlanGwMgwInterfaceType
    MAX-ACCESS  read-create
    STATUS      current
    DESCRIPTION
        "The value of tmnxWlanGwMgwProfInterfaceType specifies
         the interface type."
    DEFVAL { s2a }
    ::= { tmnxWlanGwMgwProfEntry 12 }

tmnxWlanGwMgwProfChrgCharHome OBJECT-TYPE
    SYNTAX      TmnxWlanGwChargingCharBits
    MAX-ACCESS  read-create
    STATUS      current
    DESCRIPTION
        "The value of tmnxWlanGwMgwProfChrgCharHome specifies
         the bits to set in the Charging Characteristics Information Element (IE)
         for 'home UE', if not known by other means such as RADIUS."
    REFERENCE
       "3GPP TS 29.060, section 7.7.23 Charging Characteristics
       
        3GPP TS 29.061 section 16.4.7.2 Coding 3GPP Vendor-Specific RADIUS attributes,
        13 - 3GPP-Charging-Characteristics"
    DEFVAL { { } }
    ::= { tmnxWlanGwMgwProfEntry 15 }

tmnxWlanGwMgwProfChrgCharRoam OBJECT-TYPE
    SYNTAX      TmnxWlanGwChargingCharBits
    MAX-ACCESS  read-create
    STATUS      current
    DESCRIPTION
        "The value of tmnxWlanGwMgwProfChrgCharRoam specifies
         the bits to set in the Charging Characteristics Information Element (IE)
         for roaming UE, if not known by other means such as RADIUS."
    REFERENCE
       "3GPP TS 29.060, section 7.7.23 Charging Characteristics
       
        3GPP TS 29.061 section 16.4.7.2 Coding 3GPP Vendor-Specific RADIUS attributes,
        13 - 3GPP-Charging-Characteristics"
    DEFVAL { { } }
    ::= { tmnxWlanGwMgwProfEntry 16 }

tmnxWlanGwMgwProfSeHoldTime OBJECT-TYPE
    SYNTAX      Integer32 (-1 | 0..3600)
    UNITS       "seconds"
    MAX-ACCESS  read-create
    STATUS      current
    DESCRIPTION
        "The value of tmnxWlanGwMgwProfSeHoldTime specifies, in seconds, the
         time that a GTP session context is held after the corresponding
         User Equipment is disconnected.
         
         If the same User Equipment re-connects to this system before this time
         has elapsed, its GTP session context is re-used.
         
         When the timer expires, the GTP session context is cleared.
         
         The value minus one specifies that the timer is equal to the User Equipment's
         DHCP remaining lease time.
         
         The value zero specifies that the GTP session context is cleared immediately."
    DEFVAL { 30 }
    ::= { tmnxWlanGwMgwProfEntry 20 }

tmnxWlanGwMgwProfReportWlanLoc OBJECT-TYPE
    SYNTAX      TmnxEnabledDisabled
    MAX-ACCESS  read-create
    STATUS      current
    DESCRIPTION
        "The value of tmnxWlanGwMgwProfReportWlanLoc specifies
         if this system reports UE Wifi location in the session create request
         through the GTP interface."
    REFERENCE
       "3GPP S2-124852_was_S2-124665: Location Information for 'SaMOG' user."
    DEFVAL { disabled }
    ::= { tmnxWlanGwMgwProfEntry 21 }

tmnxWlanGwMgwProfProtocolCfgOpt OBJECT-TYPE
    SYNTAX      INTEGER {
                    pco  (1),
                    apco (2)
                }
    MAX-ACCESS  read-create
    STATUS      current
    DESCRIPTION
        "The value of tmnxWlanGwMgwProfProtocolCfgOpt specifies
         if this system uses the Protocol Configuration Options Information
         Element (IE), or the Additional Protocol Configuration Options IE."
    REFERENCE
       "3GPP TS 24.008 Section 10.5.6.3 Protocol configuration options
        3GPP TS 29.275 Section 12.1.1.19 Additional Protocol Configuration Options."
    DEFVAL { pco }
    ::= { tmnxWlanGwMgwProfEntry 22 }

--
--      The MGW-Address-To-MGW-Profile map Table
--

tmnxWlanGwMgwAddrTable OBJECT-TYPE
    SYNTAX      SEQUENCE OF TmnxWlanGwMgwAddrEntry
    MAX-ACCESS  not-accessible
    STATUS      current
    DESCRIPTION
       "The tmnxWlanGwMgwAddrTable associates Mobile Gateways
        to Mobile Gateway Profiles."
    ::= { tmnxWlanGwMgwObjs 2 }

tmnxWlanGwMgwAddrEntry OBJECT-TYPE
    SYNTAX      TmnxWlanGwMgwAddrEntry
    MAX-ACCESS  not-accessible
    STATUS      current
    DESCRIPTION
        "Each conceptual row represents a prefix for 
         Mobile Gateway addresses, associating them 
         to a particular Mobile Gateway Profile.

         Entries in this table can be created or deleted via SNMP operations.
         
         A corresponding conceptual row in the tmnxNatVrtrTable must exist
         while creating a row in this table."
    INDEX { vRtrID,
            tmnxWlanGwMgwAddrType,
            tmnxWlanGwMgwAddr,
            tmnxWlanGwMgwAddrPrefixLen
           }
    ::= { tmnxWlanGwMgwAddrTable 1 }

TmnxWlanGwMgwAddrEntry ::= 
    SEQUENCE {
        tmnxWlanGwMgwAddrType            InetAddressType,
        tmnxWlanGwMgwAddr                InetAddress,
        tmnxWlanGwMgwAddrPrefixLen       InetAddressPrefixLength,
        tmnxWlanGwMgwAddrRowStatus       RowStatus,
        tmnxWlanGwMgwAddrLastMgmtChange  TimeStamp,
        tmnxWlanGwMgwAddrProfile         TNamedItem 
    }

tmnxWlanGwMgwAddrType OBJECT-TYPE
    SYNTAX      InetAddressType
    MAX-ACCESS  not-accessible
    STATUS      current
    DESCRIPTION 
        "The value of tmnxWlanGwMgwAddrType specifies
         the address type of tmnxWlanGwMgwAddr.
         
         The only value supported is 'ipv4'."
    ::= { tmnxWlanGwMgwAddrEntry 1 }

tmnxWlanGwMgwAddr OBJECT-TYPE
    SYNTAX      InetAddress (SIZE(4|16))
    MAX-ACCESS  not-accessible
    STATUS      current
    DESCRIPTION 
        "The value of tmnxWlanGwMgwAddrType specifies
         the IP address of the subnet.
         
         Only IPv4 addresses are supported."
    ::= { tmnxWlanGwMgwAddrEntry 2 }

tmnxWlanGwMgwAddrPrefixLen OBJECT-TYPE
    SYNTAX          InetAddressPrefixLength (0..32)
    MAX-ACCESS      not-accessible
    STATUS          current
    DESCRIPTION 
        "The value of tmnxWlanGwMgwAddrPrefixLen specifies
         the prefix length of the subnet."
    ::= { tmnxWlanGwMgwAddrEntry 3 }

tmnxWlanGwMgwAddrRowStatus OBJECT-TYPE
    SYNTAX      RowStatus
    MAX-ACCESS  read-create
    STATUS      current
    DESCRIPTION
       "The value of tmnxWlanGwMgwAddrRowStatus specifies 
        the row status of this row."
    ::= { tmnxWlanGwMgwAddrEntry 4 }

tmnxWlanGwMgwAddrLastMgmtChange OBJECT-TYPE
    SYNTAX          TimeStamp
    MAX-ACCESS      read-only
    STATUS          current
    DESCRIPTION
        "The value of tmnxWlanGwMgwAddrLastMgmtChange indicates the sysUpTime at
         the time of the most recent management-initiated change to this
         table row."
    ::= { tmnxWlanGwMgwAddrEntry 5 }

tmnxWlanGwMgwAddrProfile OBJECT-TYPE
    SYNTAX      TNamedItem
    MAX-ACCESS  read-create
    STATUS      current
    DESCRIPTION
       "The value of tmnxWlanGwMgwAddrProfile specifies the
        Mobile Gateway profile associated with this address prefix.
        
        This object refers to a row in the tmnxWlanGwMgwProfTable.
        
        A value for this object must be provided when the conceptual row
        is created."
    ::= { tmnxWlanGwMgwAddrEntry 6 }

--
--      The Mobile Gateway table
--

tmnxWlanGwMgwTable   OBJECT-TYPE
    SYNTAX      SEQUENCE OF TmnxWlanGwMgwEntry
    MAX-ACCESS  not-accessible
    STATUS      current
    DESCRIPTION
       "The tmnxWlanGwMgwTable contains information
        about Mobile Gateways connected to this system."
    ::= { tmnxWlanGwMgwObjs 3 }

tmnxWlanGwMgwEntry   OBJECT-TYPE
    SYNTAX      TmnxWlanGwMgwEntry
    MAX-ACCESS  not-accessible
    STATUS      current
    DESCRIPTION
        "Each conceptual row represents information about
         a particular Mobile Gateway connected to this system.

         Rows are created or removed automatically by the system."
    INDEX { vRtrID,
            tmnxWlanGwMgwRemoteAddrType,
            tmnxWlanGwMgwRemoteAddr,
            tmnxWlanGwMgwRemotePort
    }
    ::= { tmnxWlanGwMgwTable 1 }

TmnxWlanGwMgwEntry ::= 
    SEQUENCE {
        tmnxWlanGwMgwRemoteAddrType      InetAddressType,
        tmnxWlanGwMgwRemoteAddr          InetAddress,
        tmnxWlanGwMgwRemotePort          InetPortNumber,
        tmnxWlanGwMgwLocalAddrType       InetAddressType,
        tmnxWlanGwMgwLocalAddr           InetAddress,
        tmnxWlanGwMgwTime                DateAndTime,
        tmnxWlanGwMgwProfile             TNamedItemOrEmpty,
        tmnxWlanGwMgwControl             INTEGER,
        tmnxWlanGwMgwRestartCnt          Gauge32,
        tmnxWlanGwMgwState               TmnxMobPathMgmtState,
        tmnxWlanGwMgwInterfaceType       TmnxWlanGwMgwInterfaceType
    }

tmnxWlanGwMgwRemoteAddrType OBJECT-TYPE
    SYNTAX      InetAddressType
    MAX-ACCESS  not-accessible
    STATUS      current
    DESCRIPTION 
        "The value of tmnxWlanGwMgwRemoteAddrType indicates
         the address type of tmnxWlanGwMgwRemoteAddr.
         
         The only values allowed are 'ipv4' and 'ipv6'."
    ::= { tmnxWlanGwMgwEntry 1 }

tmnxWlanGwMgwRemoteAddr OBJECT-TYPE
    SYNTAX      InetAddress (SIZE(4|16))
    MAX-ACCESS  not-accessible
    STATUS      current
    DESCRIPTION
        "The value of the object tmnxWlanGwMgwRemoteAddr indicates
         the IP address of the Mobile Gateway,
         that is the source IP address in the tunnel header of
         received packets."
    ::= { tmnxWlanGwMgwEntry 2 }

tmnxWlanGwMgwRemotePort OBJECT-TYPE
    SYNTAX      InetPortNumber
    MAX-ACCESS  not-accessible
    STATUS      current
    DESCRIPTION 
        "The value of tmnxWlanGwMgwRemotePort indicates
         the remote port."
    ::= { tmnxWlanGwMgwEntry 3 }

tmnxWlanGwMgwLocalAddrType OBJECT-TYPE
    SYNTAX      InetAddressType
    MAX-ACCESS  read-only
    STATUS      current
    DESCRIPTION 
        "The value of tmnxWlanGwMgwLocalAddrType specifies
         the address type of tmnxWlanGwMgwLocalAddr.
         
         The only values allowed are 'ipv4' and 'ipv6'."
    ::= { tmnxWlanGwMgwEntry 4 }

tmnxWlanGwMgwLocalAddr OBJECT-TYPE
    SYNTAX      InetAddress (SIZE(4|16))
    MAX-ACCESS  read-only
    STATUS      current
    DESCRIPTION
        "The value of the object tmnxWlanGwMgwLocalAddr indicates
         the IP address of this system,
         that is the destination IP address in the tunnel header of
         received packets."
    ::= { tmnxWlanGwMgwEntry 5 }

tmnxWlanGwMgwTime OBJECT-TYPE
    SYNTAX      DateAndTime (SIZE (11))
    MAX-ACCESS  read-only
    STATUS      current
    DESCRIPTION 
        "The value of the object tmnxWlanGwMgwTime indicates
         the value of sysUpTime when this conceptual row was created."
    ::= { tmnxWlanGwMgwEntry 6 }

tmnxWlanGwMgwProfile OBJECT-TYPE
    SYNTAX      TNamedItemOrEmpty
    MAX-ACCESS  read-only
    STATUS      current
    DESCRIPTION 
        "The value of the object tmnxWlanGwMgwProfile indicates
         the name of the profile used for the connection with this
         Mobile Gateway.
         
         A non-empty value of this object corresponds to a value of 
         the object tmnxWlanGwMgwProfName in the tmnxWlanGwMgwProfTable."
    ::= { tmnxWlanGwMgwEntry 7 }

tmnxWlanGwMgwControl   OBJECT-TYPE
    SYNTAX      INTEGER {
                    gtpv1C (1),
                    gtpv2C (2)
                }
    MAX-ACCESS  read-only
    STATUS      current
    DESCRIPTION
       "The value of tmnxWlanGwMgwControl indicates the
        control plane protocol used for the connection with this
        Mobile Gateway."
    ::= { tmnxWlanGwMgwEntry 8 }

tmnxWlanGwMgwRestartCnt   OBJECT-TYPE
    SYNTAX      Gauge32
    MAX-ACCESS  read-only
    STATUS      current
    DESCRIPTION
       "The value of tmnxWlanGwMgwRestartCnt indicates the
        number of times this Mobile Gateway restarted.
        
        This value is learned by means of the connection
        with this Mobile Gateway."
    ::= { tmnxWlanGwMgwEntry 9 }

tmnxWlanGwMgwState   OBJECT-TYPE
    SYNTAX      TmnxMobPathMgmtState
    MAX-ACCESS  read-only
    STATUS      current
    DESCRIPTION
       "The value of tmnxWlanGwMgwState indicates the
        state of the connection with this
        Mobile Gateway."
    ::= { tmnxWlanGwMgwEntry 10 }

tmnxWlanGwMgwInterfaceType   OBJECT-TYPE
    SYNTAX      TmnxWlanGwMgwInterfaceType
    MAX-ACCESS  read-only
    STATUS      current
    DESCRIPTION
       "The value of tmnxWlanGwMgwInterfaceType indicates the
        interface type of the connection with this
        Mobile Gateway."
    ::= { tmnxWlanGwMgwEntry 11 }

--
--      The Mobile Gateway Statistics Table
--


tmnxWlanMgwStatsTable   OBJECT-TYPE
    SYNTAX      SEQUENCE OF TmnxWlanMgwStatsEntry
    MAX-ACCESS  not-accessible
    STATUS      current
    DESCRIPTION
       "The tmnxWlanMgwStatsTable contains detailed statistics information 
        about the Mobile Gateways connected to this system.
        
        The typical usage of this table is to fill in the part of the index
        that identifies a Mobile Gateway, and perform a partial walk
        to get all the statistics applicable to that Mobile Gateway."
    ::= { tmnxWlanGwMgwObjs 4 }

tmnxWlanMgwStatsEntry   OBJECT-TYPE
    SYNTAX      TmnxWlanMgwStatsEntry
    MAX-ACCESS  not-accessible
    STATUS      current
    DESCRIPTION
       "Each conceptual row contains detailed statistics information
        about a Mobile Gateway.

        Entries in this table are created and removed automatically by the 
        system."
    INDEX { vRtrID,
            tmnxWlanGwMgwRemoteAddrType,
            tmnxWlanGwMgwRemoteAddr,
            tmnxWlanGwMgwRemotePort,
            tmnxWlanMgwStatsId }
    ::= { tmnxWlanMgwStatsTable 1 }

TmnxWlanMgwStatsEntry ::= 
    SEQUENCE {
        tmnxWlanMgwStatsId               Unsigned32,
        tmnxWlanMgwStatsName             DisplayString,
        tmnxWlanMgwStatsVal              Counter64,
        tmnxWlanMgwStatsValLw            Counter32,
        tmnxWlanMgwStatsValHw            Counter32
    }

tmnxWlanMgwStatsId OBJECT-TYPE
    SYNTAX      Unsigned32 (0..44)
    MAX-ACCESS  not-accessible
    STATUS      current
    DESCRIPTION
        "The value of tmnxWlanMgwStatsId indicates
         the identifier of the WLAN Gateway statistics 
         contained in this conceptual row.
         
         It is a meaningless number generated by this system."
    ::= { tmnxWlanMgwStatsEntry 1 }

tmnxWlanMgwStatsName OBJECT-TYPE
    SYNTAX      DisplayString (SIZE (1..64))
    MAX-ACCESS  read-only
    STATUS      current
    DESCRIPTION 
       "The value of the object tmnxWlanMgwStatsName indicates
        the human-readable identifier of the statistics 
        contained in this conceptual row."
    ::= { tmnxWlanMgwStatsEntry 2 }

tmnxWlanMgwStatsVal OBJECT-TYPE
    SYNTAX      Counter64
    MAX-ACCESS  read-only
    STATUS      current
    DESCRIPTION 
       "The value of the object tmnxWlanMgwStatsVal indicates
        the value of the statistics contained in this conceptual row."
    ::= { tmnxWlanMgwStatsEntry 3 }

tmnxWlanMgwStatsValLw OBJECT-TYPE
    SYNTAX      Counter32
    MAX-ACCESS  read-only
    STATUS      current
    DESCRIPTION 
       "The value of the object tmnxWlanMgwStatsValLw indicates
        the lower 32 bits of the statistics contained in this conceptual row."
    ::= { tmnxWlanMgwStatsEntry 4 }

tmnxWlanMgwStatsValHw OBJECT-TYPE
    SYNTAX      Counter32
    MAX-ACCESS  read-only
    STATUS      current
    DESCRIPTION 
       "The value of the object tmnxWlanMgwStatsValHw indicates
        the higher 32 bits of the statistics contained in this conceptual row."
    ::= { tmnxWlanMgwStatsEntry 5 }

--
--      The GTP Session table
--

tmnxWlanGwGtpSeTable   OBJECT-TYPE
    SYNTAX      SEQUENCE OF TmnxWlanGwGtpSeEntry
    MAX-ACCESS  not-accessible
    STATUS      current
    DESCRIPTION
       "The tmnxWlanGwGtpSeTable contains information
        about GTP (GPRS Tunnel Protocol) sessions."
    ::= { tmnxWlanGwMgwObjs 5 }

tmnxWlanGwGtpSeEntry   OBJECT-TYPE
    SYNTAX      TmnxWlanGwGtpSeEntry
    MAX-ACCESS  not-accessible
    STATUS      current
    DESCRIPTION
        "Each conceptual row represents information about
         a particular GTP session.

         Rows are created or removed automatically by the system."
    INDEX { tmnxWlanGwGtpSeImsi,
            tmnxWlanGwGtpSeApn
    }
    ::= { tmnxWlanGwGtpSeTable 1 }

TmnxWlanGwGtpSeEntry ::= 
    SEQUENCE {
        tmnxWlanGwGtpSeImsi            TmnxMobImsiStr,
        tmnxWlanGwGtpSeApn             TmnxMobApn,
        tmnxWlanGwGtpSeMgwRouter       TmnxVRtrIDOrZero,
        tmnxWlanGwGtpSeMgwAddrType     InetAddressType,
        tmnxWlanGwGtpSeMgwAddr         InetAddress,
        tmnxWlanGwGtpSeRemoteCtrlTeid  Unsigned32,
        tmnxWlanGwGtpSeLocalCtrlTeid   Unsigned32,
        tmnxWlanGwGtpSeChrgChar        TmnxWlanGwChargingCharBits
    }

tmnxWlanGwGtpSeImsi OBJECT-TYPE
    SYNTAX      TmnxMobImsiStr (SIZE(9..15))
    MAX-ACCESS  not-accessible
    STATUS      current
    DESCRIPTION 
        "The value of tmnxWlanGwGtpSeImsi indicates
         the IMSI."
    ::= { tmnxWlanGwGtpSeEntry 1 }

tmnxWlanGwGtpSeApn OBJECT-TYPE
    SYNTAX      TmnxMobApn
    MAX-ACCESS  not-accessible
    STATUS      current
    DESCRIPTION
        "The value of the object tmnxWlanGwGtpSeApn indicates
         the APN (Access Point Name)."
    REFERENCE
       "3GPP TS 23.003 Numbering, addressing and identification, 
        section 9 Definition of Access Point Name"
    ::= { tmnxWlanGwGtpSeEntry 2 }

tmnxWlanGwGtpSeMgwRouter OBJECT-TYPE
    SYNTAX      TmnxVRtrIDOrZero
    MAX-ACCESS  read-only
    STATUS      current
    DESCRIPTION
        "The value of tmnxWlanGwGtpSeMgwRouter indicates 
         the identifier of the virtual router instance 
         where the GTP tunnel is terminated." 
    ::= { tmnxWlanGwGtpSeEntry 3 }
    
tmnxWlanGwGtpSeMgwAddrType OBJECT-TYPE
    SYNTAX      InetAddressType
    MAX-ACCESS  read-only
    STATUS      current
    DESCRIPTION 
        "The value of tmnxWlanGwGtpSeMgwAddrType indicates
         the address type of tmnxWlanGwGtpSeMgwAddr."
    ::= { tmnxWlanGwGtpSeEntry 4 }

tmnxWlanGwGtpSeMgwAddr OBJECT-TYPE
    SYNTAX      InetAddress (SIZE(4|16))
    MAX-ACCESS  read-only
    STATUS      current
    DESCRIPTION
        "The value of the object tmnxWlanGwGtpSeMgwAddr indicates
         the IP address of the Mobile Gateway,
         that is the source IP address in the tunnel header of
         received packets."
    ::= { tmnxWlanGwGtpSeEntry 5 }

tmnxWlanGwGtpSeRemoteCtrlTeid OBJECT-TYPE
    SYNTAX      Unsigned32
    MAX-ACCESS  read-only
    STATUS      current
    DESCRIPTION
        "The value of tmnxWlanGwGtpSeRemoteCtrlTeid indicates 
         the remote control plane Tunnel Endpoint Identifier (TEID)." 
    ::= { tmnxWlanGwGtpSeEntry 6 }
    
tmnxWlanGwGtpSeLocalCtrlTeid OBJECT-TYPE
    SYNTAX      Unsigned32
    MAX-ACCESS  read-only
    STATUS      current
    DESCRIPTION
        "The value of tmnxWlanGwGtpSeLocalCtrlTeid indicates 
         the local control plane Tunnel Endpoint Identifier (TEID)." 
    ::= { tmnxWlanGwGtpSeEntry 7 }
    
tmnxWlanGwGtpSeChrgChar OBJECT-TYPE
    SYNTAX      TmnxWlanGwChargingCharBits
    MAX-ACCESS  read-only
    STATUS      current
    DESCRIPTION
        "The value of tmnxWlanGwGtpSeChrgChar indicates 
         the Charging Characteristics." 
    ::= { tmnxWlanGwGtpSeEntry 10 }   

--
--      The Bearer Context table
--

tmnxWlanGwBcTable   OBJECT-TYPE
    SYNTAX      SEQUENCE OF TmnxWlanGwBcEntry
    MAX-ACCESS  not-accessible
    STATUS      current
    DESCRIPTION
       "The tmnxWlanGwBcTable contains information
        about GTP (GPRS Tunnel Protocol) bearers."
    ::= { tmnxWlanGwMgwObjs 6 }

tmnxWlanGwBcEntry   OBJECT-TYPE
    SYNTAX      TmnxWlanGwBcEntry
    MAX-ACCESS  not-accessible
    STATUS      current
    DESCRIPTION
        "Each conceptual row represents information about
         a particular bearer context.

         Rows are created or removed automatically by the system."
    INDEX { tmnxWlanGwGtpSeImsi,
            tmnxWlanGwGtpSeApn,
            tmnxWlanGwBcId
    }
    ::= { tmnxWlanGwBcTable 1 }

TmnxWlanGwBcEntry ::= 
    SEQUENCE {
        tmnxWlanGwBcId          TmnxMobBearerId,
        tmnxWlanGwBcRemoteTeid  Unsigned32,
        tmnxWlanGwBcLocalTeid   Unsigned32,
        tmnxWlanGwBcQosUlGbr    Unsigned32,
        tmnxWlanGwBcQosUlMbr    Unsigned32,
        tmnxWlanGwBcQosDlGbr    Unsigned32,
        tmnxWlanGwBcQosDlMbr    Unsigned32,
        tmnxWlanGwBcQosQci      TmnxMobQci,
        tmnxWlanGwBcQosArp      TmnxMobArp
    }

tmnxWlanGwBcId OBJECT-TYPE
    SYNTAX      TmnxMobBearerId
    MAX-ACCESS  not-accessible
    STATUS      current
    DESCRIPTION 
        "The value of tmnxWlanGwBcId indicates
         the identifier of this bearer context."
    ::= { tmnxWlanGwBcEntry 1 }

tmnxWlanGwBcRemoteTeid OBJECT-TYPE
    SYNTAX      Unsigned32
    MAX-ACCESS  read-only
    STATUS      current
    DESCRIPTION
        "The value of tmnxWlanGwBcRemoteTeid indicates 
         the remote Tunnel Endpoint Identifier (TEID)." 
    ::= { tmnxWlanGwBcEntry 2 }
    
tmnxWlanGwBcLocalTeid OBJECT-TYPE
    SYNTAX      Unsigned32
    MAX-ACCESS  read-only
    STATUS      current
    DESCRIPTION
        "The value of tmnxWlanGwBcLocalTeid indicates 
         the local Tunnel Endpoint Identifier (TEID)." 
    ::= { tmnxWlanGwBcEntry 3 }

tmnxWlanGwBcQosUlGbr  OBJECT-TYPE
    SYNTAX      Unsigned32
    UNITS       "Kbps"
    MAX-ACCESS  read-only
    STATUS      current
    DESCRIPTION
        "The value of tmnxWlanGwBcQosUlGbr indicates 
         the uplink Guaranteed Bit Rate (GBR)."
    ::= { tmnxWlanGwBcEntry 10 }

tmnxWlanGwBcQosUlMbr  OBJECT-TYPE
    SYNTAX      Unsigned32
    UNITS       "Kbps"
    MAX-ACCESS  read-only
    STATUS      current
    DESCRIPTION
        "The value of tmnxWlanGwBcQosUlMbr indicates 
         the uplink Maximum Bit Rate (MBR)."
    ::= { tmnxWlanGwBcEntry 11 }

tmnxWlanGwBcQosDlGbr  OBJECT-TYPE
    SYNTAX      Unsigned32
    UNITS       "Kbps"
    MAX-ACCESS  read-only
    STATUS      current
    DESCRIPTION
        "The value of tmnxWlanGwBcQosDlGbr indicates 
         the downlink Guaranteed Bit Rate (GBR)."
    ::= { tmnxWlanGwBcEntry 12 }

tmnxWlanGwBcQosDlMbr  OBJECT-TYPE
    SYNTAX      Unsigned32
    UNITS       "Kbps"
    MAX-ACCESS  read-only
    STATUS      current
    DESCRIPTION
        "The value of tmnxWlanGwBcQosDlMbr indicates
         the downlink Maximum Bit Rate (MBR)."
    ::= { tmnxWlanGwBcEntry 13 }

tmnxWlanGwBcQosQci  OBJECT-TYPE
    SYNTAX      TmnxMobQci
    MAX-ACCESS  read-only
    STATUS      current
    DESCRIPTION
        "The value of tmnxWlanGwBcQosQci indicates the Qos Class Identifier"
    ::= { tmnxWlanGwBcEntry 14 }

tmnxWlanGwBcQosArp  OBJECT-TYPE
    SYNTAX      TmnxMobArp
    MAX-ACCESS  read-only
    STATUS      current
    DESCRIPTION
        "The value of tmnxWlanGwBcQosArp indicates the Allocation and Retention
         Priority (ARP)."
    ::= { tmnxWlanGwBcEntry 15 }
 

--
--      The Mobile Gateway Cache table
--

tmnxWlanGwMgwCacheTable   OBJECT-TYPE
    SYNTAX      SEQUENCE OF TmnxWlanGwMgwCacheEntry
    MAX-ACCESS  not-accessible
    STATUS      obsolete
    DESCRIPTION
       "This table is obsoleted and replaced with the tmnxWlanGwMgwArecCacheTable."
    ::= { tmnxWlanGwMgwObjs 7 }

tmnxWlanGwMgwCacheEntry   OBJECT-TYPE
    SYNTAX      TmnxWlanGwMgwCacheEntry
    MAX-ACCESS  not-accessible
    STATUS      obsolete
    DESCRIPTION
       "This table is obsoleted and replaced with the tmnxWlanGwMgwArecCacheTable."
    INDEX { vRtrID,
            tmnxWlanGwMgwCacheApn,
            tmnxWlanGwMgwCacheAddrType,
            tmnxWlanGwMgwCacheAddr
    }
    ::= { tmnxWlanGwMgwCacheTable 1 }

TmnxWlanGwMgwCacheEntry ::= 
    SEQUENCE {
        tmnxWlanGwMgwCacheApn          TmnxMobApnDomainName,
        tmnxWlanGwMgwCacheAddrType     InetAddressType,
        tmnxWlanGwMgwCacheAddr         InetAddress,
        tmnxWlanGwMgwCacheTtl          Unsigned32
    }

tmnxWlanGwMgwCacheApn OBJECT-TYPE
    SYNTAX      TmnxMobApnDomainName
    MAX-ACCESS  not-accessible
    STATUS      obsolete
    DESCRIPTION
        "The value of the object tmnxWlanGwMgwCacheApn indicates
         the APN (Access Point Name) of this DNS cache entry."
    REFERENCE
       "3GPP TS 23.003 Numbering, addressing and identification, 
        section 9 Definition of Access Point Name"
    ::= { tmnxWlanGwMgwCacheEntry 1 }

tmnxWlanGwMgwCacheAddrType OBJECT-TYPE
    SYNTAX      InetAddressType
    MAX-ACCESS  not-accessible
    STATUS      obsolete
    DESCRIPTION 
        "The value of tmnxWlanGwMgwRemoteAddrType indicates
         the address type of tmnxWlanGwMgwRemoteAddr.
         
         The only values allowed are 'ipv4' and 'ipv6'."
    ::= { tmnxWlanGwMgwCacheEntry 2 }

tmnxWlanGwMgwCacheAddr OBJECT-TYPE
    SYNTAX      InetAddress (SIZE(4|16))
    MAX-ACCESS  not-accessible
    STATUS      obsolete
    DESCRIPTION
        "The value of the object tmnxWlanGwMgwCacheAddr indicates
         the IP address of the Mobile Gateway."
    ::= { tmnxWlanGwMgwCacheEntry 3 }

tmnxWlanGwMgwCacheTtl OBJECT-TYPE    
    SYNTAX          Unsigned32
    UNITS           "seconds"
    MAX-ACCESS      read-only
    STATUS          obsolete
    DESCRIPTION
        "The value of tmnxWlanGwMgwCacheTtl indicates
         the period of time left for this cache entry."
    ::= { tmnxWlanGwMgwCacheEntry 4 }

--
--      The WLAN Gateway router configuration table
-- 

tmnxWlanGwTable OBJECT-TYPE
    SYNTAX      SEQUENCE OF TmnxWlanGwEntry
    MAX-ACCESS  not-accessible
    STATUS      current
    DESCRIPTION
        "The tmnxWlanGwTable allows configuration of 
         WLAN Gateway functions in a virtual router instance."
    ::= { tmnxWlanGwObjs 8 }

tmnxWlanGwEntry OBJECT-TYPE
    SYNTAX      TmnxWlanGwEntry
    MAX-ACCESS  not-accessible
    STATUS      current
    DESCRIPTION
        "Each entry represents the configuration for 
         WLAN Gateway functions in a particular virtual router instance.
         
         Entries in this table can be created and deleted via SNMP SET
         operations to tmnxWlanGwRowStatus.
         
         A corresponding row in the TIMETRA-VRTR-MIB::vRtrConfTable must exist
         in order to create a row in this table."
    INDEX { vRtrID }
    ::= { tmnxWlanGwTable 1 }

TmnxWlanGwEntry ::=
    SEQUENCE {
        tmnxWlanGwRowStatus              RowStatus,
        tmnxWlanGwLastCh                 TimeStamp,
        tmnxWlanGwApn                    TmnxMobApnOrZero,
        tmnxWlanGwMobAcctInterimUpdate   TmnxEnabledDisabled
    }

tmnxWlanGwRowStatus OBJECT-TYPE
    SYNTAX      RowStatus
    MAX-ACCESS  read-create
    STATUS      current
    DESCRIPTION
        "The value of tmnxWlanGwRowStatus controls the creation and
         deletion of rows in the table."
    ::= { tmnxWlanGwEntry 1 }

tmnxWlanGwLastCh OBJECT-TYPE
    SYNTAX      TimeStamp
    MAX-ACCESS  read-only
    STATUS      current
    DESCRIPTION
        "The value of tmnxWlanGwLastCh indicates the sysUpTime at
         the time of the most recent management-initiated change to this
         conceptual row."
    ::= { tmnxWlanGwEntry 2 }

tmnxWlanGwApn OBJECT-TYPE
    SYNTAX      TmnxMobApnOrZero (SIZE(0..80))
    MAX-ACCESS  read-create
    STATUS      current
    DESCRIPTION
        "The value of tmnxWlanGwApn specifies
         the Network Identifier part of the Access Point Name (APN) 
         to be used for UE in this virtual router instance 
         if the APN cannot be determined by other means."
    REFERENCE
       "3GPP TS 23.003, 
        section 9.1.1 Format of APN Network Identifier"
    DEFVAL { "" }
    ::= { tmnxWlanGwEntry 3 }

tmnxWlanGwMobAcctInterimUpdate OBJECT-TYPE
    SYNTAX      TmnxEnabledDisabled
    MAX-ACCESS  read-create
    STATUS      current
    DESCRIPTION
        "The value of tmnxWlanGwMobAcctInterimUpdate specifies
         the administrative state of sending mobility-triggered accounting
         interim updates.
         
         While the value of the object tmnxWlanGwMobAcctInterimUpdate is 
         equal to 'enabled', the system will send Interim-Update messages
         triggered by UE mobility." 
    DEFVAL { disabled } 
    ::= { tmnxWlanGwEntry 10 }

--
--      The GTP Statistics Table
--


tmnxWlanGwGtpStatsTable   OBJECT-TYPE
    SYNTAX      SEQUENCE OF TmnxWlanGwGtpStatsEntry
    MAX-ACCESS  not-accessible
    STATUS      current
    DESCRIPTION
       "The tmnxWlanGwGtpStatsTable contains detailed statistics information 
        about the GTP protocol in this system.
        
        The typical usage of this table is to perform a walk
        to get all the statistics."
    ::= { tmnxWlanGwMgwObjs 8 }

tmnxWlanGwGtpStatsEntry   OBJECT-TYPE
    SYNTAX      TmnxWlanGwGtpStatsEntry
    MAX-ACCESS  not-accessible
    STATUS      current
    DESCRIPTION
       "Each conceptual row contains detailed information
        about a GTP statistic.

        Entries in this table are created and removed automatically by the 
        system."
    INDEX { tmnxWlanGwGtpStatsId }
    ::= { tmnxWlanGwGtpStatsTable 1 }

TmnxWlanGwGtpStatsEntry ::= 
    SEQUENCE {
        tmnxWlanGwGtpStatsId             Unsigned32,
        tmnxWlanGwGtpStatsName           DisplayString,
        tmnxWlanGwGtpStatsVal            Counter64,
        tmnxWlanGwGtpStatsValLw          Counter32,
        tmnxWlanGwGtpStatsValHw          Counter32
    }

tmnxWlanGwGtpStatsId OBJECT-TYPE
    SYNTAX      Unsigned32 (0..71)
    MAX-ACCESS  not-accessible
    STATUS      current
    DESCRIPTION
        "The value of tmnxWlanGwGtpStatsId indicates
         the identifier of the GTP statistics 
         contained in this conceptual row.
         
         It is a meaningless number generated by this system."
    ::= { tmnxWlanGwGtpStatsEntry 1 }

tmnxWlanGwGtpStatsName OBJECT-TYPE
    SYNTAX      DisplayString (SIZE (1..56))
    MAX-ACCESS  read-only
    STATUS      current
    DESCRIPTION 
       "The value of the object tmnxWlanGwGtpStatsName indicates
        the human-readable identifier of the statistics 
        contained in this conceptual row."
    ::= { tmnxWlanGwGtpStatsEntry 2 }

tmnxWlanGwGtpStatsVal OBJECT-TYPE
    SYNTAX      Counter64
    MAX-ACCESS  read-only
    STATUS      current
    DESCRIPTION 
       "The value of the object tmnxWlanGwGtpStatsVal indicates
        the value of the statistics contained in this conceptual row."
    ::= { tmnxWlanGwGtpStatsEntry 3 }

tmnxWlanGwGtpStatsValLw OBJECT-TYPE
    SYNTAX      Counter32
    MAX-ACCESS  read-only
    STATUS      current
    DESCRIPTION 
       "The value of the object tmnxWlanGwGtpStatsValLw indicates
        the lower 32 bits of the statistics contained in this conceptual row."
    ::= { tmnxWlanGwGtpStatsEntry 4 }

tmnxWlanGwGtpStatsValHw OBJECT-TYPE
    SYNTAX      Counter32
    MAX-ACCESS  read-only
    STATUS      current
    DESCRIPTION 
       "The value of the object tmnxWlanGwGtpStatsValHw indicates
        the higher 32 bits of the statistics contained in this conceptual row."
    ::= { tmnxWlanGwGtpStatsEntry 5 }

--
--      The Mobile Gateway A-records Cache table
--

tmnxWlanGwMgwArecCacheTable   OBJECT-TYPE
    SYNTAX      SEQUENCE OF TmnxWlanGwMgwArecCacheEntry
    MAX-ACCESS  not-accessible
    STATUS      current
    DESCRIPTION
       "The tmnxWlanGwMgwArecCacheTable contains information
        about the Mobile Gateways DNS cache.
        
        When a DNS request is done to find a Mobile Gateway
        for a particular APN, the result is cached."
    ::= { tmnxWlanGwMgwObjs 10 }

tmnxWlanGwMgwArecCacheEntry   OBJECT-TYPE
    SYNTAX      TmnxWlanGwMgwArecCacheEntry
    MAX-ACCESS  not-accessible
    STATUS      current
    DESCRIPTION
        "Each conceptual row represents information about
         a particular Mobile Gateway A-record cache instance.
         
         Each conceptual row associates an APN in a router instance
         with a Mobile Gateway.

         Rows are created or removed automatically by the system."
    INDEX { vRtrID,
            tmnxWlanGwMgwArecCacheApn,
            tmnxWlanGwMgwArecCacheIndex
    }
    ::= { tmnxWlanGwMgwArecCacheTable 1 }

TmnxWlanGwMgwArecCacheEntry ::= 
    SEQUENCE {
        tmnxWlanGwMgwArecCacheApn        TmnxMobApnDomainName,
        tmnxWlanGwMgwArecCacheIndex      Unsigned32,
        tmnxWlanGwMgwArecCacheAddrType   InetAddressType,
        tmnxWlanGwMgwArecCacheAddr       InetAddress,
        tmnxWlanGwMgwArecCacheTtl        Unsigned32
    }

tmnxWlanGwMgwArecCacheApn OBJECT-TYPE
    SYNTAX      TmnxMobApnDomainName
    MAX-ACCESS  not-accessible
    STATUS      current
    DESCRIPTION
        "The value of the object tmnxWlanGwMgwArecCacheApn indicates
         the APN (Access Point Name) of this DNS cache entry."
    REFERENCE
       "3GPP TS 23.003 Numbering, addressing and identification, 
        section 9 Definition of Access Point Name"
    ::= { tmnxWlanGwMgwArecCacheEntry 1 }

tmnxWlanGwMgwArecCacheIndex OBJECT-TYPE
    SYNTAX      Unsigned32
    MAX-ACCESS  not-accessible
    STATUS      current
    DESCRIPTION
        "The value of the object tmnxWlanGwMgwArecCacheIndex indicates
         the identifier of this entry within a set of rows that have the same
         APN.
         
         It is a number generated by the system."
    ::= { tmnxWlanGwMgwArecCacheEntry 2 }

tmnxWlanGwMgwArecCacheAddrType OBJECT-TYPE
    SYNTAX      InetAddressType
    MAX-ACCESS  read-only
    STATUS      current
    DESCRIPTION 
        "The value of tmnxWlanGwMgwArecCacheAddrType indicates
         the address type of tmnxWlanGwMgwArecCacheAddr.
         
         The only values allowed are 'ipv4' and 'ipv6'."
    ::= { tmnxWlanGwMgwArecCacheEntry 3 }

tmnxWlanGwMgwArecCacheAddr OBJECT-TYPE
    SYNTAX      InetAddress (SIZE(4|16))
    MAX-ACCESS  read-only
    STATUS      current
    DESCRIPTION
        "The value of the object tmnxWlanGwMgwArecCacheAddr indicates
         the IP address of the Mobile Gateway."
    ::= { tmnxWlanGwMgwArecCacheEntry 4 }

tmnxWlanGwMgwArecCacheTtl OBJECT-TYPE    
    SYNTAX          Unsigned32
    UNITS           "seconds"
    MAX-ACCESS      read-only
    STATUS          current
    DESCRIPTION
        "The value of tmnxWlanGwMgwArecCacheTtl indicates
         the period of time left for this cache entry."
    ::= { tmnxWlanGwMgwArecCacheEntry 5 }

--
--      The Mobile Gateway S-NAPTR Cache table
--

tmnxWlanGwMgwSnaptrCacheTable   OBJECT-TYPE
    SYNTAX      SEQUENCE OF TmnxWlanGwMgwSnaptrCacheEntry
    MAX-ACCESS  not-accessible
    STATUS      current
    DESCRIPTION
       "The tmnxWlanGwMgwSnaptrCacheTable contains information
        about the Mobile Gateways DNS S-NAPTR (Straightforward
        Naming Authority Pointer) cache.
        
        When a DNS NAPTR request is done to find a Mobile Gateway
        for a particular APN, the result is cached."
    REFERENCE 
       "3GPP TS 29.303 / RFC 3958"
    ::= { tmnxWlanGwMgwObjs 11 }

tmnxWlanGwMgwSnaptrCacheEntry   OBJECT-TYPE
    SYNTAX      TmnxWlanGwMgwSnaptrCacheEntry
    MAX-ACCESS  not-accessible
    STATUS      current
    DESCRIPTION
        "Each conceptual row represents information about
         a particular Mobile Gateway S-NAPTR cache instance.
         
         Each conceptual row associates an APN and service for a given 
         order and preference in a router instance with a Domain Name.

         Rows are created or removed automatically by the system."
    INDEX { vRtrID,
            tmnxWlanGwMgwSnaptrCacheApn,
            tmnxWlanGwMgwSnaptrCacheOrder,
            tmnxWlanGwMgwSnaptrCacheIndex
    }
    ::= { tmnxWlanGwMgwSnaptrCacheTable 1 }

TmnxWlanGwMgwSnaptrCacheEntry ::= 
    SEQUENCE {
        tmnxWlanGwMgwSnaptrCacheApn      TmnxMobApnDomainName,
        tmnxWlanGwMgwSnaptrCacheOrder    Unsigned32,
        tmnxWlanGwMgwSnaptrCacheIndex    Unsigned32,
        tmnxWlanGwMgwSnaptrCachePref     Unsigned32,
        tmnxWlanGwMgwSnaptrCacheService  TmnxMobService,
        tmnxWlanGwMgwSnaptrCacheNext     INTEGER,
        tmnxWlanGwMgwSnaptrCacheRepl     TmnxMobApnDomainName,
        tmnxWlanGwMgwSnaptrCacheTtl      Unsigned32        
    }

tmnxWlanGwMgwSnaptrCacheApn OBJECT-TYPE
    SYNTAX      TmnxMobApnDomainName
    MAX-ACCESS  not-accessible
    STATUS      current
    DESCRIPTION
        "The value of the object tmnxWlanGwMgwSnaptrCacheApn indicates
         the APN (Access Point Name) of this DNS cache entry."
    REFERENCE
       "3GPP TS 23.003 Numbering, addressing and identification, 
        section 9 Definition of Access Point Name"
    ::= { tmnxWlanGwMgwSnaptrCacheEntry 1 }

tmnxWlanGwMgwSnaptrCacheOrder OBJECT-TYPE
    SYNTAX      Unsigned32
    MAX-ACCESS  not-accessible
    STATUS      current
    DESCRIPTION 
        "The value of tmnxWlanGwMgwSnaptrCacheOrder indicates
         the order of this cache entry.
         
         If more than one NAPTR record matches, they are processed in
         increasing values of tmnxWlanGwMgwSnaptrCacheOrder."
    ::= { tmnxWlanGwMgwSnaptrCacheEntry 2 }

tmnxWlanGwMgwSnaptrCacheIndex OBJECT-TYPE
    SYNTAX      Unsigned32
    MAX-ACCESS  not-accessible
    STATUS      current
    DESCRIPTION
        "The value of the object tmnxWlanGwMgwSnaptrCacheIndex indicates
         the identifier of this entry within a set of rows that have the same
         APN and order.
         
         It is a number generated by the system."
    ::= { tmnxWlanGwMgwSnaptrCacheEntry 3 }

tmnxWlanGwMgwSnaptrCachePref OBJECT-TYPE
    SYNTAX      Unsigned32
    MAX-ACCESS  read-only
    STATUS      current
    DESCRIPTION
        "The value of the object tmnxWlanGwMgwSnaptrCachePref indicates
         the preference of this cache entry.
         
         A lower value for tmnxWlanGwMgwSnaptrCachePref indicates a higher preference."
    ::= { tmnxWlanGwMgwSnaptrCacheEntry 4 }

tmnxWlanGwMgwSnaptrCacheService OBJECT-TYPE
    SYNTAX      TmnxMobService (SIZE(1..80))
    MAX-ACCESS  read-only
    STATUS      current
    DESCRIPTION
        "The value of the object tmnxWlanGwMgwSnaptrCacheService indicates
         the service associated with this cache entry."
    ::= { tmnxWlanGwMgwSnaptrCacheEntry 5 }

tmnxWlanGwMgwSnaptrCacheNext OBJECT-TYPE    
    SYNTAX          INTEGER {
                        dnsSrv                           (1),
                        dnsA                             (2),
                        dnsNaptr                         (3)
                    }
    MAX-ACCESS      read-only
    STATUS          current
    DESCRIPTION
        "The value of tmnxWlanGwMgwSnaptrCacheNext indicates
         the next lookup operation for this cache entry.
         
         For the next lookup operation, the value of tmnxWlanGwMgwSnaptrCacheRepl
         must be used instead of the original APN value."
    ::= { tmnxWlanGwMgwSnaptrCacheEntry 6 }

tmnxWlanGwMgwSnaptrCacheRepl OBJECT-TYPE    
    SYNTAX          TmnxMobApnDomainName
    MAX-ACCESS      read-only
    STATUS          current
    DESCRIPTION
        "The value of tmnxWlanGwMgwSnaptrCacheRepl indicates
         the APN value to be substituted for the original APN in the next lookup."
    ::= { tmnxWlanGwMgwSnaptrCacheEntry 7 }
       
tmnxWlanGwMgwSnaptrCacheTtl OBJECT-TYPE    
    SYNTAX          Unsigned32
    UNITS           "seconds"
    MAX-ACCESS      read-only
    STATUS          current
    DESCRIPTION
        "The value of tmnxWlanGwMgwSnaptrCacheTtl indicates
         the period of time left for this cache entry."
    ::= { tmnxWlanGwMgwSnaptrCacheEntry 8 }

--
--      The Mobile Gateway DNS SRV Cache table
--

tmnxWlanGwMgwSrvCacheTable   OBJECT-TYPE
    SYNTAX      SEQUENCE OF TmnxWlanGwMgwSrvCacheEntry
    MAX-ACCESS  not-accessible
    STATUS      current
    DESCRIPTION
       "The tmnxWlanGwMgwSrvCacheTable contains information
        about the Mobile Gateways DNS SRV cache.
        
        When a DNS SRV request is done to find a DNS server
        for a particular APN, the result is cached."
    REFERENCE 
       "IETF RFC 2782"
    ::= { tmnxWlanGwMgwObjs 12 }

tmnxWlanGwMgwSrvCacheEntry   OBJECT-TYPE
    SYNTAX      TmnxWlanGwMgwSrvCacheEntry
    MAX-ACCESS  not-accessible
    STATUS      current
    DESCRIPTION
        "Each conceptual row represents information about
         a particular Mobile Gateway SRV cache instance.
         
         Each conceptual row associates an APN for a given 
         priority and weight in a router instance, with a target Domain Name.

         Rows are created or removed automatically by the system."
    INDEX { vRtrID,
            tmnxWlanGwMgwSrvCacheApn,
            tmnxWlanGwMgwSrvCachePriority,
            tmnxWlanGwMgwSrvCacheIndex
    }
    ::= { tmnxWlanGwMgwSrvCacheTable 1 }

TmnxWlanGwMgwSrvCacheEntry ::= 
    SEQUENCE {
        tmnxWlanGwMgwSrvCacheApn      TmnxMobApnDomainName,
        tmnxWlanGwMgwSrvCachePriority Unsigned32,
        tmnxWlanGwMgwSrvCacheIndex    Unsigned32,
        tmnxWlanGwMgwSrvCacheWeight   Unsigned32,
        tmnxWlanGwMgwSrvCachePort     InetPortNumber,
        tmnxWlanGwMgwSrvCacheTarget   TmnxMobApnDomainName,
        tmnxWlanGwMgwSrvCacheTtl      Unsigned32        
    }

tmnxWlanGwMgwSrvCacheApn OBJECT-TYPE
    SYNTAX      TmnxMobApnDomainName
    MAX-ACCESS  not-accessible
    STATUS      current
    DESCRIPTION
        "The value of the object tmnxWlanGwMgwSrvCacheApn indicates
         the APN (Access Point Name) of this DNS cache entry."
    REFERENCE
       "3GPP TS 23.003 Numbering, addressing and identification, 
        section 9 Definition of Access Point Name"
    ::= { tmnxWlanGwMgwSrvCacheEntry 1 }

tmnxWlanGwMgwSrvCachePriority OBJECT-TYPE
    SYNTAX      Unsigned32 (0..65535)
    MAX-ACCESS  not-accessible
    STATUS      current
    DESCRIPTION 
        "The value of tmnxWlanGwMgwSrvCachePriority indicates
         the priority of this cache entry.
         
         The lower the number, the higher the priority.
         
         If more than one SERV record matches, they are processed according to
         their value of tmnxWlanGwMgwSrvCacheWeight."
    ::= { tmnxWlanGwMgwSrvCacheEntry 2 }

tmnxWlanGwMgwSrvCacheIndex OBJECT-TYPE
    SYNTAX      Unsigned32
    MAX-ACCESS  not-accessible
    STATUS      current
    DESCRIPTION
        "The value of the object tmnxWlanGwMgwSrvCacheIndex indicates
         the identifier of this entry within a set of rows that have the same
         APN and priority.
         
         It is a number generated by the system."
    ::= { tmnxWlanGwMgwSrvCacheEntry 3 }

tmnxWlanGwMgwSrvCacheWeight OBJECT-TYPE
    SYNTAX      Unsigned32 (0..65535)
    MAX-ACCESS  read-only
    STATUS      current
    DESCRIPTION
        "The value of the object tmnxWlanGwMgwSrvCacheWeight indicates
         the weight of this cache entry.
         
         Cache entries with larger weights should have a higher probability of
         being used."
    ::= { tmnxWlanGwMgwSrvCacheEntry 4 }

tmnxWlanGwMgwSrvCachePort OBJECT-TYPE
    SYNTAX      InetPortNumber
    MAX-ACCESS  read-only
    STATUS      current
    DESCRIPTION
        "The value of the object tmnxWlanGwMgwSrvCachePort indicates
         the port on this target host of this service."
    ::= { tmnxWlanGwMgwSrvCacheEntry 5 }

tmnxWlanGwMgwSrvCacheTarget OBJECT-TYPE    
    SYNTAX          TmnxMobApnDomainName
    MAX-ACCESS      read-only
    STATUS          current
    DESCRIPTION
        "The value of tmnxWlanGwMgwSrvCacheTarget indicates
         the domain name of the target host."
    ::= { tmnxWlanGwMgwSrvCacheEntry 6 }
    
tmnxWlanGwMgwSrvCacheTtl OBJECT-TYPE    
    SYNTAX          Unsigned32
    UNITS           "seconds"
    MAX-ACCESS      read-only
    STATUS          current
    DESCRIPTION
        "The value of tmnxWlanGwMgwSrvCacheTtl indicates
         the period of time left for this cache entry."
    ::= { tmnxWlanGwMgwSrvCacheEntry 7 }



--
--      Mobile Gateway Packet Data Network Gateway Profile Table
--

tmnxWlanGwPgwTable OBJECT-TYPE
    SYNTAX      SEQUENCE OF TmnxWlanGwPgwEntry
    MAX-ACCESS  not-accessible
    STATUS      current
    DESCRIPTION
        "The tmnxWlanGwPgwTable allows configuration of 
         how to communicate with a Packet Data Network Gateway (PGW) Mobile Gateway."
    ::= { tmnxWlanGwMgwObjs 20 }

tmnxWlanGwPgwEntry OBJECT-TYPE
    SYNTAX      TmnxWlanGwPgwEntry
    MAX-ACCESS  not-accessible
    STATUS      current
    DESCRIPTION
        "Each entry represents the configuration
         for a specific Mobile Gateway Profile, to be used when the Mobile Gateway
         is a Packet Data Network Gateway (PGW).
        
         Entries in this table are created and destroyed automatically by the system."
    AUGMENTS { tmnxWlanGwMgwProfEntry }
    ::= { tmnxWlanGwPgwTable 1 }

TmnxWlanGwPgwEntry ::=
    SEQUENCE {
        tmnxWlanGwPgwLastChanged         TimeStamp,
        tmnxWlanGwPgwQosUplinkGbrRate    TmnxMobProfGbrRate,
        tmnxWlanGwPgwQosUplinkMbrRate    TmnxMobProfMbrRate,
        tmnxWlanGwPgwQosDwnlinkGbrRate   TmnxMobProfGbrRate,
        tmnxWlanGwPgwQosDwnlinkMbrRate   TmnxMobProfMbrRate,
        tmnxWlanGwPgwQosArpValue         TmnxMobArpValue,
        tmnxWlanGwPgwQosQciValue         TmnxMobQci         
    }

tmnxWlanGwPgwLastChanged OBJECT-TYPE
    SYNTAX      TimeStamp
    MAX-ACCESS  read-only
    STATUS      current
    DESCRIPTION
        "The value of tmnxWlanGwPgwLastChanged indicates the sysUpTime at
         the time of the most recent management-initiated change to this
         profile."
    ::= { tmnxWlanGwPgwEntry 1 }

tmnxWlanGwPgwQosUplinkGbrRate OBJECT-TYPE
    SYNTAX      TmnxMobProfGbrRate
    UNITS       "Kbps"
    MAX-ACCESS  read-create
    STATUS      current
    DESCRIPTION
        "The value of tmnxWlanGwPgwQosUplinkGbrRate specifies the
         uplink Guaranteed Bit Rate (GBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 0 }
    ::= { tmnxWlanGwPgwEntry 2 }

tmnxWlanGwPgwQosUplinkMbrRate OBJECT-TYPE
    SYNTAX      TmnxMobProfMbrRate
    UNITS       "Kbps"
    MAX-ACCESS  read-create
    STATUS      current
    DESCRIPTION
        "The value of tmnxWlanGwPgwQosUplinkMbrRate specifies the
         uplink Maximum Bit Rate (MBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 0 }
    ::= { tmnxWlanGwPgwEntry 3 }

tmnxWlanGwPgwQosDwnlinkGbrRate OBJECT-TYPE
    SYNTAX      TmnxMobProfGbrRate
    UNITS       "Kbps"
    MAX-ACCESS  read-create
    STATUS      current
    DESCRIPTION
        "The value of tmnxWlanGwPgwQosDwnlinkGbrRate specifies the
         downlink Guaranteed Bit Rate (GBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 0 }
    ::= { tmnxWlanGwPgwEntry 4 }

tmnxWlanGwPgwQosDwnlinkMbrRate OBJECT-TYPE
    SYNTAX      TmnxMobProfMbrRate
    UNITS       "Kbps"
    MAX-ACCESS  read-create
    STATUS      current
    DESCRIPTION
        "The value of tmnxWlanGwPgwQosDwnlinkMbrRate specifies the
         downlink Maximum Bit Rate (MBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 0 }
    ::= { tmnxWlanGwPgwEntry 5 }

tmnxWlanGwPgwQosArpValue  OBJECT-TYPE
    SYNTAX      TmnxMobArpValue
    MAX-ACCESS  read-create
    STATUS      current
    DESCRIPTION
        "The value of tmnxWlanGwPgwQosArpValue specifies the
         allocation/retention priority to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 1 }
    ::= { tmnxWlanGwPgwEntry 6 }

tmnxWlanGwPgwQosQciValue  OBJECT-TYPE
    SYNTAX      TmnxMobQci
    MAX-ACCESS  read-create
    STATUS      current
    DESCRIPTION
        "The value of tmnxWlanGwPgwQosQciValue specifies the
         QoS Class Identifier (QCI) value to be used in the GTP messages
         as 'QOS IE' (for a Gn interface) or 'Bearer QOS' (for an S2a/S2b
         interface)."
    REFERENCE
       "3GPP TS 29.060, section 7.7.34 Quality of Service (QoS) Profile
       
        3GPP TS 129.274, section 8.15 Bearer Quality of Service (Bearer QoS)
        
        3GPP TS 23.203, section 6.5 Quality of Service Control rule"
    DEFVAL { 8 }
    ::= { tmnxWlanGwPgwEntry 7 }

--
--      Mobile Gateway Gateway GPRS Support Node Profile Table
--

tmnxWlanGwGgsnTable OBJECT-TYPE
    SYNTAX      SEQUENCE OF TmnxWlanGwGgsnEntry
    MAX-ACCESS  not-accessible
    STATUS      current
    DESCRIPTION
        "The tmnxWlanGwGgsnTable allows configuration of 
         how to communicate with a Gateway GPRS Support Node (GGSN) Mobile Gateway."
    ::= { tmnxWlanGwMgwObjs 21 }

tmnxWlanGwGgsnEntry OBJECT-TYPE
    SYNTAX      TmnxWlanGwGgsnEntry
    MAX-ACCESS  not-accessible
    STATUS      current
    DESCRIPTION
        "Each entry represents the configuration
         for a specific Mobile Gateway Profile, to be used when the Mobile Gateway
         is a Gateway GPRS Support Node (GGSN).
        
         Entries in this table are created and destroyed automatically by the system."
    AUGMENTS { tmnxWlanGwMgwProfEntry }
    ::= { tmnxWlanGwGgsnTable 1 }

TmnxWlanGwGgsnEntry ::=
    SEQUENCE {
        tmnxWlanGwGgsnLastChanged        TimeStamp,
        tmnxWlanGwGgsnQosUplinkGbrRate   TmnxMobProfGbrRate,
        tmnxWlanGwGgsnQosUplinkMbrRate   TmnxMobProfMbrRate,
        tmnxWlanGwGgsnQosDwnlinkGbrRate  TmnxMobProfGbrRate,
        tmnxWlanGwGgsnQosDwnlinkMbrRate  TmnxMobProfMbrRate,
        tmnxWlanGwGgsnQosArpValue        TmnxMobArpValue         
    }

tmnxWlanGwGgsnLastChanged OBJECT-TYPE
    SYNTAX      TimeStamp
    MAX-ACCESS  read-only
    STATUS      current
    DESCRIPTION
        "The value of tmnxWlanGwGgsnLastChanged indicates the sysUpTime at
         the time of the most recent management-initiated change to this
         profile."
    ::= { tmnxWlanGwGgsnEntry 1 }

tmnxWlanGwGgsnQosUplinkGbrRate OBJECT-TYPE
    SYNTAX      TmnxMobProfGbrRate
    UNITS       "Kbps"
    MAX-ACCESS  read-create
    STATUS      current
    DESCRIPTION
        "The value of tmnxWlanGwGgsnQosUplinkGbrRate specifies the
         uplink Guaranteed Bit Rate (GBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 5000 }
    ::= { tmnxWlanGwGgsnEntry 2 }

tmnxWlanGwGgsnQosUplinkMbrRate OBJECT-TYPE
    SYNTAX      TmnxMobProfMbrRate
    UNITS       "Kbps"
    MAX-ACCESS  read-create
    STATUS      current
    DESCRIPTION
        "The value of tmnxWlanGwGgsnQosUplinkMbrRate specifies the
         uplink Maximum Bit Rate (MBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 5000 }
    ::= { tmnxWlanGwGgsnEntry 3 }

tmnxWlanGwGgsnQosDwnlinkGbrRate OBJECT-TYPE
    SYNTAX      TmnxMobProfGbrRate
    UNITS       "Kbps"
    MAX-ACCESS  read-create
    STATUS      current
    DESCRIPTION
        "The value of tmnxWlanGwGgsnQosDwnlinkGbrRate specifies the
         downlink Guaranteed Bit Rate (GBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 2000 }
    ::= { tmnxWlanGwGgsnEntry 4 }

tmnxWlanGwGgsnQosDwnlinkMbrRate OBJECT-TYPE
    SYNTAX      TmnxMobProfMbrRate
    UNITS       "Kbps"
    MAX-ACCESS  read-create
    STATUS      current
    DESCRIPTION
        "The value of tmnxWlanGwGgsnQosDwnlinkMbrRate specifies the
         downlink Maximum Bit Rate (MBR) to be used in the GTP messages
         as 'QOS IE' (for a Gn interface) or 'Bearer QOS' (for an S2a/S2b
         interface)."
    REFERENCE
       "3GPP TS 29.060, section 7.7.34 Quality of Service (QoS) Profile
       
        3GPP TS 129 274, section 8.15 Bearer Quality of Service (Bearer QoS)"
    DEFVAL { 2000 }
    ::= { tmnxWlanGwGgsnEntry 5 }

tmnxWlanGwGgsnQosArpValue  OBJECT-TYPE
    SYNTAX      TmnxMobArpValue (1..3)
    MAX-ACCESS  read-create
    STATUS      current
    DESCRIPTION
        "The value of tmnxWlanGwGgsnQosArpValue specifies the admission control
         to prioritize allocation and retention for bearer establishment and
         modification."
    REFERENCE
       "3GPP TS 29.060, section 7.7.34 Quality of Service (QoS) Profile
       
        3GPP TS 129 274, section 8.15 Bearer Quality of Service (Bearer QoS)
        
        3GPP TS 23.107 Table 5 Note 1"
    DEFVAL { 1 }
    ::= { tmnxWlanGwGgsnEntry 6 }
    
-- --------------------------------------------------------
--      Mobile Gateway Distributed Subscriber management 
-- --------------------------------------------------------
--
--      The Group Interface Distributed subscriber management
--      configuration Table
--

tmnxWlanGwVlanDsmTable OBJECT-TYPE
    SYNTAX      SEQUENCE OF TmnxWlanGwVlanDsmEntry
    MAX-ACCESS  not-accessible
    STATUS      current
    DESCRIPTION
       "The tmnxWlanGwVlanDsmTable contains objects to configure
        Distributed Subscriber Management (DSM) for Soft GRE Group-Interfaces
        and for ranges of IEEE 802.1q VLAN tags
        in Soft GRE Group-Interfaces."
    ::= { tmnxWlanGwDsmSubObjs 1 }

tmnxWlanGwVlanDsmEntry OBJECT-TYPE
    SYNTAX      TmnxWlanGwVlanDsmEntry
    MAX-ACCESS  not-accessible
    STATUS      current
    DESCRIPTION
        "Each conceptual row represents the set of 
         Distributed subscriber management configuration data
         for a range of VLAN Q-tags on a particular interface,
         or for the interface itself.
         
         Users whose traffic comes in on this interface 
         tagged with a matching VLAN Q-tag are to be processed according to
         the configuration specified in this conceptual row;
         otherwise, the default configuration specified 
         in the default range [4096-4096] must be used.

         Rows in this table are created and destroyed automatically by the system.
                  
         A single row in this table is always created by the system and 
         cannot be destroyed: the default range [4096-4096]."
    AUGMENTS {tmnxWlanGwVlanEntry}
    ::= { tmnxWlanGwVlanDsmTable 1 }

TmnxWlanGwVlanDsmEntry ::= 
    SEQUENCE {
        tmnxWlanGwVlanDsmLastCh           TimeStamp,
        tmnxWlanGwVlanDsmAdminState       TmnxEnabledDisabled,
        tmnxWlanGwVlanDsmAcctPlcy         TNamedItemOrEmpty,
        tmnxWlanGwVlanDsmEgressPolicer    TNamedItemOrEmpty,
        tmnxWlanGwVlanDsmIngressPolicer   TNamedItemOrEmpty,
        tmnxWlanGwVlanDsmIpFilter         TNamedItemOrEmpty,     
        tmnxWlanGwVlanDsmOneTimeRdrUrl    TmnxHttpRedirectUrl,     
        tmnxWlanGwVlanDsmOneTimeRdrPort   Unsigned32,
        tmnxWlanGwVlanDsmAcctUpdInterv    Unsigned32,
        tmnxWlanGwVlanDsmDefAppProfile    TNamedItemOrEmpty
    }

tmnxWlanGwVlanDsmLastCh OBJECT-TYPE
    SYNTAX      TimeStamp
    MAX-ACCESS  read-only
    STATUS      current
    DESCRIPTION
        "The value of tmnxWlanGwVlanDsmLastCh indicates the sysUpTime at
         the time of the most recent management-initiated change to this
         table row."
    ::= { tmnxWlanGwVlanDsmEntry 1 }
   
tmnxWlanGwVlanDsmAdminState OBJECT-TYPE
    SYNTAX      TmnxEnabledDisabled
    MAX-ACCESS  read-create
    STATUS      current
    DESCRIPTION
        "The value of tmnxWlanGwVlanDsmAdminState specifies
         the administrative state of Distributed subscriber management." 
    DEFVAL { disabled } 
    ::= { tmnxWlanGwVlanDsmEntry 2 }

tmnxWlanGwVlanDsmAcctPlcy OBJECT-TYPE
    SYNTAX      TNamedItemOrEmpty
    MAX-ACCESS  read-create
    STATUS      current
    DESCRIPTION
        "The value of tmnxWlanGwVlanDsmAcctPlcy specifies the identifier
         of the accounting policy.
         
         An entry with the same name must exist 
         in the TIMETRA-RADIUS-MIB::tmnxRadIsaPlcyTable."
    DEFVAL { "" }
    ::= { tmnxWlanGwVlanDsmEntry 3 }
    
tmnxWlanGwVlanDsmEgressPolicer OBJECT-TYPE
    SYNTAX      TNamedItemOrEmpty
    MAX-ACCESS  read-create
    STATUS      current
    DESCRIPTION
        "The value of tmnxWlanGwVlanDsmEgressPolicer specifies the identifier
         of the distributed-sub-mgmt policer for egress traffic.
         
         An entry with the same name must exist 
         in the tmnxWlanGwPolicerTable."
    DEFVAL { "" }
    ::= { tmnxWlanGwVlanDsmEntry 4 }
    
tmnxWlanGwVlanDsmIngressPolicer OBJECT-TYPE
    SYNTAX      TNamedItemOrEmpty
    MAX-ACCESS  read-create
    STATUS      current
    DESCRIPTION
        "The value of tmnxWlanGwVlanDsmIngressPolicer specifies the identifier
         of the distributed-sub-mgmt policer for ingress traffic.
         
         An entry with the same name must exist 
         in the tmnxWlanGwDsmIpFilTable."
    DEFVAL { "" }
    ::= { tmnxWlanGwVlanDsmEntry 5 }
    
tmnxWlanGwVlanDsmIpFilter OBJECT-TYPE
    SYNTAX      TNamedItemOrEmpty
    MAX-ACCESS  read-create
    STATUS      current
    DESCRIPTION
        "The value of tmnxWlanGwVlanDsmIpFilter specifies the identifier
         of the distributed-sub-mgmt IP filter.
                  
         A row with the same name must exist in the tmnxWlanGwDsmIpFilTable."
    DEFVAL { "" }
    ::= { tmnxWlanGwVlanDsmEntry 6 }
    
tmnxWlanGwVlanDsmOneTimeRdrUrl OBJECT-TYPE
    SYNTAX      TmnxHttpRedirectUrl
    MAX-ACCESS  read-create
    STATUS      current
    DESCRIPTION
        "The value of tmnxWlanGwVlanDsmOneTimeRdrUrl specifies the URL
         to redirect to.

         This string may contain a number of substitution macro's:
         - $URL: specifies that '$URL' must be substituted with the content of the
                 Request-URI in the HTTP GET Request received.
                 
         - $MAC: specifies that '$MAC' must be replaced with a string that
                 represents the MAC address of the subscriber host;
                 the MAC address is formatted in Nokia SROS style,
                 like 00:0c:f1:99:85:b8.
                 
         - $IP:  specifies that '$IP' must be replaced with a string that represents
                 the IP address of the subscriber host."
    DEFVAL { ''H }
    ::= { tmnxWlanGwVlanDsmEntry 7 }

tmnxWlanGwVlanDsmOneTimeRdrPort OBJECT-TYPE
    SYNTAX      Unsigned32 (1..65535)
    MAX-ACCESS  read-create
    STATUS      current
    DESCRIPTION
        "The value of tmnxWlanGwVlanDsmOneTimeRdrUrl specifies
         the destination port for redirected HTTP protocol packets."
    DEFVAL { 80 }
    ::= { tmnxWlanGwVlanDsmEntry 8 }

tmnxWlanGwVlanDsmAcctUpdInterv OBJECT-TYPE
    SYNTAX      Unsigned32 (0 | 5..259200)
    UNITS       "minutes"
    MAX-ACCESS  read-create
    STATUS      current
    DESCRIPTION
        "The value of tmnxWlanGwVlanDsmAcctUpdInterv specifies
         the time interval between consecutive Interim Accounting Update
         messages.
         
         The value zero specifies that the system does not send
         Interim Accounting Update messages."
    REFERENCE
        "RFC 2866 RADIUS Accounting
         section 5.1 Acct-Status-Type.
         
         RFC 2869 RADIUS Extensions
         section 2.1.  RADIUS support for Interim Accounting Updates."
    DEFVAL { 0 }
    ::= { tmnxWlanGwVlanDsmEntry 9 }

tmnxWlanGwVlanDsmDefAppProfile OBJECT-TYPE
    SYNTAX      TNamedItemOrEmpty
    MAX-ACCESS  read-create
    STATUS      current
    DESCRIPTION
        "The value of tmnxWlanGwVlanDsmDefAppProfile specifies the identifier
         of the default application profile.
                  
         A row with the same name must exist in the TIMETRA-BSX-NG-MIB::tmnxBsxAppProfTable."
    DEFVAL { "" }
    ::= { tmnxWlanGwVlanDsmEntry 10 }
    
--
--      The Distributed subscriber management IP Filter Table
--

tmnxWlanGwDsmIpFilTable OBJECT-TYPE
    SYNTAX      SEQUENCE OF TmnxWlanGwDsmIpFilEntry
    MAX-ACCESS  not-accessible
    STATUS      current
    DESCRIPTION
        "The tmnxWlanGwDsmIpFilTable allows configuration of 
         IP filters distributed on ISA cards for DSM subscribers."
    ::= { tmnxWlanGwDsmSubObjs 2 }

tmnxWlanGwDsmIpFilEntry OBJECT-TYPE
    SYNTAX      TmnxWlanGwDsmIpFilEntry
    MAX-ACCESS  not-accessible
    STATUS      current
    DESCRIPTION
        "Each conceptual row represents the configuration
         for a specific distributed-sub-mgmt IP filter.
        
         Rows in this table can be created and deleted via SNMP SET
         operations to tmnxWlanGwDsmIpFilRowStatus."
    INDEX { IMPLIED tmnxWlanGwDsmIpFilName }
    ::= { tmnxWlanGwDsmIpFilTable 1 }

TmnxWlanGwDsmIpFilEntry ::=
    SEQUENCE {
        tmnxWlanGwDsmIpFilName            TNamedItem,
        tmnxWlanGwDsmIpFilRowStatus       RowStatus,
        tmnxWlanGwDsmIpFilLastCh          TimeStamp,
        tmnxWlanGwDsmIpFilDescription     TItemDescription,
        tmnxWlanGwDsmIpFilDefaultAction   TmnxWlanGwDsmFilterAction,
        tmnxWlanGwDsmIpFilDefaultAction6  TmnxWlanGwDsmFilterAction        
    }

tmnxWlanGwDsmIpFilName OBJECT-TYPE
    SYNTAX      TNamedItem
    MAX-ACCESS  not-accessible
    STATUS      current
    DESCRIPTION
        "The value of tmnxWlanGwDsmIpFilName specifies the identifier of 
         this distributed-sub-mgmt IP filter."
    ::= { tmnxWlanGwDsmIpFilEntry 1 }

tmnxWlanGwDsmIpFilRowStatus OBJECT-TYPE
    SYNTAX      RowStatus
    MAX-ACCESS  read-create
    STATUS      current
    DESCRIPTION
        "The value of tmnxWlanGwDsmIpFilRowStatus controls the creation and
         deletion of rows in the table."
    ::= { tmnxWlanGwDsmIpFilEntry 2 }

tmnxWlanGwDsmIpFilLastCh OBJECT-TYPE
    SYNTAX      TimeStamp
    MAX-ACCESS  read-only
    STATUS      current
    DESCRIPTION
        "The value of tmnxWlanGwDsmIpFilLastCh indicates the sysUpTime at
         the time of the most recent management-initiated change to this
         policy."
    ::= { tmnxWlanGwDsmIpFilEntry 3 }

tmnxWlanGwDsmIpFilDescription OBJECT-TYPE
    SYNTAX      TItemDescription
    MAX-ACCESS  read-create
    STATUS      current
    DESCRIPTION
        "The value of tmnxWlanGwDsmIpFilDescription specifies the user provided
         description of this subscriber ISA RADIUS policy."
    DEFVAL { "" }
    ::= { tmnxWlanGwDsmIpFilEntry 4 }

tmnxWlanGwDsmIpFilDefaultAction OBJECT-TYPE
    SYNTAX      TmnxWlanGwDsmFilterAction 
    MAX-ACCESS  read-create
    STATUS      current
    DESCRIPTION
        "The value of tmnxWlanGwDsmIpFilDefaultAction specifies
         for IPv4 the action to take for a packet that does not
         match any of the filter entries of this filter."
    DEFVAL { drop }
    ::= { tmnxWlanGwDsmIpFilEntry 5 }

tmnxWlanGwDsmIpFilDefaultAction6 OBJECT-TYPE
    SYNTAX      TmnxWlanGwDsmFilterAction 
    MAX-ACCESS  read-create
    STATUS      current
    DESCRIPTION
        "The value of tmnxWlanGwDsmIpFilDefaultAction6 specifies
         for IPv6 the action to take for a packet that does not
         match any of the filter entries of this filter."
    DEFVAL { drop }
    ::= { tmnxWlanGwDsmIpFilEntry 6 }

--
--      The Distributed subscriber management IP Filter Entry Table
--

tmnxWlanGwDsmIpFilN3Table OBJECT-TYPE
    SYNTAX      SEQUENCE OF TmnxWlanGwDsmIpFilN3Entry
    MAX-ACCESS  not-accessible
    STATUS      current
    DESCRIPTION
        "The tmnxWlanGwDsmIpFilN3Table allows configuration of 
         distributed-sub-mgmt IP filter entries."
    ::= { tmnxWlanGwDsmSubObjs 3 }

tmnxWlanGwDsmIpFilN3Entry OBJECT-TYPE
    SYNTAX      TmnxWlanGwDsmIpFilN3Entry
    MAX-ACCESS  not-accessible
    STATUS      current
    DESCRIPTION
        "Each row represents the configuration for a particular
         filter entry of a distributed-sub-mgmt IP filter.
         
         Each row contains match criteria and the action to take
         for matching packets. 
        
         Rows in this table can be created and deleted
         via SNMP SET operations to tmnxWlanGwDsmIpFilN3RowStatus."
    INDEX { tmnxWlanGwDsmIpFilName,
            tmnxWlanGwDsmIpFilN3Index }
    ::= { tmnxWlanGwDsmIpFilN3Table 1 }

TmnxWlanGwDsmIpFilN3Entry ::=
    SEQUENCE {
        tmnxWlanGwDsmIpFilN3Index         Unsigned32,
        tmnxWlanGwDsmIpFilN3RowStatus     RowStatus,
        tmnxWlanGwDsmIpFilN3LastCh        TimeStamp,
        tmnxWlanGwDsmIpFilN3Description   TItemDescription,
        tmnxWlanGwDsmIpFilN3Action        TmnxWlanGwDsmFilterActionOrNone,
        tmnxWlanGwDsmIpFilN3Protocol      TIpProtocol,
        tmnxWlanGwDsmIpFilN3DestAddrType  InetAddressType,
        tmnxWlanGwDsmIpFilN3DestAddr      InetAddress,
        tmnxWlanGwDsmIpFilN3DestPrefLen   InetAddressPrefixLength,
        tmnxWlanGwDsmIpFilN3DestPortOp    INTEGER,
        tmnxWlanGwDsmIpFilN3DestPort1     InetPortNumber
    }
    
tmnxWlanGwDsmIpFilN3Index OBJECT-TYPE
    SYNTAX      Unsigned32 (1..1024)
    MAX-ACCESS  not-accessible
    STATUS      current
    DESCRIPTION
        "The value of tmnxWlanGwDsmIpFilN3Index specifies the index
         of this filter entry."
   ::= { tmnxWlanGwDsmIpFilN3Entry 1 }

tmnxWlanGwDsmIpFilN3RowStatus OBJECT-TYPE
    SYNTAX      RowStatus
    MAX-ACCESS  read-create
    STATUS      current
    DESCRIPTION
        "The value of tmnxWlanGwDsmIpFilN3RowStatus controls the creation and
         deletion of rows in the table."
    ::= { tmnxWlanGwDsmIpFilN3Entry 2 }

tmnxWlanGwDsmIpFilN3LastCh OBJECT-TYPE
    SYNTAX      TimeStamp
    MAX-ACCESS  read-only
    STATUS      current
    DESCRIPTION
        "The value tmnxWlanGwDsmIpFilN3LastCh indicates the sysUpTime at
         the time of the most recent management-initiated change to this
         conceptual row."
    ::= { tmnxWlanGwDsmIpFilN3Entry 3 }

tmnxWlanGwDsmIpFilN3Description OBJECT-TYPE
    SYNTAX      TItemDescription
    MAX-ACCESS  read-create
    STATUS      current
    DESCRIPTION
        "The value of tmnxWlanGwDsmIpFilN3Description specifies the user provided
         description of this subscriber ISA RADIUS policy."
    DEFVAL { "" }
    ::= { tmnxWlanGwDsmIpFilN3Entry 4 }

tmnxWlanGwDsmIpFilN3Action OBJECT-TYPE
    SYNTAX      TmnxWlanGwDsmFilterActionOrNone
    MAX-ACCESS  read-create
    STATUS      current
    DESCRIPTION
        "The value of the object tmnxWlanGwDsmIpFilN3Action specifies
         the action to take for packets that match this filter entry."
    DEFVAL { none }
    ::= { tmnxWlanGwDsmIpFilN3Entry 5 }

tmnxWlanGwDsmIpFilN3Protocol OBJECT-TYPE
    SYNTAX      TIpProtocol
    MAX-ACCESS  read-create
    STATUS      current
    DESCRIPTION
        "The value of the object tmnxWlanGwDsmIpFilN3Protocol specifies
         the IP protocol to match.  
         
         The value minus one specifies no IP protocol matching."
    DEFVAL { -1 }
    ::= { tmnxWlanGwDsmIpFilN3Entry 6 }
    
tmnxWlanGwDsmIpFilN3DestAddrType OBJECT-TYPE
    SYNTAX      InetAddressType
    MAX-ACCESS  read-create
    STATUS      current
    DESCRIPTION 
        "The value of tmnxWlanGwDsmIpFilN3DestAddrType specifies
         the address type of tmnxWlanGwDsmIpFilN3DestAddr.
         
         The values  supported are 'unknown' and 'ipv4'."
    DEFVAL { unknown }
    ::= { tmnxWlanGwDsmIpFilN3Entry 7 }

tmnxWlanGwDsmIpFilN3DestAddr OBJECT-TYPE
    SYNTAX      InetAddress (SIZE(0|4))
    MAX-ACCESS  read-create
    STATUS      current
    DESCRIPTION 
        "The value of tmnxWlanGwDsmIpFilN3DestAddr specifies
         the IP address of the destination prefix to match."
    DEFVAL { ''H }
        ::= { tmnxWlanGwDsmIpFilN3Entry 8 }

tmnxWlanGwDsmIpFilN3DestPrefLen OBJECT-TYPE
    SYNTAX      InetAddressPrefixLength (0..32)
    MAX-ACCESS  read-create
    STATUS      current
    DESCRIPTION 
        "The value of tmnxWlanGwDsmIpFilN3DestPrefLen specifies
         the length of the destination prefix to match."
    DEFVAL { 0 }
    ::= { tmnxWlanGwDsmIpFilN3Entry 9 }

tmnxWlanGwDsmIpFilN3DestPortOp OBJECT-TYPE
    SYNTAX      INTEGER {
                    none(0),
                    eq(1)
                }
    MAX-ACCESS  read-create
    STATUS      current
    DESCRIPTION
        "The value of the object tmnxWlanGwDsmIpFilN3DestPortOp specifies
         the operation to perform on the object tmnxWlanGwDsmIpFilN3DestPort1."
    DEFVAL { none }
    ::= { tmnxWlanGwDsmIpFilN3Entry 10 }

tmnxWlanGwDsmIpFilN3DestPort1 OBJECT-TYPE
    SYNTAX      InetPortNumber
    MAX-ACCESS  read-create
    STATUS      current
    DESCRIPTION
        "The value of this object specifies the value to compare
         with the destination port in each packet, according to
         the value of the object tmnxWlanGwDsmIpFilN3DestPortOp."
    DEFVAL { 0 }
    ::= { tmnxWlanGwDsmIpFilN3Entry 11 }

--
--      The Distributed subscriber management IP Filter Entry Table for IPv6
--

tmnxWlanGwDsmIpFil6N3Table OBJECT-TYPE
    SYNTAX      SEQUENCE OF TmnxWlanGwDsmIpFil6N3Entry
    MAX-ACCESS  not-accessible
    STATUS      current
    DESCRIPTION
        "The tmnxWlanGwDsmIpFil6N3Table allows configuration of 
         distributed-sub-mgmt IPv6 filter entries."
    ::= { tmnxWlanGwDsmSubObjs 8 }

tmnxWlanGwDsmIpFil6N3Entry OBJECT-TYPE
    SYNTAX      TmnxWlanGwDsmIpFil6N3Entry
    MAX-ACCESS  not-accessible
    STATUS      current
    DESCRIPTION
        "Each row represents the configuration for a particular
         filter entry of a distributed-sub-mgmt IPv6 filter.
         
         Each row contains match criteria and the action to take
         for matching packets. 
        
         Rows in this table can be created and deleted
         via SNMP SET operations to tmnxWlanGwDsmIpFil6N3RowStatus."
    INDEX { tmnxWlanGwDsmIpFilName,
            tmnxWlanGwDsmIpFil6N3Index }
    ::= { tmnxWlanGwDsmIpFil6N3Table 1 }

TmnxWlanGwDsmIpFil6N3Entry ::=
    SEQUENCE {
        tmnxWlanGwDsmIpFil6N3Index         Unsigned32,
        tmnxWlanGwDsmIpFil6N3RowStatus     RowStatus,
        tmnxWlanGwDsmIpFil6N3LastCh        TimeStamp,
        tmnxWlanGwDsmIpFil6N3Description   TItemDescription,
        tmnxWlanGwDsmIpFil6N3Action        TmnxWlanGwDsmFilterActionOrNone,
        tmnxWlanGwDsmIpFil6N3Protocol      TIpProtocol,
        tmnxWlanGwDsmIpFil6N3DestAddrTyp   InetAddressType,
        tmnxWlanGwDsmIpFil6N3DestAddr      InetAddress,
        tmnxWlanGwDsmIpFil6N3DestPrefLen   InetAddressPrefixLength,
        tmnxWlanGwDsmIpFil6N3DestPortOp    INTEGER,
        tmnxWlanGwDsmIpFil6N3DestPort1     InetPortNumber
    }
    
tmnxWlanGwDsmIpFil6N3Index OBJECT-TYPE
    SYNTAX      Unsigned32 (1..1024)
    MAX-ACCESS  not-accessible
    STATUS      current
    DESCRIPTION
        "The value of tmnxWlanGwDsmIpFil6N3Index specifies the index
         of this filter entry."
   ::= { tmnxWlanGwDsmIpFil6N3Entry 1 }

tmnxWlanGwDsmIpFil6N3RowStatus OBJECT-TYPE
    SYNTAX      RowStatus
    MAX-ACCESS  read-create
    STATUS      current
    DESCRIPTION
        "The value of tmnxWlanGwDsmIpFil6N3RowStatus controls the creation and
         deletion of rows in the table."
    ::= { tmnxWlanGwDsmIpFil6N3Entry 2 }

tmnxWlanGwDsmIpFil6N3LastCh OBJECT-TYPE
    SYNTAX      TimeStamp
    MAX-ACCESS  read-only
    STATUS      current
    DESCRIPTION
        "The value tmnxWlanGwDsmIpFil6N3LastCh indicates the sysUpTime at
         the time of the most recent management-initiated change to this
         conceptual row."
    ::= { tmnxWlanGwDsmIpFil6N3Entry 3 }

tmnxWlanGwDsmIpFil6N3Description OBJECT-TYPE
    SYNTAX      TItemDescription
    MAX-ACCESS  read-create
    STATUS      current
    DESCRIPTION
        "The value of tmnxWlanGwDsmIpFil6N3Description specifies the user provided
         description of this subscriber ISA RADIUS policy."
    DEFVAL { "" }
    ::= { tmnxWlanGwDsmIpFil6N3Entry 4 }

tmnxWlanGwDsmIpFil6N3Action OBJECT-TYPE
    SYNTAX      TmnxWlanGwDsmFilterActionOrNone
    MAX-ACCESS  read-create
    STATUS      current
    DESCRIPTION
        "The value of the object tmnxWlanGwDsmIpFil6N3Action specifies
         the action to take for packets that match this filter entry."
    DEFVAL { none }
    ::= { tmnxWlanGwDsmIpFil6N3Entry 5 }

tmnxWlanGwDsmIpFil6N3Protocol OBJECT-TYPE
    SYNTAX      TIpProtocol
    MAX-ACCESS  read-create
    STATUS      current
    DESCRIPTION
        "The value of the object tmnxWlanGwDsmIpFil6N3Protocol specifies
         the IP protocol to match.  
         
         The value minus one specifies no IP protocol matching."
    DEFVAL { -1 }
    ::= { tmnxWlanGwDsmIpFil6N3Entry 6 }
    
tmnxWlanGwDsmIpFil6N3DestAddrTyp OBJECT-TYPE
    SYNTAX      InetAddressType
    MAX-ACCESS  read-create
    STATUS      current
    DESCRIPTION 
        "The value of tmnxWlanGwDsmIpFil6N3DestAddrTyp specifies
         the address type of tmnxWlanGwDsmIpFil6N3DestAddr.
         
         The values supported are 'unknown' and 'ipv6'."
    DEFVAL { unknown }
    ::= { tmnxWlanGwDsmIpFil6N3Entry 7 }

tmnxWlanGwDsmIpFil6N3DestAddr OBJECT-TYPE
    SYNTAX      InetAddress (SIZE(0|16))
    MAX-ACCESS  read-create
    STATUS      current
    DESCRIPTION 
        "The value of tmnxWlanGwDsmIpFil6N3DestAddr specifies
         the IPv6 address of the destination prefix to match."
    DEFVAL { ''H }
        ::= { tmnxWlanGwDsmIpFil6N3Entry 8 }

tmnxWlanGwDsmIpFil6N3DestPrefLen OBJECT-TYPE
    SYNTAX      InetAddressPrefixLength (0..128)
    MAX-ACCESS  read-create
    STATUS      current
    DESCRIPTION 
        "The value of tmnxWlanGwDsmIpFil6N3DestPrefLen specifies
         the length of the destination prefix to match."
    DEFVAL { 0 }
    ::= { tmnxWlanGwDsmIpFil6N3Entry 9 }

tmnxWlanGwDsmIpFil6N3DestPortOp OBJECT-TYPE
    SYNTAX      INTEGER {
                    none(0),
                    eq(1)
                }
    MAX-ACCESS  read-create
    STATUS      current
    DESCRIPTION
        "The value of the object tmnxWlanGwDsmIpFil6N3DestPortOp specifies
         the operation to perform on the object tmnxWlanGwDsmIpFil6N3DestPort1."
    DEFVAL { none }
    ::= { tmnxWlanGwDsmIpFil6N3Entry 10 }

tmnxWlanGwDsmIpFil6N3DestPort1 OBJECT-TYPE
    SYNTAX      InetPortNumber
    MAX-ACCESS  read-create
    STATUS      current
    DESCRIPTION
        "The value of this object specifies the value to compare
         with the destination port in each packet, according to
         the value of the object tmnxWlanGwDsmIpFil6N3DestPortOp."
    DEFVAL { 0 }
    ::= { tmnxWlanGwDsmIpFil6N3Entry 11 }
    
--
--      The Distributed subscriber management Policer Table
--

tmnxWlanGwPolicerTable OBJECT-TYPE
    SYNTAX      SEQUENCE OF TmnxWlanGwPolicerEntry
    MAX-ACCESS  not-accessible
    STATUS      current
    DESCRIPTION
        "The tmnxWlanGwPolicerTable allows configuration of 
         traffic policer templates distributed on ISA cards 
         for DSM subscribers."
    ::= { tmnxWlanGwDsmSubObjs 4 }

tmnxWlanGwPolicerEntry     OBJECT-TYPE
    SYNTAX      TmnxWlanGwPolicerEntry
    MAX-ACCESS  not-accessible
    STATUS      current
    DESCRIPTION
        "Each conceptual row represents the configuration
         for a specific distributed-sub-mgmt traffic policer template.

         Rows in this table can be created and deleted via SNMP SET
         operations to tmnxWlanGwPolicerRowStatus."
    INDEX { IMPLIED tmnxWlanGwPolicerName }
    ::= { tmnxWlanGwPolicerTable 1 }

TmnxWlanGwPolicerEntry ::=
    SEQUENCE {
        tmnxWlanGwPolicerName            TNamedItem,
        tmnxWlanGwPolicerRowLastChange   TimeStamp,
        tmnxWlanGwPolicerRowStatus       RowStatus,
        tmnxWlanGwPolicerDescription     TItemDescription,
        tmnxWlanGwPolicerType            INTEGER,
        tmnxWlanGwPolicerAction          INTEGER,
        tmnxWlanGwPolicerAdminPIR        TPIRRate,
        tmnxWlanGwPolicerAdminCIR        TCIRRate,
        tmnxWlanGwPolicerMBS             TmnxWlanGwBurstSize,
        tmnxWlanGwPolicerCBS             TmnxWlanGwBurstSize,
        tmnxWlanGwPolicerPIRAdaptation   TAdaptationRule,
        tmnxWlanGwPolicerCIRAdaptation   TAdaptationRule
    }

tmnxWlanGwPolicerName  OBJECT-TYPE
    SYNTAX      TNamedItem
    MAX-ACCESS  not-accessible
    STATUS      current
    DESCRIPTION
        "The value of tmnxWlanGwPolicerName specifies the
         name defined for the policerlication."
    ::= { tmnxWlanGwPolicerEntry 1 }

tmnxWlanGwPolicerRowLastChange  OBJECT-TYPE
    SYNTAX       TimeStamp
    MAX-ACCESS   read-only
    STATUS       current
    DESCRIPTION
        "The value of tmnxWlanGwPolicerRowLastChange indicates the
         last time, since system startup, a successful set was
         performed on this row."
    ::= { tmnxWlanGwPolicerEntry 2 }
    
tmnxWlanGwPolicerRowStatus  OBJECT-TYPE
    SYNTAX      RowStatus
    MAX-ACCESS  read-create
    STATUS      current
    DESCRIPTION
        "The value of tmnxWlanGwPolicerRowStatus specifies the
         row status of this row."
    ::= { tmnxWlanGwPolicerEntry 3 }

tmnxWlanGwPolicerDescription  OBJECT-TYPE
    SYNTAX      TItemDescription
    MAX-ACCESS  read-create
    STATUS      current
    DESCRIPTION
        "The value of tmnxWlanGwPolicerDescription specifies the
         description of the policer."
    DEFVAL      { "" }
    ::= { tmnxWlanGwPolicerEntry 4 }

tmnxWlanGwPolicerType  OBJECT-TYPE
    SYNTAX      INTEGER {
                    singleBucketBandwidth    (0),
                    dualBucketBandwidth      (1)
                }
    MAX-ACCESS  read-create
    STATUS      current
    DESCRIPTION
        "The value of tmnxWlanGwPolicerType specifies 
         the number of buckets used by the policer.
         
         A value for this object must be specified when
         the conceptual row is created.
         
         The value of this object can not be modified 
         while this conceptual row exists."
    ::= { tmnxWlanGwPolicerEntry 5 }

tmnxWlanGwPolicerAction  OBJECT-TYPE
    SYNTAX      INTEGER {
                    permitDeny   (0),
                    priorityMark (1)
                }
    MAX-ACCESS  read-create
    STATUS      current
    DESCRIPTION
        "The value of tmnxWlanGwPolicerAction specifies if
         the action taken by the policer is to permit or drop
         the packet or is to mark the packet(s) as in-profile or 
         out-of-profile."
    DEFVAL      { permitDeny }
    ::= { tmnxWlanGwPolicerEntry 6 }

tmnxWlanGwPolicerAdminPIR OBJECT-TYPE
    SYNTAX       TPIRRate
    UNITS        "kbps"
    MAX-ACCESS   read-create
    STATUS       current
    DESCRIPTION
        "The value of tmnxWlanGwPolicerAdminPIR specifies the
         administrative PIR (Peak Information Rate)."
    DEFVAL { -1 }
    ::= { tmnxWlanGwPolicerEntry 7 }

tmnxWlanGwPolicerAdminCIR OBJECT-TYPE
    SYNTAX       TCIRRate
    UNITS        "kbps"
    MAX-ACCESS   read-create
    STATUS       current
    DESCRIPTION
        "The value of tmnxWlanGwPolicerAdminCIR specifies the
         administrative CIR specified by the user."
    DEFVAL { 0 }
    ::= { tmnxWlanGwPolicerEntry 8 }

tmnxWlanGwPolicerMBS OBJECT-TYPE
    SYNTAX       TmnxWlanGwBurstSize
    UNITS        "kilobytes"
    MAX-ACCESS   read-create
    STATUS       current
    DESCRIPTION
        "The value of tmnxWlanGwPolicerMBS specifies the
         maximum burst size specified by the user to
         be used in conjunction with the PIR."
    DEFVAL { 0 }
    ::= { tmnxWlanGwPolicerEntry 9 }

tmnxWlanGwPolicerCBS OBJECT-TYPE
    SYNTAX       TmnxWlanGwBurstSize
    UNITS        "kilobytes"
    MAX-ACCESS   read-create
    STATUS       current
    DESCRIPTION
        "The value of tmnxWlanGwPolicerCBS specifies the
         committed burst size specified by the user to
         be used in conjunction with the CIR."
    DEFVAL { 0 }
    ::= { tmnxWlanGwPolicerEntry 10 }

tmnxWlanGwPolicerPIRAdaptation OBJECT-TYPE
    SYNTAX       TAdaptationRule
    MAX-ACCESS   read-create
    STATUS       current
    DESCRIPTION
        "The value of tmnxWlanGwPolicerPIRAdaptation specifies the
         adaptation rule to be used while computing the operational PIR
         value. 
         
         The adaptation rule specifies the rules to compute the
         operational values while maintaining minimum offset."
    DEFVAL { closest }
    ::= { tmnxWlanGwPolicerEntry 11 }

tmnxWlanGwPolicerCIRAdaptation OBJECT-TYPE
    SYNTAX       TAdaptationRule
    MAX-ACCESS   read-create
    STATUS       current
    DESCRIPTION
        "The value of tmnxWlanGwPolicerCIRAdaptation specifies the
         adaptation rule to be used while computing the operational CIR
         value. The adaptation rule specifies the rules to compute the
         operational values while maintaining minimum offset."
    DEFVAL { closest }
    ::= { tmnxWlanGwPolicerEntry 12 }
    
--
--      The Distributed Subscriber Management table
--

tmnxWlanGwDsmTable   OBJECT-TYPE
    SYNTAX      SEQUENCE OF TmnxWlanGwDsmEntry
    MAX-ACCESS  not-accessible
    STATUS      current
    DESCRIPTION
       "The tmnxWlanGwDsmTable contains objects to configure
        the Distributed Subscriber Management (DSM) for
        WLAN Gateway interfaces."
    ::= { tmnxWlanGwDsmSubObjs 9 }
   
tmnxWlanGwDsmEntry   OBJECT-TYPE
    SYNTAX      TmnxWlanGwDsmEntry
    MAX-ACCESS  not-accessible
    STATUS      current
    DESCRIPTION
        "Each conceptual row represents a set of 
         Distributed Subscriber Management configuration data
         for a particular interface."
    AUGMENTS { tmnxWlanGwEntry }
    ::= { tmnxWlanGwDsmTable 1 }

TmnxWlanGwDsmEntry ::= 
    SEQUENCE {
        tmnxWlanGwDsmLastCh              TimeStamp,
        tmnxWlanGwDsmIpv6TcpMssAdjust    Unsigned32
    }

tmnxWlanGwDsmLastCh OBJECT-TYPE
    SYNTAX      TimeStamp
    MAX-ACCESS  read-only
    STATUS      current
    DESCRIPTION
        "The value of tmnxWlanGwDsmLastCh indicates the sysUpTime at
         the time of the most recent management-initiated change to
         this table row."
    ::= { tmnxWlanGwDsmEntry 1 }

tmnxWlanGwDsmIpv6TcpMssAdjust OBJECT-TYPE
    SYNTAX      Unsigned32 (0|160..10240)
    UNITS       "bytes"
    MAX-ACCESS  read-create
    STATUS      current
    DESCRIPTION
        "The value of tmnxWlanGwDsmIpv6TcpMssAdjust specifies 
         the value to put into the TCP Maximum Segment Size (MSS) option
         if not already present, or if the present value is higher.
         
         The value zero means that no MSS option adjustment is done."
    DEFVAL { 0 }
    ::= { tmnxWlanGwDsmEntry 2 }

-- ----------------------------------------------------------------------------
-- User Equipment (UE)
-- ----------------------------------------------------------------------------     

-- UE Query Usage:
--
-- (1) Get a unique query ID by means of an SNMP get-request on the
-- tmnxWlanGwUeNextQryId object;
-- (2) Create a conceptual row in the query table tmnxWlanGwUeQryTable
-- with the unique query ID as index;
-- get the number of matching UE's by reading tmnxWlanGwUeQryNumResults
-- and refine the search criteria if necessary.
-- (3) Get the result by walking the result table tmnxWlanGwUeResTable
-- within the scope of the same unique query ID.
 
-- The next query ID

tmnxWlanGwUeNextQryId OBJECT-TYPE
    SYNTAX      Unsigned32
    MAX-ACCESS  read-only
    STATUS      current
    DESCRIPTION
        "The value of the object tmnxWlanGwUeNextQryId indicates
         the next available unique query identifier to use in
         User Equipment queries.
         
         Multiple concurrent queries are supported; each query and its
         results are identified with a unique query ID supplied by the
         system."
    ::= { tmnxWlanGwUeObjs 1 }

tmnxWlanGwUeMaxQryId OBJECT-TYPE
    SYNTAX      Unsigned32
    MAX-ACCESS  read-only
    STATUS      current
    DESCRIPTION
        "The value of the object tmnxWlanGwUeMaxQryId indicates
         the maximum value of a query identifier for use in
         User Equipment queries.
         
         Multiple concurrent queries are supported; each query and its
         results are identified with a unique query ID supplied by the
         system.
         
         The value of the object tmnxWlanGwUeMaxQryId indicates
         also the maximum number of concurrent queries."
    ::= { tmnxWlanGwUeObjs 2 }

-- The query table

tmnxWlanGwUeQryTable OBJECT-TYPE
    SYNTAX      SEQUENCE OF TmnxWlanGwUeQryEntry
    MAX-ACCESS  not-accessible
    STATUS      current
    DESCRIPTION
       "The tmnxWlanGwUeQryTable contains queries for
        User Equipment.
        
        Conceptual rows in this table are created and destroyed
        by means of SNMP operations on the tmnxWlanGwUeQryRowStatus object.
        
        Conceptual rows in this table are volatile: they are lost upon reboot
        or switchover."
    ::= { tmnxWlanGwUeObjs 3 }

tmnxWlanGwUeQryEntry OBJECT-TYPE
    SYNTAX          TmnxWlanGwUeQryEntry
    MAX-ACCESS      not-accessible
    STATUS          current
    DESCRIPTION
        "Each conceptual row represents a query for User Equipment.

         Entries in this table can be created or deleted by means of 
         SNMP operations on the tmnxWlanGwUeQryRowStatus object."
    INDEX { tmnxWlanGwUeQryId }
    ::= { tmnxWlanGwUeQryTable 1 }

TmnxWlanGwUeQryEntry ::= 
    SEQUENCE {
        tmnxWlanGwUeQryId                Unsigned32,
        tmnxWlanGwUeQryRowStatus         RowStatus,
        tmnxWlanGwUeQryWhereState        BITS,
        tmnxWlanGwUeQryWhereMacAddress   MacAddress,
        tmnxWlanGwUeQryWhereAddrType     InetAddressType,
        tmnxWlanGwUeQryWhereAddr         InetAddress,
        tmnxWlanGwUeQryWhereIsaGrp       TmnxWlanGwIsaGrpIdOrZero,
        tmnxWlanGwUeQryWhereMemberId     Unsigned32, 
        tmnxWlanGwUeQryWhereQTag         QTagFullRangeOrNone,       
        tmnxWlanGwUeQryWhereTuRouter     TmnxVRtrIDOrZero,
        tmnxWlanGwUeQryWhereTuRemAddrTyp InetAddressType,
        tmnxWlanGwUeQryWhereTuRemAddr    InetAddress,
        tmnxWlanGwUeQryWhereTuLocAddrTyp InetAddressType,
        tmnxWlanGwUeQryWhereTuLocAddr    InetAddress,
        tmnxWlanGwUeQryWhereEncap        TmnxWlanGwUeEncapsulation,
        tmnxWlanGwUeQryWhereSlaacPrefTyp InetAddressType,
        tmnxWlanGwUeQryWhereSlaacPref    InetAddress,
        tmnxWlanGwUeQryWhereDhcp6AddrTyp InetAddressType,
        tmnxWlanGwUeQryWhereDhcp6Addr    InetAddress,
        tmnxWlanGwUeQryNumResults        Gauge32
    }

tmnxWlanGwUeQryId OBJECT-TYPE
    SYNTAX      Unsigned32
    MAX-ACCESS  not-accessible
    STATUS      current
    DESCRIPTION
       "The value of tmnxWlanGwUeQryId specifies the query ID of this User Equipment query.
       
        Get a unique query ID by means of an SNMP get on the tmnxWlanGwUeNextQryId
        object."
    ::= { tmnxWlanGwUeQryEntry 1 }

tmnxWlanGwUeQryRowStatus OBJECT-TYPE
    SYNTAX      RowStatus
    MAX-ACCESS  read-create
    STATUS      current
    DESCRIPTION
       "The value of tmnxWlanGwUeQryRowStatus specifies the row status of this row."
    ::= { tmnxWlanGwUeQryEntry 2 }

tmnxWlanGwUeQryWhereState OBJECT-TYPE
    SYNTAX      BITS {
                    bDataTriggered (0),
                    bDhcpTriggered (1),
                    bIpAssigned (2),
                    bAuthorizedOnly (3),
                    bIpAssignedAuthorized (4),
                    bAlreadySignedIn (5),
                    bPortal (6),
                    bDistributedSubMgmt (7),
                    bEsmUser (8),
                    bL2User (9),
                    reserved10 (10),
                    bDeletePending (11)
                }
    MAX-ACCESS  read-create
    STATUS      current
    DESCRIPTION
       "The value of tmnxWlanGwUeQryWhereState specifies 
        the set of UE state values.
        
        When the value of tmnxWlanGwUeQryWhereState is not all zeroes,
        the tmnxWlanGwUeResTable will contain only rows with this query ID
        where the value of the object tmnxWlanGwUeResState is equal to
        one of the states corresponding to the bits set in tmnxWlanGwUeQryWhereState.
        
        Setting the value of tmnxWlanGwUeQryWhereState to all zeroes
        is equivalent of setting it to all ones, and specifies
        that the tmnxWlanGwUeResTable may contain rows with this query ID
        having any value of the object tmnxWlanGwUeResState."
    DEFVAL { { } }
    ::= { tmnxWlanGwUeQryEntry 3 }
 
tmnxWlanGwUeQryWhereMacAddress OBJECT-TYPE
    SYNTAX      MacAddress
    MAX-ACCESS  read-create
    STATUS      current
    DESCRIPTION
        "The value of the object tmnxWlanGwUeQryWhereMacAddress specifies
         the MAC address.
         
         When the value of tmnxWlanGwUeQryWhereMacAddress is not all zeroes,
         the tmnxWlanGwUeResTable will contain only rows with this query ID
         where the value of tmnxWlanGwUeResMacAddress is equal to this value." 
    DEFVAL { '000000000000'H }
    ::= { tmnxWlanGwUeQryEntry 4 }

tmnxWlanGwUeQryWhereAddrType OBJECT-TYPE
    SYNTAX      InetAddressType
    MAX-ACCESS  read-create
    STATUS      current
    DESCRIPTION
        "The value of tmnxWlanGwUeQryWhereAddrType specifies
         the type of the User Equipment's IP address.
         
         When the value of tmnxWlanGwUeQryWhereAddrType is not 'unknown',
         the tmnxWlanGwUeResTable will contain only rows with this query ID
         where the value of tmnxWlanGwUeResAddrType is equal to this value."
    DEFVAL { unknown }
    ::= { tmnxWlanGwUeQryEntry 5 }

tmnxWlanGwUeQryWhereAddr OBJECT-TYPE
    SYNTAX      InetAddress (SIZE(0|4|16))
    MAX-ACCESS  read-create
    STATUS      current
    DESCRIPTION
        "The value of tmnxWlanGwUeQryWhereAddr specifies 
         the IP address of the remote endpoint of the UE tunnel.
         
         When the value of tmnxWlanGwUeQryWhereAddr is not empty,
         the tmnxWlanGwUeResTable will contain only rows
         where the value of tmnxWlanGwUeResAddr is equal to this value."
    DEFVAL { ''H }  
    ::= { tmnxWlanGwUeQryEntry 6 }
    
tmnxWlanGwUeQryWhereIsaGrp OBJECT-TYPE
    SYNTAX      TmnxWlanGwIsaGrpIdOrZero
    MAX-ACCESS  read-create
    STATUS      current
    DESCRIPTION
        "The value of tmnxWlanGwUeQryWhereIsaGrp specifies 
         the identifier of the WLAN Gateway Integrated Service Adaptor group.
         
         When the value of tmnxWlanGwUeQryWhereIsaGrp is non-zero,
         the tmnxWlanGwUeResTable will contain only rows with this query ID
         where the WLAN Gateway ISA group is equal to this value."
    DEFVAL { 0 }
    ::= { tmnxWlanGwUeQryEntry 7 }

tmnxWlanGwUeQryWhereMemberId OBJECT-TYPE
    SYNTAX      Unsigned32
    MAX-ACCESS  read-create
    STATUS      current
    DESCRIPTION
        "The value of tmnxWlanGwUeQryWhereMemberId specifies 
         the identifier of the WLAN Gateway ISA Group member.
         
         When the value of tmnxWlanGwUeQryWhereMemberId is non-zero,
         the tmnxWlanGwUeResTable will contain only rows with this query ID
         where the WLAN Gateway ISA Group member is equal to this value."
    DEFVAL { 0 }
    ::= { tmnxWlanGwUeQryEntry 8 }

tmnxWlanGwUeQryWhereQTag OBJECT-TYPE
    SYNTAX      QTagFullRangeOrNone
    MAX-ACCESS  read-create
    STATUS      current
    DESCRIPTION
        "The value of tmnxWlanGwUeQryWhereQTag specifies 
         the VLAN Q-tag present in the traffic received from a UE.
         
         When the value of tmnxWlanGwUeQryWhereQTag is non-zero,
         the tmnxWlanGwUeResTable will contain only rows with this query ID
         where the value of tmnxWlanGwUeResQTag is equal to this value." 
    DEFVAL { -1 }
    ::= { tmnxWlanGwUeQryEntry 9 }

tmnxWlanGwUeQryWhereTuRouter OBJECT-TYPE
    SYNTAX      TmnxVRtrIDOrZero
    MAX-ACCESS  read-create
    STATUS      current
    DESCRIPTION
        "The value of tmnxWlanGwUeQryWhereTuRouter specifies 
         the virtual router instance.
         
         When the value of tmnxWlanGwUeQryWhereTuRouter is non-zero,
         the tmnxWlanGwUeResTable will contain only rows with this query ID
         where the value of tmnxWlanGwUeResTuRouter is equal to this value." 
    DEFVAL { 0 }
    ::= { tmnxWlanGwUeQryEntry 10 }
    
tmnxWlanGwUeQryWhereTuRemAddrTyp OBJECT-TYPE
    SYNTAX      InetAddressType
    MAX-ACCESS  read-create
    STATUS      current
    DESCRIPTION
        "The value of tmnxWlanGwUeQryWhereTuRemAddrTyp specifies
         the type of tmnxWlanGwUeQryWhereTuRemAddr.
         
         When the value of tmnxWlanGwUeQryWhereTuRemAddrTyp is not 'unknown',
         the tmnxWlanGwUeResTable will contain only rows with this query ID
         where the value of tmnxWlanGwUeResTuAddrType is equal to this value."
    DEFVAL { unknown }
    ::= { tmnxWlanGwUeQryEntry 11 }

tmnxWlanGwUeQryWhereTuRemAddr OBJECT-TYPE
    SYNTAX      InetAddress (SIZE(0|4|16))
    MAX-ACCESS  read-create
    STATUS      current
    DESCRIPTION
        "The value of tmnxWlanGwUeQryWhereTuRemAddr specifies 
         the IP address of the remote endpoint of the UE tunnel.
         
         When the value of tmnxWlanGwUeQryWhereTuRemAddr is not empty,
         the tmnxWlanGwUeResTable will contain only rows
         where the value of tmnxWlanGwUeResTuRemoteAddr is equal to this value."
    DEFVAL { ''H }  
    ::= { tmnxWlanGwUeQryEntry 12 }
    
tmnxWlanGwUeQryWhereTuLocAddrTyp OBJECT-TYPE
    SYNTAX      InetAddressType
    MAX-ACCESS  read-create
    STATUS      current
    DESCRIPTION
        "The value of tmnxWlanGwUeQryWhereTuLocAddrTyp specifies
         the type of tmnxWlanGwUeQryWhereTuLocAddr.
         
         When the value of tmnxWlanGwUeQryWhereTuRemAddrTyp is not 'unknown',
         the tmnxWlanGwUeResTable will contain only rows with this query ID
         where the value of tmnxWlanGwUeResTuAddrType is equal to this value."
    DEFVAL { unknown }
    ::= { tmnxWlanGwUeQryEntry 13 }

tmnxWlanGwUeQryWhereTuLocAddr OBJECT-TYPE
    SYNTAX      InetAddress (SIZE(0|4|16))
    MAX-ACCESS  read-create
    STATUS      current
    DESCRIPTION
        "The value of tmnxWlanGwUeQryWhereTuLocAddr specifies 
         the IP address of the local endpoint of the UE tunnel.
         
         When the value of tmnxWlanGwUeQryWhereTuLocAddr is not empty,
         the tmnxWlanGwUeResTable will contain only rows with this query ID
         where the value of tmnxWlanGwUeResTuLocalAddr is equal to this value."
    DEFVAL { ''H }  
    ::= { tmnxWlanGwUeQryEntry 14 }
    
tmnxWlanGwUeQryWhereEncap OBJECT-TYPE
    SYNTAX      TmnxWlanGwUeEncapsulation
    MAX-ACCESS  read-create
    STATUS      current
    DESCRIPTION
        "The value of tmnxWlanGwUeQryWhereEncap specifies 
         the encapsulation type present in the traffic received from a UE.
         
         When the value of tmnxWlanGwUeQryWhereEncap is non-zero,
         the tmnxWlanGwUeResTable will contain only rows with this query ID
         where the value of tmnxWlanGwUeResEncapsulation is equal to this value." 
    DEFVAL { notSpecified }
    ::= { tmnxWlanGwUeQryEntry 15 }

tmnxWlanGwUeQryWhereSlaacPrefTyp OBJECT-TYPE
    SYNTAX      InetAddressType
    MAX-ACCESS  read-create
    STATUS      current
    DESCRIPTION
        "The value of tmnxWlanGwUeQryWhereSlaacPrefTyp specifies the type
         of tmnxWlanGwUeQryWhereSlaacPref.
         
         When the value of tmnxWlanGwUeQryWhereSlaacPrefTyp is not 'unknown',
         the tmnxWlanGwUeResTable will contain only rows with this query ID
         where the value of tmnxWlanGwUeQryWhereSlaacPrefTyp is equal to this value."
    DEFVAL { unknown }
    ::= { tmnxWlanGwUeQryEntry 16 }

tmnxWlanGwUeQryWhereSlaacPref OBJECT-TYPE
    SYNTAX      InetAddress (SIZE(0|16))
    MAX-ACCESS  read-create
    STATUS      current
    DESCRIPTION
        "The value of tmnxWlanGwUeQryWhereSlaacPref specifies the IPv6 prefix
         used to filter on new SLAAC prefixes.
         
         When the value of tmnxWlanGwUeQryWhereSlaacPref is not empty,
         the tmnxWlanGwUeResTable will contain only rows with this query ID
         where the value of tmnxWlanGwUeQryWhereSlaacPref is equal to this value."
    DEFVAL { ''H }  
    ::= { tmnxWlanGwUeQryEntry 17 }

tmnxWlanGwUeQryWhereDhcp6AddrTyp OBJECT-TYPE
    SYNTAX      InetAddressType
    MAX-ACCESS  read-create
    STATUS      current
    DESCRIPTION
        "The value of tmnxWlanGwUeQryWhereDhcp6AddrTyp specifies the type
         of tmnxWlanGwUeQryWhereDhcp6Addr.
         
         When the value of tmnxWlanGwUeQryWhereDhcp6AddrTyp is not 'unknown',
         the tmnxWlanGwUeResTable will contain only rows with this query ID
         where the value of tmnxWlanGwUeQryWhereDhcp6AddrTyp is equal to this value."
    DEFVAL { unknown }
    ::= { tmnxWlanGwUeQryEntry 18 }

tmnxWlanGwUeQryWhereDhcp6Addr OBJECT-TYPE
    SYNTAX      InetAddress (SIZE(0|16))
    MAX-ACCESS  read-create
    STATUS      current
    DESCRIPTION
        "The value of tmnxWlanGwUeQryWhereDhcp6Addr specifies the IPv6 address
         used to filter on new DHCPv6 addresses.
         
         When the value of tmnxWlanGwUeQryWhereDhcp6Addr is not empty,
         the tmnxWlanGwUeResTable will contain only rows with this query ID
         where the value of tmnxWlanGwUeQryWhereDhcp6Addr is equal to this value."
    DEFVAL { ''H }  
    ::= { tmnxWlanGwUeQryEntry 19 }

tmnxWlanGwUeQryNumResults OBJECT-TYPE
    SYNTAX      Gauge32
    MAX-ACCESS  read-only
    STATUS      current
    DESCRIPTION
        "The value of tmnxWlanGwUeQryNumResults indicates
         the current number of User Equipment matching this query.
         
         It is recommended to examine this value before starting
         to read the tmnxWlanGwUeResTable."
    ::= { tmnxWlanGwUeQryEntry 200 }

    
--  The query result table


tmnxWlanGwUeResTable OBJECT-TYPE
    SYNTAX      SEQUENCE OF TmnxWlanGwUeResEntry
    MAX-ACCESS  not-accessible
    STATUS      current
    DESCRIPTION
       "The tmnxWlanGwUeResTable contains the results
        of one or more queries for User Equipment."
    ::= { tmnxWlanGwUeObjs 4 }

tmnxWlanGwUeResEntry OBJECT-TYPE
    SYNTAX      TmnxWlanGwUeResEntry
    MAX-ACCESS  not-accessible
    STATUS      current
    DESCRIPTION
        "Each conceptual row represents a UE.

         Conceptual rows in this table are created and destroyed automatically
         by the system.        
        
         Conceptual rows in this table are volatile: they are lost upon reboot
         or switchover.
         
         The system creates rows in this table as a result of the
         creation of a row in the query table tmnxWlanGwUeQryTable,
         and destroys them when that row is destroyed."
    INDEX { tmnxWlanGwUeQryId,
            tmnxWlanGwUeResId
          }
    ::= { tmnxWlanGwUeResTable 1 }

TmnxWlanGwUeResEntry ::= 
    SEQUENCE {
        tmnxWlanGwUeResId                TmnxWlanGwUeIdentifier,      
        tmnxWlanGwUeResMacAddress        MacAddress,
        tmnxWlanGwUeResQTag              QTagFullRangeOrNone,       
        tmnxWlanGwUeResAddrType          InetAddressType,
        tmnxWlanGwUeResAddr              InetAddress,
        tmnxWlanGwUeResState             INTEGER,
        tmnxWlanGwUeResIsaGrp            TmnxWlanGwIsaGrpIdOrZero,
        tmnxWlanGwUeResIsaMemberId       Unsigned32,       
        tmnxWlanGwUeResTuRouter          TmnxVRtrIDOrZero,
        tmnxWlanGwUeResTuAddrType        InetAddressType,
        tmnxWlanGwUeResTuRemoteAddr      InetAddress,
        tmnxWlanGwUeResTuLocalAddr       InetAddress,
        tmnxWlanGwUeResEncapsulation     TmnxWlanGwUeEncapsulation,
        tmnxWlanGwUeResApMacAddress      MacAddress,
        tmnxWlanGwUeResSsid              TNamedItemOrEmpty,
        tmnxWlanGwUeResMplsLabel         MplsLabel,
        tmnxWlanGwUeResLastMoveTime      DateAndTime,
        tmnxWlanGwUeResExpirationTime    DateAndTime,
        tmnxWlanGwUeResIdleTimeout       Unsigned32,
        tmnxWlanGwUeResSessionTimeout    DateAndTime,
        tmnxWlanGwUeResNatPlcy           TNamedItemOrEmpty,
        tmnxWlanGwUeResHttpRdrPlcy       TNamedItemOrEmpty,
        tmnxWlanGwUeResDsmIpFilter       TNamedItemOrEmpty,
        tmnxWlanGwUeResDsmAcctPlcy       TNamedItemOrEmpty,
        tmnxWlanGwUeResDsmAcctUpdInterv  Unsigned32,
        tmnxWlanGwUeResAcctUpdate        DateAndTime,
        tmnxWlanGwUeResIngOperPir        TPIRRate,
        tmnxWlanGwUeResIngOperCir        TCIRRate,
        tmnxWlanGwUeResEgrOperPir        TPIRRate,
        tmnxWlanGwUeResEgrOperCir        TCIRRate,
        tmnxWlanGwUeResDsmAppProfile     TNamedItemOrEmpty,
        tmnxWlanGwUeResRxPkts            Counter64,                    
        tmnxWlanGwUeResRxOctets          Counter64,                    
        tmnxWlanGwUeResTxPkts            Counter64,                    
        tmnxWlanGwUeResTxOctets          Counter64,
        tmnxWlanGwUeResSlaacAddrType     InetAddressType,
        tmnxWlanGwUeResSlaacPref         InetAddress,
        tmnxWlanGwUeResSlaacAddr1        InetAddress,
        tmnxWlanGwUeResSlaacAddr2        InetAddress,
        tmnxWlanGwUeResSlaacAddr3        InetAddress,
        tmnxWlanGwUeResDhcp6AddrType     InetAddressType,
        tmnxWlanGwUeResDhcp6Addr         InetAddress,
        tmnxWlanGwUeResDhcp6AddrDepr     TruthValue,
        tmnxWlanGwUeResDhcp6IAID         Unsigned32,
        tmnxWlanGwUeResDhcp6IAIDValid    TruthValue,
        tmnxWlanGwUeResSlaacLeaseExpire  DateAndTime,
        tmnxWlanGwUeResDhcp6LeaseExpire  DateAndTime
    }

tmnxWlanGwUeResId OBJECT-TYPE
    SYNTAX      TmnxWlanGwUeIdentifier
    MAX-ACCESS  not-accessible
    STATUS      current
    DESCRIPTION
        "The value of tmnxWlanGwUeResId indicates the identifier of 
         this User Equipment."
    ::= { tmnxWlanGwUeResEntry 1 }
    
tmnxWlanGwUeResMacAddress OBJECT-TYPE
    SYNTAX      MacAddress
    MAX-ACCESS  read-only
    STATUS      current
    DESCRIPTION
        "The value of the object tmnxWlanGwUeResMacAddress indicates
         the MAC address of this UE."
    ::= { tmnxWlanGwUeResEntry 2 }

tmnxWlanGwUeResQTag OBJECT-TYPE
    SYNTAX      QTagFullRangeOrNone
    MAX-ACCESS  read-only
    STATUS      current
    DESCRIPTION     
        "The value of the object tmnxWlanGwUeResQTag indicates
         the VLAN Q-tag present in the traffic received from this UE.
         
         The value of this object can be used to identify the retailer
         service, by means of the tmnxWlanGwIfRetailTable.
         
         The value minus one indicates that the traffic received from this UE
         does not have a VLAN Q-tag."
    ::= { tmnxWlanGwUeResEntry 3 }

tmnxWlanGwUeResAddrType OBJECT-TYPE
    SYNTAX      InetAddressType
    MAX-ACCESS  read-only
    STATUS      current
    DESCRIPTION 
        "The value of tmnxWlanGwUeResAddrType indicates
         the address type of tmnxWlanGwUeResAddr."
    ::= { tmnxWlanGwUeResEntry 4 }

tmnxWlanGwUeResAddr OBJECT-TYPE
    SYNTAX      InetAddress (SIZE(4|16))
    MAX-ACCESS  read-only
    STATUS      current
    DESCRIPTION
        "The value of the object tmnxWlanGwUeResAddr indicates
         the IP address this UE."
    ::= { tmnxWlanGwUeResEntry 5 }

tmnxWlanGwUeResState OBJECT-TYPE
    SYNTAX      INTEGER {
                    new (1),
                    dataTriggered (2),
                    dhcpTriggered (3),
                    ipAssigned (4),
                    authorizedOnly (5),
                    ipAssignedAuthorized (6),
                    alreadySignedIn (7),
                    portal (8),
                    distributedSubMgmt (9),
                    esmUser (10),
                    l2User (11),
                    gtpAuthorized (12),
                    deletePending (13)
                }
    MAX-ACCESS  read-only
    STATUS      current
    DESCRIPTION
        "The value of the object tmnxWlanGwUeResState indicates
         the state of this UE."
    ::= { tmnxWlanGwUeResEntry 6 }
    
tmnxWlanGwUeResIsaGrp OBJECT-TYPE
    SYNTAX      TmnxWlanGwIsaGrpIdOrZero
    MAX-ACCESS  read-only
    STATUS      current
    DESCRIPTION
       "The value of the object tmnxWlanGwUeResIsaGrp indicates 
        the identifier of the WLAN Gateway Integrated Service Adaptor group 
        associated with this UE."
    ::= { tmnxWlanGwUeResEntry 7 }

tmnxWlanGwUeResIsaMemberId OBJECT-TYPE
    SYNTAX      Unsigned32
    MAX-ACCESS  read-only
    STATUS      current
    DESCRIPTION
       "The value of the object tmnxWlanGwUeResIsaMemberId indicates 
        the identifier of the WLAN Gateway ISA Group member associated with this UE."
    ::= { tmnxWlanGwUeResEntry 8 }

tmnxWlanGwUeResTuRouter OBJECT-TYPE
   SYNTAX      TmnxVRtrIDOrZero
   MAX-ACCESS  read-only
   STATUS      current
   DESCRIPTION
       "The object tmnxWlanGwUeResTuRouter indicates 
       the identifier of the virtual router instance 
       where the tunneled User Equipment traffic is routed."
   ::= { tmnxWlanGwUeResEntry 9 }

tmnxWlanGwUeResTuAddrType OBJECT-TYPE
    SYNTAX      InetAddressType
    MAX-ACCESS  read-only
    STATUS      current
    DESCRIPTION 
        "The value of tmnxWlanGwUeResTuAddrType indicates
         the address type of tmnxWlanGwUeResTuRemoteAddr 
         and tmnxWlanGwUeResTuLocalAddr."
    ::= { tmnxWlanGwUeResEntry 10 }

tmnxWlanGwUeResTuRemoteAddr OBJECT-TYPE
    SYNTAX      InetAddress (SIZE(0|4|16))
    MAX-ACCESS  read-only
    STATUS      current
    DESCRIPTION
        "The value of the object tmnxWlanGwUeResTuRemoteAddr indicates
         the IP address of the remote endpoint of this UE's tunnel,
         that is the source IP address in the tunnel header of
         received packets."
    ::= { tmnxWlanGwUeResEntry 11 }

tmnxWlanGwUeResTuLocalAddr OBJECT-TYPE
    SYNTAX      InetAddress (SIZE(0|4|16))
    MAX-ACCESS  read-only
    STATUS      current
    DESCRIPTION
        "The value of the object tmnxWlanGwUeResTuLocalAddr indicates
         the IP address of the local endpoint of this UE's tunnel,
         that is the destination IP address in the tunnel header of
         received packets."
    ::= { tmnxWlanGwUeResEntry 12 }

tmnxWlanGwUeResEncapsulation OBJECT-TYPE
    SYNTAX      TmnxWlanGwUeEncapsulation
    MAX-ACCESS  read-only
    STATUS      current
    DESCRIPTION
        "The value of the object tmnxWlanGwUeResEncapsulation indicates
         the encapsulation used in this UE's tunnel."
    ::= { tmnxWlanGwUeResEntry 13 }
    
-- for the objects below, there is no query object initially   
tmnxWlanGwUeResApMacAddress OBJECT-TYPE
    SYNTAX      MacAddress
    MAX-ACCESS  read-only
    STATUS      current
    DESCRIPTION
        "The value of the object tmnxWlanGwUeResApMacAddress indicates
         the MAC address of the Access Point of this UE."
    ::= { tmnxWlanGwUeResEntry 100 }   

tmnxWlanGwUeResSsid OBJECT-TYPE
    SYNTAX      TNamedItemOrEmpty
    MAX-ACCESS  read-only
    STATUS      current
    DESCRIPTION 
       "The value of tmnxWlanGwUeResSsid indicates 
        the Service Set ID (SSID) of this UE.
        
        This object refers to a conceptual row in the tmnxWlanGwSsidTable."
    ::= { tmnxWlanGwUeResEntry 101 }
    
tmnxWlanGwUeResMplsLabel OBJECT-TYPE
    SYNTAX      MplsLabel
    MAX-ACCESS  read-only
    STATUS      current
    DESCRIPTION     
        "The value of the object tmnxWlanGwUeResMplsLabel indicates
         the MPLS label present in the traffic received from this UE.
         
         The value zero indicates that the traffic received from this UE
         does not have an MPLS label."
    ::= { tmnxWlanGwUeResEntry 102 }

tmnxWlanGwUeResLastMoveTime OBJECT-TYPE
    SYNTAX      DateAndTime (SIZE (11))
    MAX-ACCESS  read-only
    STATUS      current
    DESCRIPTION
        "The value of tmnxWlanGwUeResLastMoveTime indicates
         the time of the most recent Access Point move of this UE."
    ::= { tmnxWlanGwUeResEntry 103 }

tmnxWlanGwUeResExpirationTime OBJECT-TYPE
    SYNTAX      DateAndTime (SIZE (11))
    MAX-ACCESS  read-only
    STATUS      current
    DESCRIPTION
        "The value of tmnxWlanGwUeResExpirationTime indicates
         the time when the system context of this UE will
         expire and be removed from this system,
         unless it is renewed."
    ::= { tmnxWlanGwUeResEntry 104 }

tmnxWlanGwUeResIdleTimeout OBJECT-TYPE
    SYNTAX      Unsigned32
    UNITS       "seconds"
    MAX-ACCESS  read-only
    STATUS      current
    DESCRIPTION
        "The value of tmnxWlanGwUeResIdleTimeout indicates
         the time that this UE can remain inactive
         before its system context will be removed from this system.

         An idle timeout can be imposed by an AAA server."
    ::= { tmnxWlanGwUeResEntry 105 }

tmnxWlanGwUeResSessionTimeout OBJECT-TYPE
    SYNTAX      DateAndTime (SIZE (11))
    MAX-ACCESS  read-only
    STATUS      current
    DESCRIPTION
        "The value of tmnxWlanGwUeResSessionTimeout indicates
         the time when this UE's system context will be removed
         unconditionally.
         
         A session timeout can be imposed by an AAA server."
    ::= { tmnxWlanGwUeResEntry 106 }

tmnxWlanGwUeResNatPlcy OBJECT-TYPE
    SYNTAX      TNamedItemOrEmpty
    MAX-ACCESS  read-only
    STATUS      current
    DESCRIPTION 
       "The value of tmnxWlanGwUeResNatPlcy indicates 
        the NAT (Network Address Translation) policy of this UE.
        
        This object refers to a conceptual row
        in the TIMETRA-NAT-MIB::tmnxNatPlcyTable.
        
        One source for this information is the tmnxWlanGwVlanNatPlcy."
    ::= { tmnxWlanGwUeResEntry 107 }
    
tmnxWlanGwUeResHttpRdrPlcy OBJECT-TYPE
    SYNTAX      TNamedItemOrEmpty
    MAX-ACCESS  read-only
    STATUS      current
    DESCRIPTION 
       "The value of tmnxWlanGwUeResHttpRdrPlcy indicates 
        the HTTP redirect policy of this UE.
        
        This object refers to a conceptual row
        in the TIMETRA-SUBSCRIBER-MGMT-MIB::tmnxSubHttpRdrPlcyTable.
        
        One source for this information is the tmnxWlanGwVlanHttpRdrPlcy."
    ::= { tmnxWlanGwUeResEntry 108 }
    
tmnxWlanGwUeResDsmIpFilter OBJECT-TYPE
    SYNTAX      TNamedItemOrEmpty
    MAX-ACCESS  read-only
    STATUS      current
    DESCRIPTION 
       "The value of tmnxWlanGwUeResDsmIpFilter indicates 
        the DSM IP filter of this UE.
        
        This object refers to a conceptual row
        in the tmnxWlanGwDsmIpFilTable.
        
        One source for this information is the tmnxWlanGwVlanDsmIpFilter."
    ::= { tmnxWlanGwUeResEntry 109 }
    
tmnxWlanGwUeResDsmAcctPlcy OBJECT-TYPE
    SYNTAX      TNamedItemOrEmpty
    MAX-ACCESS  read-only
    STATUS      current
    DESCRIPTION 
       "The value of tmnxWlanGwUeResDsmAcctPlcy indicates 
        the accounting policy of this UE.
        
        This object refers to a conceptual row
        in the TIMETRA-RADIUS-MIB::tmnxRadIsaPlcyTable.
        
        One source for this information is the tmnxWlanGwVlanDsmAcctPlcy."
    ::= { tmnxWlanGwUeResEntry 110 }
    
tmnxWlanGwUeResDsmAcctUpdInterv OBJECT-TYPE
    SYNTAX      Unsigned32
    UNITS       "seconds"
    MAX-ACCESS  read-only
    STATUS      current
    DESCRIPTION
        "The value of tmnxWlanGwUeResDsmAcctUpdInterv indicates
         the time interval between consecutive Interim Accounting Update
         messages.
        
        One source for this information is the tmnxWlanGwVlanDsmAcctUpdInterv."
    ::= { tmnxWlanGwUeResEntry 111 }

tmnxWlanGwUeResAcctUpdate OBJECT-TYPE
    SYNTAX      DateAndTime (SIZE (11))
    MAX-ACCESS  read-only
    STATUS      current
    DESCRIPTION
        "The value of tmnxWlanGwUeResAcctUpdate indicates
         the time when the next accounting update for this UE
         is going to be transmitted."
    ::= { tmnxWlanGwUeResEntry 112 }

tmnxWlanGwUeResIngOperPir OBJECT-TYPE
    SYNTAX      TPIRRate
    UNITS       "kbps"
    MAX-ACCESS  read-only
    STATUS      current
    DESCRIPTION
        "The value of tmnxWlanGwUeResIngOperPir indicates
         the actual ingress PIR (Peak Information Rate).
        
        One source for this information is the tmnxWlanGwPolicerAdminPIR."
    ::= { tmnxWlanGwUeResEntry 113 }

tmnxWlanGwUeResIngOperCir OBJECT-TYPE
    SYNTAX      TCIRRate
    UNITS       "kbps"
    MAX-ACCESS  read-only
    STATUS      current
    DESCRIPTION
        "The value of tmnxWlanGwUeResIngOperPir indicates
         the actual ingress CIR (Committed Information Rate).
        
        One source for this information is the tmnxWlanGwPolicerAdminCIR."
    ::= { tmnxWlanGwUeResEntry 114 }

tmnxWlanGwUeResEgrOperPir OBJECT-TYPE
    SYNTAX      TPIRRate
    UNITS       "kbps"
    MAX-ACCESS  read-only
    STATUS      current
    DESCRIPTION
        "The value of tmnxWlanGwUeResEgrOperPir indicates
         the actual egress PIR (Peak Information Rate).
        
        One source for this information is the tmnxWlanGwPolicerAdminPIR."
    ::= { tmnxWlanGwUeResEntry 115 }

tmnxWlanGwUeResEgrOperCir OBJECT-TYPE
    SYNTAX      TCIRRate
    UNITS       "kbps"
    MAX-ACCESS  read-only
    STATUS      current
    DESCRIPTION
        "The value of tmnxWlanGwUeResEgrOperCir indicates
         the actual egress CIR (Committed Information Rate).
        
        One source for this information is the tmnxWlanGwPolicerAdminCIR."
    ::= { tmnxWlanGwUeResEntry 116 }

tmnxWlanGwUeResDsmAppProfile OBJECT-TYPE
    SYNTAX      TNamedItemOrEmpty
    MAX-ACCESS  read-only
    STATUS      current
    DESCRIPTION 
       "The value of tmnxWlanGwUeResDsmAcctPlcy indicates 
        the application profile of this UE.
        
        This object refers to a conceptual row
        in the TIMETRA-BSX-NG-MIB::tmnxBsxAppProfTable.
        
        One source for this information is the tmnxWlanGwVlanDsmDefAppProfile."
    ::= { tmnxWlanGwUeResEntry 130 }
    
 tmnxWlanGwUeResRxPkts OBJECT-TYPE
    SYNTAX      Counter64
    MAX-ACCESS  read-only
    STATUS      current
    DESCRIPTION
        "The value of tmnxWlanGwUeResRxPkts indicates
         the number of packets received from this UE."
    ::= { tmnxWlanGwUeResEntry 200 }

tmnxWlanGwUeResRxOctets OBJECT-TYPE
    SYNTAX      Counter64
    MAX-ACCESS  read-only
    STATUS      current
    DESCRIPTION
        "The value of tmnxWlanGwUeResRxOctets indicates
         the number of octets received from this UE."
    ::= { tmnxWlanGwUeResEntry 201 }

tmnxWlanGwUeResTxPkts OBJECT-TYPE
    SYNTAX      Counter64
    MAX-ACCESS  read-only
    STATUS      current
    DESCRIPTION
        "The value of tmnxWlanGwUeResTxPkts indicates
         the number of packets transmitted to this UE."
    ::= { tmnxWlanGwUeResEntry 202 }

tmnxWlanGwUeResTxOctets OBJECT-TYPE
    SYNTAX      Counter64
    MAX-ACCESS  read-only
    STATUS      current
    DESCRIPTION
        "The value of tmnxWlanGwUeResTxOctets indicates
         the number of octets transmitted to this UE."
    ::= { tmnxWlanGwUeResEntry 203 }

tmnxWlanGwUeResSlaacAddrType OBJECT-TYPE
    SYNTAX      InetAddressType
    MAX-ACCESS  read-only
    STATUS      current
    DESCRIPTION
        "The value of tmnxWlanGwUeResSlaacAddrType indicates
         the type of tmnxWlanGwUeResSlaacPref, tmnxWlanGwUeResSlaacAddr1,
         tmnxWlanGwUeResSlaacAddr2 and tmnxWlanGwUeResSlaacAddr3."
    ::= { tmnxWlanGwUeResEntry 300 }

tmnxWlanGwUeResSlaacPref OBJECT-TYPE
    SYNTAX      InetAddress (SIZE(0|16))
    MAX-ACCESS  read-only
    STATUS      current
    DESCRIPTION
        "The value of tmnxWlanGwUeResSlaacPref indicates
         the SLAAC prefix."
    ::= { tmnxWlanGwUeResEntry 301 }

tmnxWlanGwUeResSlaacAddr1 OBJECT-TYPE
    SYNTAX      InetAddress (SIZE(0|16))
    MAX-ACCESS  read-only
    STATUS      current
    DESCRIPTION
        "The value of tmnxWlanGwUeResSlaacAddr1 indicates
         the SLAAC address (1 of 3)."
    ::= { tmnxWlanGwUeResEntry 302 }

tmnxWlanGwUeResSlaacAddr2 OBJECT-TYPE
    SYNTAX      InetAddress (SIZE(0|16))
    MAX-ACCESS  read-only
    STATUS      current
    DESCRIPTION
        "The value of tmnxWlanGwUeResSlaacAddr2 indicates
         the SLAAC address (2 of 3)."
    ::= { tmnxWlanGwUeResEntry 303 }

tmnxWlanGwUeResSlaacAddr3 OBJECT-TYPE
    SYNTAX      InetAddress (SIZE(0|16))
    MAX-ACCESS  read-only
    STATUS      current
    DESCRIPTION
        "The value of tmnxWlanGwUeResSlaacAddr3 indicates
         the SLAAC address (3 of 3)."
    ::= { tmnxWlanGwUeResEntry 304 }

tmnxWlanGwUeResDhcp6AddrType OBJECT-TYPE
    SYNTAX      InetAddressType
    MAX-ACCESS  read-only
    STATUS      current
    DESCRIPTION
        "The value of tmnxWlanGwUeResDhcp6AddrType indicates
         the type of tmnxWlanGwUeResDhcp6Addr."
    ::= { tmnxWlanGwUeResEntry 305 }
 
tmnxWlanGwUeResDhcp6Addr OBJECT-TYPE
    SYNTAX      InetAddress (SIZE(0|16))
    MAX-ACCESS  read-only
    STATUS      current
    DESCRIPTION
        "The value of tmnxWlanGwUeResDhcp6Addr indicates
         the DHCPv6 address."
    ::= { tmnxWlanGwUeResEntry 306 }

tmnxWlanGwUeResDhcp6AddrDepr OBJECT-TYPE
    SYNTAX      TruthValue
    MAX-ACCESS  read-only
    STATUS      current
    DESCRIPTION
        "The value of tmnxWlanGwUeResDhcp6AddrDepr indicates
         whether the DHCPv6 address is deprecated or not."
    ::= { tmnxWlanGwUeResEntry 307 }
     
tmnxWlanGwUeResDhcp6IAID OBJECT-TYPE
    SYNTAX      Unsigned32
    MAX-ACCESS  read-only
    STATUS      current
    DESCRIPTION
        "The value of tmnxWlanGwUeResDhcp6IAID indicates
         the DHCPv6 Identity Association Identifier IAID."
    ::= { tmnxWlanGwUeResEntry 308 }
     
tmnxWlanGwUeResDhcp6IAIDValid OBJECT-TYPE
    SYNTAX      TruthValue
    MAX-ACCESS  read-only
    STATUS      current
    DESCRIPTION
        "The value of tmnxWlanGwUeResDhcp6IAIDValid indicates
         whether the IAID available in tmnxWlanGwUeResDhcp6IAID
         is valid or not."
    ::= { tmnxWlanGwUeResEntry 309 }
     
tmnxWlanGwUeResSlaacLeaseExpire OBJECT-TYPE
    SYNTAX      DateAndTime (SIZE (11))
    MAX-ACCESS  read-only
    STATUS      current
    DESCRIPTION
        "The value of tmnxWlanGwUeResSlaacLeaseExpire indicates
         when the lease of the Slaac prefix and addresses will expire."
    ::= { tmnxWlanGwUeResEntry 310 }
 
tmnxWlanGwUeResDhcp6LeaseExpire OBJECT-TYPE
    SYNTAX      DateAndTime (SIZE (11))
    MAX-ACCESS  read-only
    STATUS      current
    DESCRIPTION
        "The value of tmnxWlanGwUeResDhcp6LeaseExpire indicates
         when the lease of the DHCPv6 address will expire."
    ::= { tmnxWlanGwUeResEntry 311 }
 
-- --------------------------------------------------------
-- WLAN Gateway scalar objects
-- --------------------------------------------------------

--
-- System configuration objects
--
tmnxWlanGwSysCfgServingNwMcc  OBJECT-TYPE
    SYNTAX      TmnxMobMccOrEmpty
    MAX-ACCESS  read-write
    STATUS      current
    DESCRIPTION
        "The value of tmnxWlanGwSysCfgServingNwMcc specifies the Mobile
         Country Code (MCC) portion of the Serving Network."
    DEFVAL { ''H }    
    ::= { tmnxWlanGwSysCfgObjs 1 }

tmnxWlanGwSysCfgServingNwMnc  OBJECT-TYPE
    SYNTAX      TmnxMobMncOrEmpty
    MAX-ACCESS  read-write
    STATUS      current
    DESCRIPTION
        "The value of tmnxWlanGwSysCfgServingNwMnc specifies the Mobile
         Network Code (MNC) portion of the Serving Network."
    DEFVAL { ''H }
    ::= { tmnxWlanGwSysCfgObjs 2 }

tmnxWlanGwSysCfgMgwMaxHeldSe  OBJECT-TYPE
    SYNTAX      Unsigned32 (0..262144)
    MAX-ACCESS  read-write
    STATUS      current
    DESCRIPTION
        "The value of tmnxWlanGwSysCfgMgwMaxHeldSe specifies
         the maximum number of GTP session contexts held in the system
         while their UE's are disconnected.
         
         Refer also to the object tmnxWlanGwMgwProfSeHoldTime.
         
         The held session contexts are kept in a First-In-First-Out (FIFO) storage:
         when a new session is added to the storage and the number of held sessions
         reaches the value of tmnxWlanGwSysCfgMgwMaxHeldSe, the session context being
         held the longest time is cleared."
    DEFVAL { 2000 }
    ::= { tmnxWlanGwSysCfgObjs 5 }


tmnxWlanGwSysCfgVirtChassisId OBJECT-TYPE
    SYNTAX      DisplayString (SIZE (0..16))
    MAX-ACCESS  read-create
    STATUS      current
    DESCRIPTION
        "The value of tmnxWlanGwSysCfgVirtChassisId specifies the
         virtual chassis identifier or dual homing key which links
         two wlan-gw's together."
    DEFVAL { "" }
    ::= { tmnxWlanGwSysCfgObjs 15 }

tmnxWlanGwVplsTable OBJECT-TYPE
    SYNTAX     SEQUENCE OF TmnxWlanGwVplsEntry
    MAX-ACCESS not-accessible
    STATUS     current
    DESCRIPTION
        "The tmnxWlanGwVplsTable has an entry for each TLS Service."
    ::= { tmnxWlanGwObjs 12 }

tmnxWlanGwVplsEntry OBJECT-TYPE
    SYNTAX     TmnxWlanGwVplsEntry
    MAX-ACCESS not-accessible
    STATUS     current
    DESCRIPTION
        "Each row entry in the tmnxWlanGwVplsTable represents additional
         columns in the TIMETRA-SERV-MIB::svcTlsInfoTable for attributes 
         needed in a multi-chassis operation."
    AUGMENTS { svcTlsInfoEntry }
    ::= { tmnxWlanGwVplsTable 1 }

TmnxWlanGwVplsEntry ::= SEQUENCE
   {
       tmnxWlanGwVplsLastMgmtChange     TimeStamp,
       tmnxWlanGwVplsAdminState         TmnxEnabledDisabled,
       tmnxWlanGwVplsDescription        TItemDescription,           
       tmnxWlanGwVplsSapTemplate        TNamedItemOrEmpty
   }

tmnxWlanGwVplsLastMgmtChange OBJECT-TYPE
    SYNTAX     TimeStamp
    MAX-ACCESS read-only
    STATUS     current
    DESCRIPTION
        "The value of tmnxWlanGwVplsLastMgmtChange indicates the sysUpTime
         at the time of the last change of this entry.

         If no changes occurred since the last re-initialization
         of the local network management subsystem, then this object contains
         a zero value."
    ::= { tmnxWlanGwVplsEntry 1 }

tmnxWlanGwVplsAdminState OBJECT-TYPE
    SYNTAX     TmnxEnabledDisabled
    MAX-ACCESS read-write
    STATUS     current
    DESCRIPTION
        "The value of tmnxWlanGwVplsAdminState specifies 
        the administrative status of this conceptual row."
    DEFVAL { disabled }
    ::= { tmnxWlanGwVplsEntry 2 }

tmnxWlanGwVplsDescription OBJECT-TYPE
    SYNTAX     TItemDescription
    MAX-ACCESS read-write
    STATUS     current
    DESCRIPTION
        "The value of tmnxWlanGwVplsDescription specifies
         the description of this conceptual row."
    DEFVAL { ''H }
    ::= { tmnxWlanGwVplsEntry 3 }

tmnxWlanGwVplsSapTemplate OBJECT-TYPE
    SYNTAX     TNamedItemOrEmpty
    MAX-ACCESS read-write
    STATUS     current
    DESCRIPTION
        "The value of tmnxWlanGwVplsSapTemplate specifies
         the name of the VPLS SAP template associated with this
         VPLS service for the purpose of WLAN Gateway Layer 2 wholesale.
         
         While the value of tmnxWlanGwVplsSapTemplate is not empty,
         a conceptual row with the same name must exist
         in the TIMETRA-SAP-MIB::sapTmplTable.
         
         The configuration in the template is applied to the internal
         connection between the WLAN Gateway service and the
         Layer 2 service."
    DEFVAL { ''H }
    ::= { tmnxWlanGwVplsEntry 4 }

--
-- Read-only objects
--
tmnxWlanGwGrpTableLastCh OBJECT-TYPE
    SYNTAX      TimeStamp
    MAX-ACCESS  read-only
    STATUS      current
    DESCRIPTION
        "The value of the object tmnxWlanGwGrpTableLastCh indicates
         the value of sysUpTime at the time of the last modification of
         an entry in the tmnxWlanGwGrpTable."
    ::= { tmnxWlanGwObjs 100 }

tmnxWlanGwIomTableLastCh OBJECT-TYPE
    SYNTAX      TimeStamp
    MAX-ACCESS  read-only
    STATUS      current
    DESCRIPTION
        "The value of the object tmnxWlanGwIomTableLastCh indicates
         the value of sysUpTime at the time of the last modification of
         an entry in the tmnxWlanGwIomTable."
    ::= { tmnxWlanGwObjs 101 }
    
tmnxWlanGwSoftGreIfTableLastCh OBJECT-TYPE
    SYNTAX      TimeStamp
    MAX-ACCESS  read-only
    STATUS      current
    DESCRIPTION
        "The value of the object tmnxWlanGwSoftGreIfTableLastCh indicates
         the value of sysUpTime at the time of the last modification of
         an entry in the tmnxWlanGwSoftGreIfTable."
    ::= { tmnxWlanGwObjs 102 }

tmnxWlanGwIfRetailTableLastCh OBJECT-TYPE
    SYNTAX      TimeStamp
    MAX-ACCESS  read-only
    STATUS      obsolete
    DESCRIPTION
        "The value of the object tmnxWlanGwIfRetailTableLastCh indicates
         the value of sysUpTime at the time of the last modification of
         an entry in the tmnxWlanGwIfRetailTable."
    ::= { tmnxWlanGwObjs 103 }

tmnxWlanGwMgwProfTableLastCh OBJECT-TYPE
    SYNTAX      TimeStamp
    MAX-ACCESS  read-only
    STATUS      current
    DESCRIPTION
        "The value of the object tmnxWlanGwMgwProfTableLastCh indicates
         the value of sysUpTime at the time of the last modification of
         an entry in the tmnxWlanGwMgwProfTable."
    ::= { tmnxWlanGwObjs 104 }

tmnxWlanGwMgwAddrTableLastCh OBJECT-TYPE
    SYNTAX      TimeStamp
    MAX-ACCESS  read-only
    STATUS      current
    DESCRIPTION
        "The value of the object tmnxWlanGwMgwAddrTableLastCh indicates
         the value of sysUpTime at the time of the last modification of
         an entry in the tmnxWlanGwMgwAddrTable."
    ::= { tmnxWlanGwObjs 105 }

tmnxWlanGwTableLastCh OBJECT-TYPE
    SYNTAX      TimeStamp
    MAX-ACCESS  read-only
    STATUS      current
    DESCRIPTION
        "The value of the object tmnxWlanGwTableLastCh indicates
         the value of sysUpTime at the time of the last modification of
         an entry in the tmnxWlanGwTable."
    ::= { tmnxWlanGwObjs 106 }

tmnxWlanGwVlanTableLastCh OBJECT-TYPE
    SYNTAX      TimeStamp
    MAX-ACCESS  read-only
    STATUS      current
    DESCRIPTION
        "The value of the object tmnxWlanGwVlanTableLastCh indicates
         the value of sysUpTime at the time of the last modification of
         an entry in the tmnxWlanGwVlanTable."
    ::= { tmnxWlanGwObjs 107 }


tmnxWlanGwPgwTableLastCh OBJECT-TYPE
    SYNTAX      TimeStamp
    MAX-ACCESS  read-only
    STATUS      current
    DESCRIPTION
        "The value of the object tmnxWlanGwPgwTableLastCh indicates
         the value of sysUpTime at the time of the last modification of
         an entry in the tmnxWlanGwPgwTable."
    ::= { tmnxWlanGwObjs 108 }

tmnxWlanGwGgsnTableLastCh OBJECT-TYPE
    SYNTAX      TimeStamp
    MAX-ACCESS  read-only
    STATUS      current
    DESCRIPTION
        "The value of the object tmnxWlanGwGgsnTableLastCh indicates
         the value of sysUpTime at the time of the last modification of
         an entry in the tmnxWlanGwGgsnTable."
    ::= { tmnxWlanGwObjs 109 }

tmnxWlanGwSubIfTableLastCh OBJECT-TYPE
    SYNTAX      TimeStamp
    MAX-ACCESS  read-only
    STATUS      current
    DESCRIPTION
        "The value of the object tmnxWlanGwSubIfTableLastCh indicates
         the value of sysUpTime at the time of the last modification of
         an entry in the tmnxWlanGwSubIfTable."
    ::= { tmnxWlanGwObjs 110 }

tmnxWlanGwVlanDsmTableLastCh OBJECT-TYPE
    SYNTAX      TimeStamp
    MAX-ACCESS  read-only
    STATUS      current
    DESCRIPTION
        "The value of the object tmnxWlanGwVlanDsmTableLastCh indicates
         the value of sysUpTime at the time of the last modification of
         an entry in the tmnxWlanGwVlanDsmTable."
    ::= { tmnxWlanGwObjs 111 }

tmnxWlanGwDsmIpFilTableLastCh OBJECT-TYPE
    SYNTAX      TimeStamp
    MAX-ACCESS  read-only
    STATUS      current
    DESCRIPTION
        "The value of the object tmnxWlanGwDsmIpFilTableLastCh indicates
         the value of sysUpTime at the time of the last modification of
         an entry in the tmnxWlanGwDsmIpFilTable."
    ::= { tmnxWlanGwObjs 112 }

tmnxWlanGwDsmIpFilN3TableLastCh OBJECT-TYPE
    SYNTAX      TimeStamp
    MAX-ACCESS  read-only
    STATUS      current
    DESCRIPTION
        "The value of the object tmnxWlanGwDsmIpFilN3TableLastCh indicates
         the value of sysUpTime at the time of the last modification of
         an entry in the tmnxWlanGwDsmIpFilN3Table."
    ::= { tmnxWlanGwObjs 113 }

tmnxWlanGwPolicerTableLastCh OBJECT-TYPE
    SYNTAX      TimeStamp
    MAX-ACCESS  read-only
    STATUS      current
    DESCRIPTION
        "The value of the object tmnxWlanGwPolicerTableLastCh indicates
         the value of sysUpTime at the time of the last modification of
         an entry in the tmnxWlanGwPolicerTable."
    ::= { tmnxWlanGwObjs 114 }

tmnxWlanGwL2ApTableLastCh OBJECT-TYPE
    SYNTAX      TimeStamp
    MAX-ACCESS  read-only
    STATUS      current
    DESCRIPTION
        "The value of the object tmnxWlanGwL2ApTableLastCh indicates
         the value of sysUpTime at the time of the last modification of
         an entry in the tmnxWlanGwL2ApTable."
    ::= { tmnxWlanGwObjs 117 }

tmnxWlanGwVplsTableLastCh OBJECT-TYPE
    SYNTAX      TimeStamp
    MAX-ACCESS  read-only
    STATUS      current
    DESCRIPTION
        "The value of the object tmnxWlanGwVplsTableLastCh indicates
         the value of sysUpTime at the time of the last modification of
         an entry in the tmnxWlanGwVplsTable."
    ::= { tmnxWlanGwObjs 118 }


tmnxWlanGwDsmIpFil6N3TableLastCh OBJECT-TYPE
    SYNTAX      TimeStamp
    MAX-ACCESS  read-only
    STATUS      current
    DESCRIPTION
        "The value of the object tmnxWlanGwDsmIpFil6N3TableLastCh indicates
         the value of sysUpTime at the time of the last modification of
         an entry in the tmnxWlanGwDsmIpFil6N3Table."
    ::= { tmnxWlanGwObjs 119 }

tmnxWlanGwSubIfPmTableLastCh OBJECT-TYPE
    SYNTAX      TimeStamp
    MAX-ACCESS  read-only
    STATUS      current
    DESCRIPTION
        "The value of the object tmnxWlanGwSubIfPmTableLastCh indicates
         the value of sysUpTime at the time of the last modification of
         an entry in the tmnxWlanGwSubIfPmTable."
    ::= { tmnxWlanGwObjs 122 }

tmnxWlanGwVlanDhcp6TableLastCh OBJECT-TYPE
    SYNTAX      TimeStamp
    MAX-ACCESS  read-only
    STATUS      current
    DESCRIPTION
        "The value of the object tmnxWlanGwVlanDhcp6TableLastCh indicates
         the value of sysUpTime at the time of the last modification of
         an entry in the tmnxWlanGwVlanDhcp6Table."
    ::= { tmnxWlanGwObjs 123 }

tmnxWlanGwVlanSlaacTableLastCh OBJECT-TYPE
    SYNTAX      TimeStamp
    MAX-ACCESS  read-only
    STATUS      current
    DESCRIPTION
        "The value of the object tmnxWlanGwVlanSlaacTableLastCh indicates
         the value of sysUpTime at the time of the last modification of
         an entry in the tmnxWlanGwVlanSlaacTable."
    ::= { tmnxWlanGwObjs 124 }

tmnxWlanGwDsmTableLastCh OBJECT-TYPE
    SYNTAX      TimeStamp
    MAX-ACCESS  read-only
    STATUS      current
    DESCRIPTION
        "The value of the object tmnxWlanGwDsmTableLastCh indicates
         the value of sysUpTime at the time of the last modification of
         an entry in the tmnxWlanGwDsmTable."
    ::= { tmnxWlanGwObjs 125 }

tmnxWlanGwResrcProblem OBJECT-TYPE
    SYNTAX      TruthValue
    MAX-ACCESS  read-only
    STATUS      current
    DESCRIPTION
        "The value of the object tmnxWlanGwResrcProblem indicates
         if there is a resource problem detected while attempting
         to activate some part of the WLAN Gateway configuration of this system."
    ::= { tmnxWlanGwObjs 200 }

tmnxWlanGwNumSoftGreTu OBJECT-TYPE
    SYNTAX      Gauge32
    MAX-ACCESS  read-only
    STATUS      current
    DESCRIPTION
        "The value of the object tmnxWlanGwNumSoftGreTu indicates
         the actual number of Soft GRE tunnels terminated by this system."
    ::= { tmnxWlanGwObjs 201 }

tmnxWlanGwPeakNumSoftGreTu OBJECT-TYPE
    SYNTAX      Gauge32
    MAX-ACCESS  read-only
    STATUS      current
    DESCRIPTION
        "The value of the object tmnxWlanGwPeakNumSoftGreTu indicates
         the peak number of Soft GRE tunnels terminated by this system at any time,
         since the system was last initialized or the value of this object
         was last reset."
    ::= { tmnxWlanGwObjs 202 }

tmnxWlanGwNumUe OBJECT-TYPE
    SYNTAX      Gauge32
    MAX-ACCESS  read-only
    STATUS      current
    DESCRIPTION
        "The value of the object tmnxWlanGwNumSoftGreTu indicates
         the actual number of UE processed by this system."
    ::= { tmnxWlanGwObjs 203 }

tmnxWlanGwPeakNumUe OBJECT-TYPE
    SYNTAX      Gauge32
    MAX-ACCESS  read-only
    STATUS      current
    DESCRIPTION
        "The value of the object tmnxWlanGwPeakNumSoftGreTu indicates
         the peak number of UE processed by this system at any time,
         since the system was last initialized or the value of this object
         was last reset."
    ::= { tmnxWlanGwObjs 204 }

tmnxWlanGwNumMgw OBJECT-TYPE
    SYNTAX      Gauge32
    MAX-ACCESS  read-only
    STATUS      current
    DESCRIPTION
        "The value of the object tmnxWlanGwNumMgw indicates
         the actual number of Mobile Gateways connected to this system.
         
         It is equal to the number of rows in the tmnxWlanGwMgwTable."
    ::= { tmnxWlanGwObjs 205 }

tmnxWlanGwMgwNumHeldSe OBJECT-TYPE
    SYNTAX      Gauge32
    MAX-ACCESS  read-only
    STATUS      current
    DESCRIPTION
        "The value of the object tmnxWlanGwMgwNumHeldSe indicates
         the actual number of GTP session contexts held by this system
         while their associated UE are disconnected."
    ::= { tmnxWlanGwObjs 210 }

-- ----------------------------------------------------------------------------
--  Notification objects
-- ----------------------------------------------------------------------------

tmnxWlanGwNotifyDescription  OBJECT-TYPE
    SYNTAX      DisplayString (SIZE(0..255))
    MAX-ACCESS  accessible-for-notify
    STATUS      current
    DESCRIPTION
        "The object tmnxWlanGwNotifyDescription is a printable character 
         string."
    ::= { tmnxWlanGwNotificationObjs 1 }

tmnxWlanGwNotifyTrue  OBJECT-TYPE
    SYNTAX      TruthValue
    MAX-ACCESS  accessible-for-notify
    STATUS      current
    DESCRIPTION
        "The object tmnxWlanGwNotifyTrue contains a boolean truth value."
    ::= { tmnxWlanGwNotificationObjs 2 }

tmnxWlanGwNotify3gppRelease  OBJECT-TYPE
    SYNTAX      DisplayString (SIZE(2))
    MAX-ACCESS  accessible-for-notify
    STATUS      current
    DESCRIPTION
        "The object tmnxWlanGwNotify3gppRelease contains a string representing
         a 3GPP release."
    REFERENCE
       "3GPP TS 29.061, section 16.4.7.2 Coding 3GPP Vendor-Specific RADIUS attributes
        item 5 - 3GPP-GPRS Negotiated QoS profile."
    ::= { tmnxWlanGwNotificationObjs 3 }
    
tmnxWlanGwNotifyMdaSlotNum  OBJECT-TYPE
    SYNTAX      Unsigned32
    MAX-ACCESS  accessible-for-notify
    STATUS      current
    DESCRIPTION
        "The object tmnxWlanGwNotifyMdaSlotNum contains the value of an MDA slot within a
         specific IOM card."
    ::= { tmnxWlanGwNotificationObjs 4 }
    
tmnxWlanGwNotifySubIfIndex OBJECT-TYPE
    SYNTAX      InterfaceIndex
    MAX-ACCESS  accessible-for-notify
    STATUS      current
    DESCRIPTION
        "The value of tmnxWlanGwNotifySubIfIndex indicates the index
         of the subscriber interface."
    ::= { tmnxWlanGwNotificationObjs 5 }

tmnxWlanGwNotifyAddrFamily OBJECT-TYPE
    SYNTAX      TmnxWlanGwSubIfIpsAddrFamily
    MAX-ACCESS  accessible-for-notify
    STATUS      current
    DESCRIPTION
        "The value of tmnxWlanGwNotifyAddrFamily indicates the address family
         of the pool as defined in the textual convention TmnxWlanGwSubIfIpsAddrFamily."
    ::= { tmnxWlanGwNotificationObjs 6 }
    
tmnxWlanGwNotifyIsaGrpId OBJECT-TYPE
    SYNTAX      TmnxWlanGwIsaGrpIdOrZero
    MAX-ACCESS  accessible-for-notify
    STATUS      current
    DESCRIPTION
       "The value of the object tmnxWlanGwNotifyIsaGrpId indicates
        the group identifier of the ISA for the given prefix."
    ::= { tmnxWlanGwNotificationObjs 7 }
    
tmnxWlanGwNotifyIsaMemberId OBJECT-TYPE
    SYNTAX      Unsigned32
    MAX-ACCESS  accessible-for-notify
    STATUS      current
    DESCRIPTION
       "The value of the object tmnxWlanGwNotifyIsaMemberId indicates
        the member identifier of the ISA for the given prefix."
    ::= { tmnxWlanGwNotificationObjs 8 }

tmnxWlanGwNotifyD6cServer1 OBJECT-TYPE
    SYNTAX      InetAddressIPv6
    MAX-ACCESS  accessible-for-notify
    STATUS      current
    DESCRIPTION
       "The value of the object tmnxWlanGwNotifyD6cServer1 indicates
        one of the DHCPv6 servers."
    ::= { tmnxWlanGwNotificationObjs 9 }

tmnxWlanGwNotifyD6cServer2 OBJECT-TYPE
    SYNTAX      InetAddressIPv6
    MAX-ACCESS  accessible-for-notify
    STATUS      current
    DESCRIPTION
       "The value of the object tmnxWlanGwNotifyD6cServer2 indicates
        one of the DHCPv6 servers."
    ::= { tmnxWlanGwNotificationObjs 10 }

tmnxWlanGwNotifyD6cServer3 OBJECT-TYPE
    SYNTAX      InetAddressIPv6
    MAX-ACCESS  accessible-for-notify
    STATUS      current
    DESCRIPTION
       "The value of the object tmnxWlanGwNotifyD6cServer3 indicates
        one of the DHCPv6 servers."
    ::= { tmnxWlanGwNotificationObjs 11 }

tmnxWlanGwNotifyD6cServer4 OBJECT-TYPE
    SYNTAX      InetAddressIPv6
    MAX-ACCESS  accessible-for-notify
    STATUS      current
    DESCRIPTION
       "The value of the object tmnxWlanGwNotifyD6cServer4 indicates
        one of the DHCPv6 servers."
    ::= { tmnxWlanGwNotificationObjs 12 }

tmnxWlanGwNotifyD6cServer5 OBJECT-TYPE
    SYNTAX      InetAddressIPv6
    MAX-ACCESS  accessible-for-notify
    STATUS      current
    DESCRIPTION
       "The value of the object tmnxWlanGwNotifyD6cServer5 indicates
        one of the DHCPv6 servers."
    ::= { tmnxWlanGwNotificationObjs 13 }

tmnxWlanGwNotifyD6cServer6 OBJECT-TYPE
    SYNTAX      InetAddressIPv6
    MAX-ACCESS  accessible-for-notify
    STATUS      current
    DESCRIPTION
       "The value of the object tmnxWlanGwNotifyD6cServer6 indicates
        one of the DHCPv6 servers."
    ::= { tmnxWlanGwNotificationObjs 14 }

tmnxWlanGwNotifyD6cServer7 OBJECT-TYPE
    SYNTAX      InetAddressIPv6
    MAX-ACCESS  accessible-for-notify
    STATUS      current
    DESCRIPTION
       "The value of the object tmnxWlanGwNotifyD6cServer7 indicates
        one of the DHCPv6 servers."
    ::= { tmnxWlanGwNotificationObjs 15 }

tmnxWlanGwNotifyD6cServer8 OBJECT-TYPE
    SYNTAX      InetAddressIPv6
    MAX-ACCESS  accessible-for-notify
    STATUS      current
    DESCRIPTION
       "The value of the object tmnxWlanGwNotifyD6cServer8 indicates
        one of the DHCPv6 servers."
    ::= { tmnxWlanGwNotificationObjs 16 }

tmnxWlanGwNotifySubnetAddrType OBJECT-TYPE
    SYNTAX      InetAddressType 
    MAX-ACCESS  accessible-for-notify
    STATUS      current
    DESCRIPTION
       "The value of the object tmnxWlanGwNotifySubnetAddrType indicates
        the type of the subnet address sent in the notification."
    ::= { tmnxWlanGwNotificationObjs 17 }
    
tmnxWlanGwNotifySubnetAddr OBJECT-TYPE
    SYNTAX      InetAddress (SIZE(0|4|16))
    MAX-ACCESS  accessible-for-notify
    STATUS      current
    DESCRIPTION
       "The value of the object tmnxWlanGwNotifySubnetAddr indicates
        the subnet address sent in the notification."
    ::= { tmnxWlanGwNotificationObjs 18 }
    
tmnxWlanGwNotifySubnetPrefLen OBJECT-TYPE
    SYNTAX      InetAddressPrefixLength
    MAX-ACCESS  accessible-for-notify
    STATUS      current
    DESCRIPTION
       "The value of the object tmnxWlanGwNotifySubnetPrefLen indicates
        the prefix length of the subnet address sent in the notification."
    ::= { tmnxWlanGwNotificationObjs 19 }

-- ----------------------------------------------------------------------------
--  Notifications
-- ----------------------------------------------------------------------------

tmnxWlanGwResrcProblemDetected NOTIFICATION-TYPE
    OBJECTS {
        tmnxWlanGwResrcProblem
    }
    STATUS current
    DESCRIPTION
        "The tmnxWlanGwResrcProblemDetected notification is sent when 
         the value of the object tmnxWlanGwResrcProblem changes."
    ::= { tmnxWlanGwNotifications 1}

tmnxWlanGwResrcProblemCause NOTIFICATION-TYPE
    OBJECTS {
        tmnxWlanGwNotifyDescription
    }
    STATUS current
    DESCRIPTION
        "The tmnxWlanGwResrcProblemCause notification is sent 
         to describe the cause of a WLAN Gateway resource problem."
    ::= { tmnxWlanGwNotifications 2}

tmnxWlanGwTuQosProblem NOTIFICATION-TYPE
    OBJECTS {
        tmnxWlanGwIsaMemberTuQosProblem
    }
    STATUS current
    DESCRIPTION
        "The tmnxWlanGwTuQosProblem notification is sent when the value
         of the object tmnxWlanGwIsaMemberTuQosProblem changes from or to zero
         for some member of a WLAN Gateway ISA Group in the system.
         
         [CAUSE] While creating a WLAN Gateway tunnel QoS infrastructure 
         instance, there was a resource issue.  
         
         [EFFECT] There are UE with a QoS infrastructure that does not match
         the configuration, for example: no shaper was instantiated.
         
         [RECOVERY] This may be a temporary phenomenon.
         
         If it persists, the QoS configuration or the scaling may have to
         be modified to ensure enough resources are available for the UE QoS."
    ::= { tmnxWlanGwNotifications 3}

tmnxWlanGwGrpOperStateChanged NOTIFICATION-TYPE
    OBJECTS {
        tmnxWlanGwGrpOperState
    }
    STATUS current
    DESCRIPTION
        "The tmnxWlanGwGrpOperStateChanged notification is sent when 
         the value of the object tmnxWlanGwGrpOperState changes."
    ::= { tmnxWlanGwNotifications 4}

tmnxWlanGwIomActive NOTIFICATION-TYPE
    OBJECTS {
        tmnxWlanGwIomLastMgmtChange,
        tmnxWlanGwNotifyTrue
    }
    STATUS current
    DESCRIPTION
        "The tmnxWlanGwIomActive notification is sent when 
         the value of the object tmnxWlanGwIomOperState changes from
         'primary' to any other value, or the other way around.
         
         The value 'primary' means that the IOM is active in the group."
    ::= { tmnxWlanGwNotifications 5}

tmnxWlanGwMgwConnected NOTIFICATION-TYPE
    OBJECTS {
        tmnxWlanGwMgwTime,
        tmnxWlanGwNotifyTrue
    }
    STATUS current
    DESCRIPTION
        "The tmnxWlanGwMgwConnected notification is sent
         when this system adds a conceptual row to the tmnxWlanGwMgwTable,
         or removes it.
         
         [CAUSE] A connection is established between this system's WLAN Gateway
         function and a Mobile Gateway, or such a connection disappears.
         
         The interruption of a connection with a Mobile Gateway
         can be the expected result of a management action on the Mobile Gateway,
         or it can be caused by a network failure.
         
         [EFFECT] While there is a connection with a particular Mobile Gateway, 
         User Equipment (UE) belonging to the associated 
         PLMN (Public Land Mobile Network) and serviced by this WLAN Gateway
         can be connected to their Home PLMN.
         
         [RECOVERY] If a connection with a Mobile Gateway is interrupted as
         the expected result of a management action, no recovery is required."
    ::= { tmnxWlanGwNotifications 10}


tmnxWlanGwMgwRestarted NOTIFICATION-TYPE
    OBJECTS {
        tmnxWlanGwMgwRestartCnt
    }
    STATUS current
    DESCRIPTION
        "The tmnxWlanGwMgwRestarted notification is sent
         when this system learns that a Mobile Gateway has restarted.
         
         [CAUSE] A Mobile Gateway known to this system has restarted,
         has transmitted its restart counter to this system and 
         it was found to be higher than its previously known value.
         
         [EFFECT] This system clears all sessions associated with the
         restarted Mobile Gateway (because that Mobile Gateway has lost
         its session data anyway).
         
         [RECOVERY] No recovery is required on this system."
    ::= { tmnxWlanGwNotifications 11}

tmnxWlanGwNumMgwHi NOTIFICATION-TYPE
    OBJECTS {
        tmnxWlanGwNumMgw,
        tmnxWlanGwNotifyTrue
    }
    STATUS current
    DESCRIPTION
        "The tmnxWlanGwNumMgwHi notification is sent
         when the value of tmnxWlanGwNumMgw reaches its high 
         watermark ('true') or when it reaches its low watermark 
         again ('false'). The value of the object tmnxWlanGwNumMgw indicates
         the actual number of Mobile Gateways connected to this system.
         
         The description below applies to the notification
         when sent with the value of 'true'.
         
         [CAUSE] The number of Mobile Gateways connected to this system
         is approaching the maximum supported value.
         
         [EFFECT] If the increasing trend continues, this system will not be
         able to connect some User Equipment (UE) with their Home PLMN.
         
         [RECOVERY] The network configuration may have to be modified
         such that this system will be associated with less Mobile Gateways."
    ::= { tmnxWlanGwNotifications 12}

tmnxWlanGwMgwStateChanged NOTIFICATION-TYPE
    OBJECTS {
        tmnxWlanGwMgwState
    }
    STATUS current
    DESCRIPTION
        "The tmnxWlanGwMgwStateChanged notification is sent
         when the state of a connection with a Mobile Gateway has changed.
         
         [CAUSE] The state of a connection with a Mobile Gateway has changed.
         
         [EFFECT] The effect depends on the new state.
         
         [RECOVERY] No recovery is required on this system."
    ::= { tmnxWlanGwNotifications 13}
    
tmnxWlanGwQosRadiusGtpMismatch NOTIFICATION-TYPE 
    OBJECTS {
        tmnxWlanGwMgwInterfaceType,
        tmnxWlanGwNotify3gppRelease
    }
    STATUS current
    DESCRIPTION
        "The tmnxWlanGwQosRadiusGtpMismatch notification is sent
         when the Negotiated QoS profile RADIUS attribute contains
         a release indicator either for GGSN or PGW that does not correspond
         to the interface type actually used in GTP. e.g. the release indicator is for
         GGSN and the interface type used in GTP is S2a/S2b while it should be Gn.
       
         [CAUSE] Inconsistency between the release indicator in the RADIUS
         attribute and the GTP interface type.
       
         [EFFECT] The QoS values in the tmnxWlanGwPgwTable or the tmnxWlanGwGgsnTable
         of the conceptual row corresponding to the row in the tmnxWlanGwMgwAddrTable
         that matches the WLAN are used instead.

         [RECOVERY] The RADIUS Server configuration should be corrected."
    ::= { tmnxWlanGwNotifications 14}    

tmnxWlanGwSubIfRedActiveChanged NOTIFICATION-TYPE
    OBJECTS {
        tmnxWlanGwSubIfRedActive,
        tmnxWlanGwNotifyDescription
    }
    STATUS current
    DESCRIPTION
        "The tmnxWlanGwSubIfRedActiveChanged notification is sent
         when the value of the object tmnxWlanGwSubIfRedActive has changed.
         
         [CAUSE] The tmnxWlanGwSubIfRedActiveChanged notification is sent
         when the value of the object tmnxWlanGwSubIfRedActive changes.
         The cause is explained in the tmnxWlanGwNotifyDescription.
         
         [EFFECT] While the value of the object tmnxWlanGwSubIfRedActive is equal to 'false', ...
         - this system is not performing Wifi Offload in the realm of this subscriber interface;
         the Wifi Offload functionality is supposed to be performed by its redundant peer.
         - this subscriber interface and all the group interfaces contained within this subscriber interface
         are operationally down;
         - for all group interfaces contained within this subscriber interface, the addresses
         specified in tmnxWlanGwSoftGreIfGwAddr and tmnxWlanGwSoftGreIfGwV6Addr are
         not advertised in the realm of the virtual router instance
         where the tunneled User Equipment traffic is routed;
         - the route specified with tmnxWlanGwSubIfRedExpPrefix is not exported
         in the realm of the virtual router instance associated with this subscriber interface.
         
         [RECOVERY] No recovery is required on this system."
    ::= { tmnxWlanGwNotifications 15}
    

tmnxWlanGwDsmGtpTunnelSetupFail NOTIFICATION-TYPE 
    OBJECTS {
        tmnxWlanGwIomRowStatus,
        tmnxWlanGwNotifyMdaSlotNum,
        tmnxWlanGwNotifyDescription
    }
    STATUS current
    DESCRIPTION
        "The tmnxWlanGwDsmGtpTunnelSetupFail notification is sent when
         a problem occurred while trying to setup a GTP tunnel for a
         DSM subscriber.
       
         [CAUSE] A problem occurred while trying to setup a GTP tunnel for a
         DSM subscriber.
         
         This can be caused by:
         - incomplete system configuration, or
         - inconsistent RADIUS configuration, or
         - because the GTP peer is not reachable.
       
         [EFFECT] The DSM subscriber cannot establish a connection with his 
         home mobile network.

         [RECOVERY] Depending on the cause, correct the system configuration,
         the RADIUS configuration or the network connectivity."
    ::= { tmnxWlanGwNotifications 16}
    
tmnxWlanGwSubIfPmStartD6cFailed NOTIFICATION-TYPE
    OBJECTS {
        svcId,
        tmnxWlanGwNotifySubIfIndex,
        tmnxWlanGwNotifyAddrFamily,
        tmnxWlanGwNotifyIsaGrpId,
        tmnxWlanGwNotifyIsaMemberId,
        tmnxWlanGwNotifyDescription
    }
    STATUS current
    DESCRIPTION
        "The tmnxWlanGwSubIfPmStartD6cFailed notification is sent when
         a DHCPv6 client of the Pool Manager failed to start.
         
         [CAUSE] Failed to start a DHCPv6 client.
         
         [EFFECT] No pools can be requested for this ISA-BB.
         
         [RECOVERY] Perform a shutdown/no shutdown of the DHCPv6 client."
    ::= { tmnxWlanGwNotifications 17}
    
tmnxWlanGwSubIfPmNewPlReqFailed NOTIFICATION-TYPE
    OBJECTS {
        svcId,
        tmnxWlanGwNotifySubIfIndex,
        tmnxWlanGwNotifyAddrFamily,
        tmnxWlanGwNotifyIsaGrpId,
        tmnxWlanGwNotifyIsaMemberId,
        tmnxWlanGwNotifyDescription 
    }
    STATUS current
    DESCRIPTION
        "The tmnxWlanGwSubIfPmNewPlReqFailed notification is sent when
         sending a request for a new pool is failing.
         (For example, when a DHCPv6 server is unreachable.)
         
         [CAUSE] Failed to send a request for a new pool.
         
         [EFFECT] The ISA-BB may run out of free DHCPv6 addresses or SLAAC prefixes.
         
         [RECOVERY] No recovery is needed. Retry periodically."
    ::= { tmnxWlanGwNotifications 18}
    
tmnxWlanGwSubIfPmAddNewPlFailed NOTIFICATION-TYPE
    OBJECTS {
        svcId,
        tmnxWlanGwNotifySubnetAddrType,
        tmnxWlanGwNotifySubnetAddr,
        tmnxWlanGwNotifySubnetPrefLen,
        tmnxWlanGwNotifySubIfIndex,
        tmnxWlanGwNotifyAddrFamily,
        tmnxWlanGwNotifyIsaGrpId,
        tmnxWlanGwNotifyIsaMemberId,
        tmnxWlanGwNotifyDescription 
    }
    STATUS current
    DESCRIPTION
        "The tmnxWlanGwSubIfPmAddNewPlFailed notification is sent when
         adding a new pool, given by the DHCPv6 server, is failing.
         (Examples : conflict with existing pool, subnet too small, 
          maximum number of pools reached, out of memory, etc.) 
        
         [CAUSE] Failed to add a new pool given by the server.
         
         [EFFECT] The ISA-BB may run out of free DHCPv6 addresses or SLAAC prefixes.
         
         [RECOVERY] No recovery is needed. Retry periodically."
    ::= { tmnxWlanGwNotifications 19}
    
tmnxWlanGwSubIfPmCrIntObjFailed NOTIFICATION-TYPE
    OBJECTS {
        svcId,
        tmnxWlanGwSubIfIpsSubnetAddrType,
        tmnxWlanGwSubIfIpsSubnetAddr,
        tmnxWlanGwSubIfIpsSubnetPrefLen,
        tmnxWlanGwSubIfIpsSubIfIndex,
        tmnxWlanGwNotifyAddrFamily,
        tmnxWlanGwNotifyDescription
    }
    STATUS current
    DESCRIPTION
        "The tmnxWlanGwSubIfPmCrIntObjFailed notification is sent when
         the creation of an internal object for a pool is failing.
        
         [CAUSE] Failed to create an internal object for a pool.
         
         [EFFECT] Forwarding will not work for UEs having an address/prefix
         from this pool.
         
         [RECOVERY] No recovery is needed. Retry periodically."
    ::= { tmnxWlanGwNotifications 20}
    
tmnxWlanGwSubIfPmPoolTimeout NOTIFICATION-TYPE
    OBJECTS {
        tmnxWlanGwSubIfIpsRemLeaseTime,
        tmnxWlanGwNotifyAddrFamily,
        tmnxWlanGwNotifyDescription 
    }
    STATUS current
    DESCRIPTION
        "The tmnxWlanGwSubIfPmPoolTimeout notification is sent when
         a pool is timing out unexpectedly.
        
         [CAUSE] Pool timed out unexpectedly.
         
         [EFFECT] The pool is removed from the ISA-BB together with all
         associated UEs.
         
         [RECOVERY] No recovery possible."
    ::= { tmnxWlanGwNotifications 21}

tmnxWlanGwSubIfPmPoolUsageLow NOTIFICATION-TYPE
    OBJECTS {
        tmnxWlanGwSubIfIpsUsageLevelPct,
        tmnxWlanGwNotifyAddrFamily
    }
    STATUS current
    DESCRIPTION
        "The tmnxWlanGwSubIfPmPoolUsageLow notification is sent when
         the usage of a pool drops below 1% 
        
         [CAUSE] Pool usage dropped below 1%.
         
         [EFFECT] The pool has become stale.
         
         [RECOVERY] Manually clear the pool."
    ::= { tmnxWlanGwNotifications 22}

tmnxWlanGwSubIfPmLsQryRtryFailed NOTIFICATION-TYPE
    OBJECTS {
        svcId,
        tmnxWlanGwNotifySubIfIndex,
        tmnxWlanGwNotifyAddrFamily,
        tmnxWlanGwNotifyIsaGrpId,
        tmnxWlanGwNotifyIsaMemberId,
        tmnxWlanGwNotifyDescription,
        tmnxWlanGwNotifyD6cServer1,
        tmnxWlanGwNotifyD6cServer2,
        tmnxWlanGwNotifyD6cServer3,
        tmnxWlanGwNotifyD6cServer4,
        tmnxWlanGwNotifyD6cServer5,
        tmnxWlanGwNotifyD6cServer6,
        tmnxWlanGwNotifyD6cServer7,
        tmnxWlanGwNotifyD6cServer8
    }
    STATUS current
    DESCRIPTION
        "The tmnxWlanGwSubIfPmLsQryRtryFailed notification is sent when
         the lease query retry fails.
         
         [CAUSE] Lease query retry failed.
         
         [EFFECT] The old prefix couldn't be fetched from the DHCP server.
         
         [RECOVERY] No recovery possible."
    ::= { tmnxWlanGwNotifications 23}
-- ----------------------------------------------------------------------------
--  Conformance Groups
-- ----------------------------------------------------------------------------
tmnxWlanGwIsaGroup OBJECT-GROUP
    OBJECTS {
        tmnxWlanGwGrpTableLastCh,
        tmnxWlanGwGrpRowStatus,         
        tmnxWlanGwGrpLastMgmtChange,    
        tmnxWlanGwGrpDescription,       
        tmnxWlanGwGrpAdminState,        
        tmnxWlanGwGrpActiveIomLimit,
        tmnxWlanGwGrpPortPlcy,    
        tmnxWlanGwGrpTunnelPortPlcy,    
        tmnxWlanGwGrpOperState,         
        tmnxWlanGwIomTableLastCh,
        tmnxWlanGwIomRowStatus,      
        tmnxWlanGwIomLastMgmtChange, 
        tmnxWlanGwIomOperState,
        tmnxWlanGwIsaMemberChassisIndex,
        tmnxWlanGwIsaMemberCardSlotNum,
        tmnxWlanGwIsaMemberSlotNum,
        tmnxWlanGwIsaMemberNumSoftGreTu,
        tmnxWlanGwIsaMemberNumUe,
        tmnxWlanGwIsaMemberEegMemberAct,
        tmnxWlanGwIsaMemberEegMemberPend,
        tmnxWlanGwIsaMemberTuQosProblem,
        tmnxWlanGwIsaMemberStatsName,
        tmnxWlanGwIsaMemberStatsVal,
        tmnxWlanGwIsaMemberStatsValHw,
        tmnxWlanGwIsaMemberStatsValue,
        tmnxWlanGwResrcProblem      
    }
    STATUS      current
    DESCRIPTION
        "The group of objects providing configuration of WLAN Gateway ISA 
          on Nokia SROS series systems."
    ::= { tmnxWlanGwGroups 1 }

tmnxWlanGwSoftGreGroup OBJECT-GROUP
    OBJECTS {
        tmnxWlanGwSoftGreIfLastCh,
        tmnxWlanGwSoftGreIfAdminState,
        tmnxWlanGwSoftGreIfRouter,
        tmnxWlanGwSoftGreIfGwAddrType,
        tmnxWlanGwSoftGreIfGwAddr,
        tmnxWlanGwSoftGreIfGrpId,
        tmnxWlanGwSoftGreIfShapingType,
        tmnxWlanGwSoftGreIfShapeMultiUe,
        tmnxWlanGwSoftGreIfEQosPlcy,
        tmnxWlanGwSoftGreIfESchedPlcy,
        tmnxWlanGwSoftGreIfEAggRateLimit,
        tmnxWlanGwSoftGreIfMobTrigger,
        tmnxWlanGwSoftGreIfMobHoldTime,
        tmnxWlanGwSoftGreIfDefRetailSvc,
        tmnxWlanGwSoftGreIfTcpMssAdjust,
        tmnxWlanGwSoftGreIfEHoldTime,
        tmnxWlanGwSoftGreIfNumSoftGreTu,
        tmnxWlanGwSoftGreIfTableLastCh,
        tmnxWlanGwSoftGreTuEstabTime,
        tmnxWlanGwSoftGreTuIsaGroup,
        tmnxWlanGwSoftGreTuIsaMember,
        tmnxWlanGwSoftGreTuNumUe,
        tmnxWlanGwTuQosEegSvcId,
        tmnxWlanGwTuQosEegPortId ,
        tmnxWlanGwTuQosEegEncapValue,
        tmnxWlanGwTuQosEegName,
        tmnxWlanGwTuQosEegMember,
        tmnxWlanGwTuQosState,     
        tmnxWlanGwTuQosNumUe,
        tmnxWlanGwTuQosRemainingHoldTime,     
        tmnxWlanGwSoftGreTuUeSsid
    }
    STATUS      obsolete
    DESCRIPTION
        "The group of objects providing configuration of WLAN Gateway 
         Soft GRE group interfaces on Nokia SROS series systems."
    ::= { tmnxWlanGwGroups 2 }

tmnxWlanGwObjGroup OBJECT-GROUP
    OBJECTS {
        tmnxWlanGwIfRetailRowStatus,
        tmnxWlanGwIfRetailLastCh,
        tmnxWlanGwIfRetailService,
        tmnxWlanGwIfRetailTableLastCh,
        tmnxWlanGwUeQTag,
        tmnxWlanGwUeMplsLabel,
        tmnxWlanGwUeTuRouter,
        tmnxWlanGwUeTuAddrType,
        tmnxWlanGwUeTuRemoteAddr,
        tmnxWlanGwUeTuLocalAddr,
        tmnxWlanGwUeTuQosRetailService,
        tmnxWlanGwUeSsid,
        tmnxWlanGwUePrevApAddrType,
        tmnxWlanGwUePrevApAddr,
        tmnxWlanGwUeLastMoveTime,
        tmnxWlanGwSsidNumUe,
        tmnxWlanGwNumSoftGreTu,
        tmnxWlanGwPeakNumSoftGreTu,
        tmnxWlanGwNumUe,
        tmnxWlanGwPeakNumUe     
    }
    STATUS      obsolete
    DESCRIPTION
        "The group of objects providing configuration of WLAN Gateway 
         on Nokia SROS series systems."
    ::= { tmnxWlanGwGroups 3 }

tmnxWlanGwMgwGroup OBJECT-GROUP
    OBJECTS {
        tmnxWlanGwUeImsi,
        tmnxWlanGwMgwProfTableLastCh,
        tmnxWlanGwMgwProfRowStatus,
        tmnxWlanGwMgwProfLastChanged,
        tmnxWlanGwMgwProfDescription,
        tmnxWlanGwMgwProfKeepAlvRetryCnt,
        tmnxWlanGwMgwProfMsgReTxTimeout,
        tmnxWlanGwMgwProfMsgReTxRetryCnt,
        tmnxWlanGwMgwProfKeepAlvTimeout,
        tmnxWlanGwMgwProfKeepAlvResp,
        tmnxWlanGwMgwProfTtl,
        tmnxWlanGwMgwProfInterfaceType,
        tmnxWlanGwMgwAddrTableLastCh,
        tmnxWlanGwMgwAddrRowStatus,
        tmnxWlanGwMgwAddrLastMgmtChange,
        tmnxWlanGwMgwAddrProfile,
        tmnxWlanGwMgwLocalAddrType,
        tmnxWlanGwMgwLocalAddr,
        tmnxWlanGwMgwTime,
        tmnxWlanGwMgwProfile,
        tmnxWlanGwMgwControl,
        tmnxWlanGwMgwRestartCnt,
        tmnxWlanGwMgwState,
        tmnxWlanGwMgwInterfaceType,
        tmnxWlanMgwStatsName,
        tmnxWlanMgwStatsVal,
        tmnxWlanMgwStatsValLw,
        tmnxWlanMgwStatsValHw,
        tmnxWlanGwGtpSeMgwRouter,
        tmnxWlanGwGtpSeMgwAddrType,
        tmnxWlanGwGtpSeMgwAddr,
        tmnxWlanGwGtpSeRemoteCtrlTeid,
        tmnxWlanGwGtpSeLocalCtrlTeid,
        tmnxWlanGwBcRemoteTeid,
        tmnxWlanGwBcLocalTeid,
        tmnxWlanGwSysCfgServingNwMcc,
        tmnxWlanGwSysCfgServingNwMnc,
        tmnxWlanGwRowStatus,
        tmnxWlanGwLastCh,
        tmnxWlanGwApn,
        tmnxWlanGwTableLastCh,
        tmnxWlanGwNumMgw,
        tmnxWlanGwGtpStatsName,
        tmnxWlanGwGtpStatsVal,
        tmnxWlanGwGtpStatsValLw,
        tmnxWlanGwGtpStatsValHw
    }
    STATUS      current
    DESCRIPTION
        "The group of objects providing configuration of WLAN Gateway 
         Mobile Gateway profiles on Nokia SROS series systems."
    ::= { tmnxWlanGwGroups 4 }

tmnxWlanGwSoftGreV11v0Group OBJECT-GROUP
    OBJECTS {
        tmnxWlanGwSoftGreIfDataTrigg,
        tmnxWlanGwSoftGreIfAuthPlcy,
        tmnxWlanGwSoftGreIfAuthHoldTime,
        tmnxWlanGwSoftGreIfRadProxVrtr,
        tmnxWlanGwSoftGreIfRadProxSrv,
        tmnxWlanGwSoftGreIfRadProxMacFmt,
        tmnxWlanGwSoftGreIfGwV6AddrType,
        tmnxWlanGwSoftGreIfGwV6Addr,
        tmnxWlanGwSoftGreXtLastCh,
        tmnxWlanGwSoftGreXtDhcp,
        tmnxWlanGwSoftGreXtAddrType,
        tmnxWlanGwSoftGreXtAddr,
        tmnxWlanGwSoftGreXtLeaseTime,
        tmnxWlanGwSoftGreXtActLeaseTime,
        tmnxWlanGwSoftGreXtDns1AddrType,
        tmnxWlanGwSoftGreXtDns1Addr,
        tmnxWlanGwSoftGreXtDns2AddrType,
        tmnxWlanGwSoftGreXtDns2Addr,
        tmnxWlanGwSoftGreXtNb1AddrType,
        tmnxWlanGwSoftGreXtNb1Addr,
        tmnxWlanGwSoftGreXtNb2AddrType,
        tmnxWlanGwSoftGreXtNb2Addr,
        tmnxWlanGwSoftGreXtHttpRdrPlcy,
        tmnxWlanGwSoftGreXtNatPlcy,
        tmnxWlanGwVlanTableLastCh,
        tmnxWlanGwVlanLastCh,
        tmnxWlanGwVlanRowStatus,
        tmnxWlanGwVlanRetailService,
        tmnxWlanGwVlanDhcp,
        tmnxWlanGwVlanAddrType,
        tmnxWlanGwVlanAddr,
        tmnxWlanGwVlanLeaseTime,
        tmnxWlanGwVlanActLeaseTime,
        tmnxWlanGwVlanDns1AddrType,
        tmnxWlanGwVlanDns1Addr,
        tmnxWlanGwVlanDns2AddrType,
        tmnxWlanGwVlanDns2Addr,
        tmnxWlanGwVlanNb1AddrType,
        tmnxWlanGwVlanNb1Addr,
        tmnxWlanGwVlanNb2AddrType,
        tmnxWlanGwVlanNb2Addr,    
        tmnxWlanGwVlanHttpRdrPlcy,
        tmnxWlanGwVlanNatPlcy,
        tmnxWlanGwVlanDataTrigg,
        tmnxWlanGwVlanAuthPlcy,
        tmnxWlanGwVlanAuthHoldTime,
        tmnxWlanGwVlanRadProxVrtr,
        tmnxWlanGwVlanRadProxSrv,
        tmnxWlanGwVlanRadProxMacFmt
    }
    STATUS      obsolete
    DESCRIPTION
        "The group of objects providing configuration of WLAN Gateway 
         Soft GRE group interfaces on Nokia SROS series systems,
         added in release 11.0."
    ::= { tmnxWlanGwGroups 5 }

tmnxWlanGwMgwV11v0Group OBJECT-GROUP
    OBJECTS {
        tmnxWlanGwMgwArecCacheAddrType,
        tmnxWlanGwMgwArecCacheAddr,
        tmnxWlanGwMgwArecCacheTtl
        ,tmnxWlanGwMgwSnaptrCachePref,
        tmnxWlanGwMgwSnaptrCacheService,
        tmnxWlanGwMgwSnaptrCacheNext,
        tmnxWlanGwMgwSnaptrCacheRepl,
        tmnxWlanGwMgwSnaptrCacheTtl,
        tmnxWlanGwMgwSrvCacheWeight,
        tmnxWlanGwMgwSrvCachePort,
        tmnxWlanGwMgwSrvCacheTarget,
        tmnxWlanGwMgwSrvCacheTtl        
    }
    STATUS      current
    DESCRIPTION
        "The group of objects providing management of WLAN Gateway 
         Mobile Gateways on Nokia SROS series systems,
         added in release 11.0."
    ::= { tmnxWlanGwGroups 6 }

tmnxWlanGwMgwQosIeGroup OBJECT-GROUP
    OBJECTS {
        tmnxWlanGwPgwLastChanged,
        tmnxWlanGwPgwQosUplinkGbrRate,
        tmnxWlanGwPgwQosUplinkMbrRate,
        tmnxWlanGwPgwQosDwnlinkGbrRate,
        tmnxWlanGwPgwQosDwnlinkMbrRate,
        tmnxWlanGwPgwQosArpValue,
        tmnxWlanGwPgwQosQciValue,         
        tmnxWlanGwGgsnLastChanged,
        tmnxWlanGwGgsnQosUplinkGbrRate,
        tmnxWlanGwGgsnQosUplinkMbrRate,
        tmnxWlanGwGgsnQosDwnlinkGbrRate,
        tmnxWlanGwGgsnQosDwnlinkMbrRate,
        tmnxWlanGwGgsnQosArpValue,
        tmnxWlanGwPgwTableLastCh,
        tmnxWlanGwGgsnTableLastCh,
        tmnxWlanGwBcQosUlGbr,
        tmnxWlanGwBcQosUlMbr,
        tmnxWlanGwBcQosDlGbr,
        tmnxWlanGwBcQosDlMbr,
        tmnxWlanGwBcQosArp,
        tmnxWlanGwBcQosQci
    }
    STATUS      current
    DESCRIPTION
        "The group of objects providing management of WLAN Gateway 
         Mobile Gateways QOS IE on Nokia SROS series systems."
    ::= { tmnxWlanGwGroups 10 }


tmnxWlanGwMgwChargingCharGroup OBJECT-GROUP
    OBJECTS {
        tmnxWlanGwMgwProfChrgCharHome,
        tmnxWlanGwMgwProfChrgCharRoam,
        tmnxWlanGwGtpSeChrgChar
    }
    STATUS      current
    DESCRIPTION
        "The group of objects providing management of WLAN Gateway 
         Mobile Gateways Charging Characteristics on Nokia
         SROS series systems."
    ::= { tmnxWlanGwGroups 11 }

tmnxWlanGwMobilityGroup OBJECT-GROUP
    OBJECTS {
        tmnxWlanGwMobAcctInterimUpdate,
        tmnxWlanGwSoftGreIfMobArpAp,
        tmnxWlanGwSoftGreTuApMacAddress,
        tmnxWlanGwSoftGreTuApLearnFailed
    }
    STATUS      current
    DESCRIPTION
        "The group of objects providing management of WLAN Gateway 
         UE Mobility on Nokia SROS series systems."
    ::= { tmnxWlanGwGroups 15 }

tmnxWlanGwMgwSeHoldTimeGroup OBJECT-GROUP
    OBJECTS {
        tmnxWlanGwMgwProfSeHoldTime,
        tmnxWlanGwSysCfgMgwMaxHeldSe,
        tmnxWlanGwMgwNumHeldSe
     }
    STATUS      current
    DESCRIPTION
        "The group of objects providing management of WLAN Gateway 
         Mobile Gateways GTP session hold-timers on Nokia
         SROS series systems."
    ::= { tmnxWlanGwGroups 16 }

tmnxWlanGwV12v0Group OBJECT-GROUP
    OBJECTS {
        tmnxWlanGwGrpDegraded,
        tmnxWlanGwUeQTag,
        tmnxWlanGwUeMplsLabel,
        tmnxWlanGwUeTuRouter,
        tmnxWlanGwUeTuAddrType,
        tmnxWlanGwUeTuRemoteAddr,
        tmnxWlanGwUeTuLocalAddr,
        tmnxWlanGwUeTuQosRetailService,
        tmnxWlanGwUeSsid,
        tmnxWlanGwUePrevApAddrType,
        tmnxWlanGwUePrevApAddr,
        tmnxWlanGwUeLastMoveTime,
        tmnxWlanGwSsidNumUe,
        tmnxWlanGwNumSoftGreTu,
        tmnxWlanGwPeakNumSoftGreTu,
        tmnxWlanGwNumUe,
        tmnxWlanGwPeakNumUe,
        tmnxWlanGwMgwProfReportWlanLoc,     
        tmnxWlanGwMgwProfProtocolCfgOpt,
        tmnxWlanGwUeService,
        tmnxWlanGwUeSapPortId,            
        tmnxWlanGwUeSapPortEncapValue
    }
    STATUS      current
    DESCRIPTION
        "The group of objects providing configuration of WLAN Gateway 
         added in release 12.0 of Nokia SROS series systems."
    ::= { tmnxWlanGwGroups 17 }

tmnxWlanGwSoftGreV12v0Group OBJECT-GROUP
    OBJECTS {
        tmnxWlanGwSoftGreIfLastCh,
        tmnxWlanGwSoftGreIfAdminState,
        tmnxWlanGwSoftGreIfRouter,
        tmnxWlanGwSoftGreIfGwAddrType,
        tmnxWlanGwSoftGreIfGwAddr,
        tmnxWlanGwSoftGreIfGrpId,
        tmnxWlanGwSoftGreIfShapingType,
        tmnxWlanGwSoftGreIfShapeMultiUe,
        tmnxWlanGwSoftGreIfEQosPlcy,
        tmnxWlanGwSoftGreIfESchedPlcy,
        tmnxWlanGwSoftGreIfEAggRateLimit,
        tmnxWlanGwSoftGreIfMobTrigger,
        tmnxWlanGwSoftGreIfMobHoldTime,
        tmnxWlanGwSoftGreIfDefRetailSvc,
        tmnxWlanGwSoftGreIfTcpMssAdjust,
        tmnxWlanGwSoftGreIfEHoldTime,
        tmnxWlanGwSoftGreIfNumSoftGreTu,
        tmnxWlanGwSoftGreIfTableLastCh,
        tmnxWlanGwSoftGreTuEstabTime,
        tmnxWlanGwSoftGreTuIsaGroup,
        tmnxWlanGwSoftGreTuIsaMember,
        tmnxWlanGwSoftGreTuNumUe,
        tmnxWlanGwTuQosEegSvcId,
        tmnxWlanGwTuQosEegPortId ,
        tmnxWlanGwTuQosEegEncapValue,
        tmnxWlanGwTuQosEegName,
        tmnxWlanGwTuQosEegMember,
        tmnxWlanGwTuQosState,     
        tmnxWlanGwTuQosNumUe,
        tmnxWlanGwTuQosRemainingHoldTime,     
        tmnxWlanGwSoftGreTuUeSsid,
        tmnxWlanGwSoftGreIfGwV6AddrType,
        tmnxWlanGwSoftGreIfGwV6Addr,
        tmnxWlanGwVlanTableLastCh,
        tmnxWlanGwVlanLastCh,
        tmnxWlanGwVlanRowStatus,
        tmnxWlanGwVlanRetailService,
        tmnxWlanGwVlanDhcp,
        tmnxWlanGwVlanAddrType,
        tmnxWlanGwVlanAddr,
        tmnxWlanGwVlanLeaseTime,
        tmnxWlanGwVlanActLeaseTime,
        tmnxWlanGwVlanDns1AddrType,
        tmnxWlanGwVlanDns1Addr,
        tmnxWlanGwVlanDns2AddrType,
        tmnxWlanGwVlanDns2Addr,
        tmnxWlanGwVlanNb1AddrType,
        tmnxWlanGwVlanNb1Addr,
        tmnxWlanGwVlanNb2AddrType,
        tmnxWlanGwVlanNb2Addr,    
        tmnxWlanGwVlanHttpRdrPlcy,
        tmnxWlanGwVlanNatPlcy,
        tmnxWlanGwVlanDataTrigg,
        tmnxWlanGwVlanAuthPlcy,
        tmnxWlanGwVlanAuthHoldTime,
        tmnxWlanGwVlanRadProxVrtr,
        tmnxWlanGwVlanRadProxSrv,
        tmnxWlanGwVlanRadProxMacFmt,
        tmnxWlanGwSoftGreIfDownIfGrpDeg
    }
    STATUS      current
    DESCRIPTION
        "The group of objects providing configuration of WLAN Gateway 
         Soft GRE group interfaces on Nokia SROS series systems,
         supported in release 12.0."
    ::= { tmnxWlanGwGroups 18 }


tmnxWlanGwRedGroup OBJECT-GROUP
    OBJECTS {
        tmnxWlanGwSubIfTableLastCh,
        tmnxWlanGwSubIfRowStatus,
        tmnxWlanGwSubIfLastCh,
        tmnxWlanGwSubIfRedExpPrefixType,
        tmnxWlanGwSubIfRedExpPrefix,
        tmnxWlanGwSubIfRedExpPrefixLen,
        tmnxWlanGwSubIfRedMonPrefixType,
        tmnxWlanGwSubIfRedMonPrefix,
        tmnxWlanGwSubIfRedMonPrefixLen,
        tmnxWlanGwSubIfRedAdminState,
        tmnxWlanGwSubIfRedActive,
        tmnxWlanGwSubIfRedSwitch
    }
    STATUS      current
    DESCRIPTION
        "The group of objects providing configuration of WLAN Gateway 
         redundancy on Nokia SROS series systems."
    ::= { tmnxWlanGwGroups 19 }

tmnxWlanGwDsmGroup OBJECT-GROUP
    OBJECTS {
        tmnxWlanGwGrpIsaAaGroup,
        tmnxWlanGwVlanAuthOnDhcp,
        tmnxWlanGwVlanDsmLastCh,
        tmnxWlanGwVlanDsmAdminState,
        tmnxWlanGwVlanDsmAcctPlcy,
        tmnxWlanGwVlanDsmEgressPolicer,
        tmnxWlanGwVlanDsmIngressPolicer,
        tmnxWlanGwVlanDsmIpFilter,     
        tmnxWlanGwVlanDsmOneTimeRdrUrl,     
        tmnxWlanGwVlanDsmOneTimeRdrPort,
        tmnxWlanGwVlanDsmAcctUpdInterv,
        tmnxWlanGwVlanDsmDefAppProfile,
        tmnxWlanGwVlanDsmTableLastCh,
        tmnxWlanGwDsmIpFilTableLastCh,
        tmnxWlanGwDsmIpFilRowStatus,
        tmnxWlanGwDsmIpFilLastCh,
        tmnxWlanGwDsmIpFilDescription,       
        tmnxWlanGwDsmIpFilDefaultAction,       
        tmnxWlanGwDsmIpFilDefaultAction6,       
        tmnxWlanGwDsmIpFilN3TableLastCh,
        tmnxWlanGwDsmIpFilN3RowStatus,
        tmnxWlanGwDsmIpFilN3LastCh,
        tmnxWlanGwDsmIpFilN3Description,       
        tmnxWlanGwDsmIpFilN3Action,
        tmnxWlanGwDsmIpFilN3Protocol,
        tmnxWlanGwDsmIpFilN3DestAddrType,
        tmnxWlanGwDsmIpFilN3DestAddr,
        tmnxWlanGwDsmIpFilN3DestPrefLen,
        tmnxWlanGwDsmIpFilN3DestPortOp,
        tmnxWlanGwDsmIpFilN3DestPort1,
        tmnxWlanGwDsmIpFil6N3TableLastCh,
        tmnxWlanGwDsmIpFil6N3RowStatus,
        tmnxWlanGwDsmIpFil6N3LastCh,
        tmnxWlanGwDsmIpFil6N3Description,
        tmnxWlanGwDsmIpFil6N3Action,
        tmnxWlanGwDsmIpFil6N3Protocol,
        tmnxWlanGwDsmIpFil6N3DestAddrTyp,
        tmnxWlanGwDsmIpFil6N3DestAddr,
        tmnxWlanGwDsmIpFil6N3DestPrefLen,
        tmnxWlanGwDsmIpFil6N3DestPortOp,
        tmnxWlanGwDsmIpFil6N3DestPort1,
        tmnxWlanGwDsmTableLastCh,
        tmnxWlanGwDsmLastCh,
        tmnxWlanGwDsmIpv6TcpMssAdjust,
        tmnxWlanGwPolicerRowLastChange,
        tmnxWlanGwPolicerRowStatus,
        tmnxWlanGwPolicerDescription,
        tmnxWlanGwPolicerType ,
        tmnxWlanGwPolicerAction,
        tmnxWlanGwPolicerAdminPIR,
        tmnxWlanGwPolicerAdminCIR,
        tmnxWlanGwPolicerMBS,
        tmnxWlanGwPolicerCBS,
        tmnxWlanGwPolicerPIRAdaptation,
        tmnxWlanGwPolicerCIRAdaptation,
        tmnxWlanGwPolicerTableLastCh
    }
    STATUS      current
    DESCRIPTION
        "The group of objects providing configuration of WLAN Gateway 
         Distributed subscriber management on Nokia SROS series systems."
    ::= { tmnxWlanGwGroups 20 }



tmnxWlanGwUeQryGroup OBJECT-GROUP
    OBJECTS {
        tmnxWlanGwUeNextQryId,
        tmnxWlanGwUeMaxQryId,
        tmnxWlanGwUeQryRowStatus,
        tmnxWlanGwUeQryWhereState,
        tmnxWlanGwUeQryWhereMacAddress,
        tmnxWlanGwUeQryWhereAddrType,
        tmnxWlanGwUeQryWhereAddr,
        tmnxWlanGwUeQryWhereIsaGrp,
        tmnxWlanGwUeQryWhereMemberId, 
        tmnxWlanGwUeQryWhereQTag,       
        tmnxWlanGwUeQryWhereTuRouter,
        tmnxWlanGwUeQryWhereTuRemAddrTyp,
        tmnxWlanGwUeQryWhereTuRemAddr,
        tmnxWlanGwUeQryWhereTuLocAddrTyp,
        tmnxWlanGwUeQryWhereTuLocAddr,
        tmnxWlanGwUeQryWhereEncap,
        tmnxWlanGwUeQryWhereSlaacPrefTyp,
        tmnxWlanGwUeQryWhereSlaacPref,
        tmnxWlanGwUeQryWhereDhcp6AddrTyp,
        tmnxWlanGwUeQryWhereDhcp6Addr,
        tmnxWlanGwUeQryNumResults,
        tmnxWlanGwUeResMacAddress,
        tmnxWlanGwUeResAddrType,
        tmnxWlanGwUeResAddr,
        tmnxWlanGwUeResState,
        tmnxWlanGwUeResIsaGrp,
        tmnxWlanGwUeResIsaMemberId,       
        tmnxWlanGwUeResQTag,       
        tmnxWlanGwUeResTuRouter,
        tmnxWlanGwUeResTuAddrType,
        tmnxWlanGwUeResTuLocalAddr,
        tmnxWlanGwUeResEncapsulation,
        tmnxWlanGwUeResTuRemoteAddr,
        tmnxWlanGwUeResSsid,
        tmnxWlanGwUeResApMacAddress,
        tmnxWlanGwUeResMplsLabel,
        tmnxWlanGwUeResLastMoveTime,
        tmnxWlanGwUeResExpirationTime,
        tmnxWlanGwUeResIdleTimeout,
        tmnxWlanGwUeResSessionTimeout,
        tmnxWlanGwUeResNatPlcy,
        tmnxWlanGwUeResHttpRdrPlcy,
        tmnxWlanGwUeResDsmIpFilter,
        tmnxWlanGwUeResDsmAcctPlcy,
        tmnxWlanGwUeResDsmAcctUpdInterv,
        tmnxWlanGwUeResAcctUpdate,
        tmnxWlanGwUeResIngOperPir,
        tmnxWlanGwUeResIngOperCir,
        tmnxWlanGwUeResEgrOperPir,
        tmnxWlanGwUeResEgrOperCir,
        tmnxWlanGwUeResDsmAppProfile,
        tmnxWlanGwUeResRxPkts,                    
        tmnxWlanGwUeResRxOctets,                    
        tmnxWlanGwUeResTxPkts,                    
        tmnxWlanGwUeResTxOctets,                    
        tmnxWlanGwUeResSlaacAddrType,
        tmnxWlanGwUeResSlaacPref,
        tmnxWlanGwUeResSlaacAddr1,
        tmnxWlanGwUeResSlaacAddr2,
        tmnxWlanGwUeResSlaacAddr3,
        tmnxWlanGwUeResDhcp6AddrType,
        tmnxWlanGwUeResDhcp6Addr,
        tmnxWlanGwUeResDhcp6AddrDepr,
        tmnxWlanGwUeResDhcp6IAID,
        tmnxWlanGwUeResDhcp6IAIDValid,
        tmnxWlanGwUeResSlaacLeaseExpire,
        tmnxWlanGwUeResDhcp6LeaseExpire
    }
    STATUS      current
    DESCRIPTION
        "The group of objects providing queries for
         User Equipment on Nokia SROS series systems."
    ::= { tmnxWlanGwGroups 23 }

tmnxWlanGwDsmV13v0Group  OBJECT-GROUP
    OBJECTS {
        tmnxWlanGwVlanL2Service,
        tmnxWlanGwVlanL2AdminState,
        tmnxWlanGwVlanL2Description,
        tmnxWlanGwVplsAdminState,
        tmnxWlanGwVplsDescription,
        tmnxWlanGwVplsSapTemplate,
        tmnxWlanGwVplsTableLastCh,
        tmnxWlanGwVplsLastMgmtChange,
        tmnxWlanGwSubIfPmTableLastCh,
        tmnxWlanGwSubIfPmLastChanged,
        tmnxWlanGwSubIfPmWatermarkHigh,
        tmnxWlanGwSubIfPmWatermarkLow,
        tmnxWlanGwSubIfPmWlanGwGroup,
        tmnxWlanGwSubIfPmD6cServer1,
        tmnxWlanGwSubIfPmD6cServer2,
        tmnxWlanGwSubIfPmD6cServer3,
        tmnxWlanGwSubIfPmD6cServer4,
        tmnxWlanGwSubIfPmD6cServer5,
        tmnxWlanGwSubIfPmD6cServer6,
        tmnxWlanGwSubIfPmD6cServer7,
        tmnxWlanGwSubIfPmD6cServer8,
        tmnxWlanGwSubIfPmD6cLeaseQuery,
        tmnxWlanGwSubIfPmD6cLeaseQueryMR,
        tmnxWlanGwSubIfPmD6cSourceIp,
        tmnxWlanGwSubIfPmD6cSlaacPoolNm,
        tmnxWlanGwSubIfPmD6cSlaacLinkAdd,
        tmnxWlanGwSubIfPmD6cSlaacAdminSt,
        tmnxWlanGwSubIfPmD6cIaNaPoolNm,
        tmnxWlanGwSubIfPmD6cIaNaLinkAdd,
        tmnxWlanGwSubIfPmD6cIaNaAdminSt,
        tmnxWlanGwSubIfIpsSubIfIndex,
        tmnxWlanGwSubIfIpsSubnetAddrType,
        tmnxWlanGwSubIfIpsSubnetAddr,
        tmnxWlanGwSubIfIpsSubnetPrefLen,
        tmnxWlanGwSubIfIpsAddrFamily,
        tmnxWlanGwSubIfIpsPoolIsOld,
        tmnxWlanGwSubIfIpsUsageLevelPct,
        tmnxWlanGwSubIfIpsDHCPv6Options,
        tmnxWlanGwSubIfIpsRemLeaseTime,
        tmnxWlanGwSubIfIpsIsaGrpId,
        tmnxWlanGwSubIfIpsIsaMemberId,
        tmnxWlanGwSubIfIpsServiceId,
        tmnxWlanGwVlanDhcp6TableLastCh,
        tmnxWlanGwVlanDhcp6LastChanged,
        tmnxWlanGwVlanDhcp6InitPrefLt,
        tmnxWlanGwVlanDhcp6ActPrefLt,
        tmnxWlanGwVlanDhcp6InitValidLt,
        tmnxWlanGwVlanDhcp6ActValidLt,
        tmnxWlanGwVlanDhcp6AdminState,
        tmnxWlanGwVlanSlaacTableLastCh,
        tmnxWlanGwVlanSlaacLastChanged,
        tmnxWlanGwVlanSlaacInitPrefLt,
        tmnxWlanGwVlanSlaacActPrefLt,
        tmnxWlanGwVlanSlaacInitValidLt,
        tmnxWlanGwVlanSlaacActValidLt,
        tmnxWlanGwVlanSlaacAdminState,
        tmnxWlanGwSysCfgVirtChassisId,
        tmnxWlanGwVlanIdleTimeoutAction
    }
    STATUS      current
    DESCRIPTION
        "The group of objects providing configuration of WLAN Gateway 
         Distributed subscriber management on Nokia SROS series systems,
         added in release 13.0."
    ::= { tmnxWlanGwGroups 25 }
tmnxWlanGwL2ApGroup OBJECT-GROUP
    OBJECTS {
        tmnxWlanGwSoftGreIfL2ApEncapType,
        tmnxWlanGwSoftGreTuEncap,     
        tmnxWlanGwSoftGreTuEncapTag1,     
        tmnxWlanGwSoftGreTuEncapTag2,
        tmnxWlanGwSoftGreTuService,
        tmnxWlanGwSoftGreTuInterface,
        tmnxWlanGwUeEncapsulation,     
        tmnxWlanGwL2ApRowStatus,
        tmnxWlanGwL2ApLastCh,
        tmnxWlanGwL2ApAdminState,
        tmnxWlanGwL2ApEncapType,
        tmnxWlanGwL2ApEpipeSapTemplate,
        tmnxWlanGwL2ApId,
        tmnxWlanGwL2ApTableLastCh 
    }
    STATUS      current
    DESCRIPTION
        "The group of objects providing configuration of WLAN Gateway 
         Layer 2 Access Points on Nokia SROS series systems."
    ::= { tmnxWlanGwGroups 26 }

tmnxWlanGwL2tpv3Group OBJECT-GROUP
    OBJECTS {
        tmnxWlanGwSoftGreIfMultiTuType,
        tmnxWlanGwSoftGreIfL2tpLrnCookie,
        tmnxWlanGwSoftGreIfL2tpCookie
    }
    STATUS      current
    DESCRIPTION
        "The group of objects providing configuration of 
         L2TP tunnel connections with Access Points
         on Nokia SROS series systems."
    ::= { tmnxWlanGwGroups 27 }


tmnxWlanGwObsoletedGroup     OBJECT-GROUP
    OBJECTS {   
        tmnxWlanGwMgwCacheTtl,
        tmnxWlanGwIfRetailRowStatus,
        tmnxWlanGwIfRetailLastCh,
        tmnxWlanGwIfRetailService,
        tmnxWlanGwIfRetailTableLastCh,
        tmnxWlanGwSoftGreIfDataTrigg,
        tmnxWlanGwSoftGreIfAuthPlcy,
        tmnxWlanGwSoftGreIfAuthHoldTime,
        tmnxWlanGwSoftGreIfRadProxVrtr,
        tmnxWlanGwSoftGreIfRadProxSrv,
        tmnxWlanGwSoftGreIfRadProxMacFmt,
        tmnxWlanGwSoftGreXtLastCh,
        tmnxWlanGwSoftGreXtDhcp,
        tmnxWlanGwSoftGreXtAddrType,
        tmnxWlanGwSoftGreXtAddr,
        tmnxWlanGwSoftGreXtLeaseTime,
        tmnxWlanGwSoftGreXtActLeaseTime,
        tmnxWlanGwSoftGreXtDns1AddrType,
        tmnxWlanGwSoftGreXtDns1Addr,
        tmnxWlanGwSoftGreXtDns2AddrType,
        tmnxWlanGwSoftGreXtDns2Addr,
        tmnxWlanGwSoftGreXtNb1AddrType,
        tmnxWlanGwSoftGreXtNb1Addr,
        tmnxWlanGwSoftGreXtNb2AddrType,
        tmnxWlanGwSoftGreXtNb2Addr,
        tmnxWlanGwSoftGreXtHttpRdrPlcy,
        tmnxWlanGwSoftGreXtNatPlcy
    }
    STATUS        current
    DESCRIPTION
        "The group of obsoleted WLAN Gateway objects
         on Nokia SROS series systems."
    ::= { tmnxWlanGwGroups 98 }
    
tmnxWlanGwNotifyObjsGroup     OBJECT-GROUP
    OBJECTS {   
        tmnxWlanGwNotifyDescription,
        tmnxWlanGwNotifyTrue,
        tmnxWlanGwNotify3gppRelease,
        tmnxWlanGwNotifyMdaSlotNum,
        tmnxWlanGwNotifySubIfIndex,
        tmnxWlanGwNotifyAddrFamily,
        tmnxWlanGwNotifyIsaGrpId,
        tmnxWlanGwNotifyIsaMemberId,
        tmnxWlanGwNotifyD6cServer1,
        tmnxWlanGwNotifyD6cServer2,
        tmnxWlanGwNotifyD6cServer3,
        tmnxWlanGwNotifyD6cServer4,
        tmnxWlanGwNotifyD6cServer5,
        tmnxWlanGwNotifyD6cServer6,
        tmnxWlanGwNotifyD6cServer7,
        tmnxWlanGwNotifyD6cServer8,
        tmnxWlanGwNotifySubnetAddrType,
        tmnxWlanGwNotifySubnetAddr,
        tmnxWlanGwNotifySubnetPrefLen
    }
    STATUS        current
    DESCRIPTION
        "The group of notification objects supporting WLAN Gateway notifications
         on Nokia SROS series systems."
    ::= { tmnxWlanGwGroups 99 }
    
tmnxWlanGwNotifyGroup NOTIFICATION-GROUP
    NOTIFICATIONS {
        tmnxWlanGwResrcProblemDetected,
        tmnxWlanGwResrcProblemCause,
        tmnxWlanGwTuQosProblem,
        tmnxWlanGwGrpOperStateChanged,
        tmnxWlanGwIomActive,
        tmnxWlanGwMgwConnected,
        tmnxWlanGwMgwRestarted,
        tmnxWlanGwNumMgwHi,
        tmnxWlanGwMgwStateChanged,
        tmnxWlanGwQosRadiusGtpMismatch,
        tmnxWlanGwDsmGtpTunnelSetupFail,
        tmnxWlanGwSubIfRedActiveChanged,
        tmnxWlanGwSubIfPmStartD6cFailed,
        tmnxWlanGwSubIfPmNewPlReqFailed,
        tmnxWlanGwSubIfPmAddNewPlFailed,
        tmnxWlanGwSubIfPmCrIntObjFailed,
        tmnxWlanGwSubIfPmPoolTimeout,
        tmnxWlanGwSubIfPmPoolUsageLow,
        tmnxWlanGwSubIfPmLsQryRtryFailed
    }
    STATUS      current
    DESCRIPTION
        "The group of notifications supporting WLAN Gateway
         on Nokia SROS series systems."
    ::= { tmnxWlanGwGroups 100 }

-- ----------------------------------------------------------------------------
--  Conformance information
-- ----------------------------------------------------------------------------
tmnxWlanGwCompliance MODULE-COMPLIANCE
    STATUS  obsolete
    DESCRIPTION
        "The compliance statement for management of WLAN Gateway
         on Nokia 7xxx series systems."
    MODULE  -- this module
        MANDATORY-GROUPS {
            tmnxWlanGwIsaGroup,
            tmnxWlanGwSoftGreGroup,
            tmnxWlanGwObjGroup
        }
    ::= { tmnxWlanGwCompliances 1 }

tmnxWlanGwNotifyCompliance MODULE-COMPLIANCE
    STATUS  current
    DESCRIPTION
        "The compliance statement for WLAN Gateway notifications
         on Nokia SROS series systems."
    MODULE  -- this module
        MANDATORY-GROUPS {
            tmnxWlanGwNotifyGroup
        }
    ::= { tmnxWlanGwCompliances 2 }

tmnxWlanGwV10Compliance MODULE-COMPLIANCE
    STATUS  obsolete
    DESCRIPTION
        "The compliance statement for management of WLAN Gateway
         on Nokia 7xxx series systems."
    MODULE  -- this module
        MANDATORY-GROUPS {
            tmnxWlanGwIsaGroup,
            tmnxWlanGwSoftGreGroup,
            tmnxWlanGwObjGroup,
            tmnxWlanGwMgwGroup
        }
    ::= { tmnxWlanGwCompliances 3 }

tmnxWlanGwV11Compliance MODULE-COMPLIANCE
    STATUS  obsolete
    DESCRIPTION
        "The compliance statement for management of WLAN Gateway
         on Nokia 7xxx series systems."
    MODULE  -- this module
        MANDATORY-GROUPS {
            tmnxWlanGwIsaGroup,
            tmnxWlanGwSoftGreGroup,
            tmnxWlanGwSoftGreV11v0Group,
            tmnxWlanGwObjGroup,
            tmnxWlanGwMgwGroup,
            tmnxWlanGwMgwV11v0Group,
            tmnxWlanGwMgwQosIeGroup,
            tmnxWlanGwMgwChargingCharGroup,
            tmnxWlanGwObsoletedGroup
        }
    ::= { tmnxWlanGwCompliances 4 }

tmnxWlanGwV12Compliance MODULE-COMPLIANCE
    STATUS  obsolete
    DESCRIPTION
        "The compliance statement for management of WLAN Gateway
         on Nokia 7xxx series systems
         release 12.0."
    MODULE  -- this module
        MANDATORY-GROUPS {
            tmnxWlanGwIsaGroup,
            tmnxWlanGwSoftGreV12v0Group,
            tmnxWlanGwRedGroup,

            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMgwSeHoldTimeGroup,
            tmnxWlanGwDsmGroup,
            tmnxWlanGwObsoletedGroup
        }
    ::= { tmnxWlanGwCompliances 5 }

tmnxWlanGwV13Compliance MODULE-COMPLIANCE
    STATUS  current
    DESCRIPTION
        "The compliance statement for management of WLAN Gateway
         on Nokia 7xxx series systems
         release 12.0."
    MODULE  -- this module
        MANDATORY-GROUPS {
            tmnxWlanGwIsaGroup,
            tmnxWlanGwSoftGreV12v0Group,
            tmnxWlanGwRedGroup,

            tmnxWlanGwV12v0Group,
            tmnxWlanGwMgwGroup,
            tmnxWlanGwMgwV11v0Group,
            tmnxWlanGwMgwQosIeGroup,
            tmnxWlanGwMgwChargingCharGroup,
            tmnxWlanGwMobilityGroup,
            tmnxWlanGwMgwSeHoldTimeGroup,
            tmnxWlanGwDsmGroup,
            tmnxWlanGwUeQryGroup,
            tmnxWlanGwDsmV13v0Group,
            tmnxWlanGwL2ApGroup,
            tmnxWlanGwL2tpv3Group,
            tmnxWlanGwObsoletedGroup
        }
    ::= { tmnxWlanGwCompliances 6 }

END
