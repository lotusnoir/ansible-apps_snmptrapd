ADVA-MIB DEFINITIONS ::= BEGIN

IMPORTS
    MODULE-IDENTITY,
    OBJECT-IDENTITY,
    OBJECT-TYPE,
    NOTIFICATION-TYPE,
    enterprises,
    Integer32,
    Unsigned32,
    IpAddress,
    Counter32,
    Counter64,
    Gauge32,
    TimeTicks,
    mib-2,
    snmpModules
                                        FROM  SNMPv2-SMI
    ifIndex
                                        FROM  IF-MIB
    entPhysicalIndex
                                        FROM  ENTITY-MIB
    DisplayString,
    RowStatus,
    TEXTUAL-CONVENTION,
    DateAndTime,
    TestAndIncr,
    TimeStamp, MacAddress
                                        FROM  SNMPv2-TC
    SnmpAdminString
                                        FROM  SNMP-FRAMEWORK-MIB
    MODULE-COMPLIANCE,
    NOTIFICATION-GROUP,
    OBJECT-GROUP
                                        FROM  SNMPv2-CONF;


advaMIB MODULE-IDENTITY
    LAST-UPDATED "200802210000Z"  -- February 21, 2008
    ORGANIZATION "ADVA AG Optical Networking"
    CONTACT-INFO
        "ADVA AG Optical Networking
        Justus-von-Liebig-Str. 7
        12489 Berlin, Germany

        Support Europe:
        Phone:  +49 89 89 0665 848
        Fax:    +49 89 89 0665 22848
        e-mail: support@advaoptical.com

        Support USA:
        Phone:  +1 201 995 0080
        Fax:    +1 201 995 0081
        e-mail: support-usa@advaoptical.com

        Support Asia:
        Phone:  +81 3 5408 5891
        Fax:    +81 3 5408 5899
        e-mail: support-asia@advaoptical.com"
    DESCRIPTION
        "The ADVA Optical Networking base MIB."

    REVISION    "200802210000Z"  -- February 21, 2008
    DESCRIPTION
        "Revised ADVA Common MIB version 2.0."

    REVISION    "200412140000Z"  -- December 14, 2004
    DESCRIPTION
        "The ADVA Common MIB version 1.7."

    REVISION    "200402200000Z" -- February 20, 2004
    DESCRIPTION
        "The ADVA Common MIB version 1.6."

    REVISION    "200312120000Z" -- December 12, 2003
    DESCRIPTION
        "The ADVA Common MIB version 1.5."

    REVISION    "200310070000Z" -- October 07, 2003
    DESCRIPTION
        "The ADVA Common MIB version 1.4."

    REVISION    "200306270000Z" -- June 27, 2003
    DESCRIPTION
        "The ADVA Common MIB version 1.3"

    REVISION    "200207220000Z" -- July 22, 2002
    DESCRIPTION
        "The ADVA MIB version 1.3."
        ::= { enterprises 2544 }

products        OBJECT IDENTIFIER ::= { advaMIB 1 }
common          OBJECT IDENTIFIER ::= { advaMIB 2 }


-- **************************************************************************
-- **************************  ADVA Products  *******************************
-- **************************************************************************

fsp3000               OBJECT IDENTIFIER ::= { products 4 }
fsp1000               OBJECT IDENTIFIER ::= { products 6 }
fsp2000               OBJECT IDENTIFIER ::= { products 7 }
fsp1000adm            OBJECT IDENTIFIER ::= { products 8 }
fsp1500               OBJECT IDENTIFIER ::= { products 9 }
fsp150                OBJECT IDENTIFIER ::= { products 10 }
fspR7                 OBJECT IDENTIFIER ::= { products 11 }
fsp150cm              OBJECT IDENTIFIER ::= { products 12 }
fspNm                 OBJECT IDENTIFIER ::= { products 13 }
fsp3000alm            OBJECT IDENTIFIER ::= { products 14 }

aos                   OBJECT IDENTIFIER ::= { products 20 }
aosCommon             OBJECT IDENTIFIER ::= { aos 1 }
aosProducts           OBJECT IDENTIFIER ::= { aos 2 }

fsp3000c              OBJECT IDENTIFIER ::= { aosProducts 1 }
fspxg480              OBJECT IDENTIFIER ::= { aosProducts 2 }


END
