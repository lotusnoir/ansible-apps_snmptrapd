--  ***************************************************************************
--  ADVA-FSPR7-TC-MIB.txt
--
--               ADVA AG Optical Networking MIB File
--
--  Copyright 2011 ADVA AG Optical Networking.
--
--  All rights reserved.
--  ***************************************************************************

--  Definition of textual conventions.



ADVA-FSPR7-TC-MIB DEFINITIONS ::= BEGIN

IMPORTS
    TEXTUAL-CONVENTION
                                        FROM  SNMPv2-TC
    MODULE-IDENTITY
                                        FROM  SNMPv2-SMI
    fspR7
                                        FROM  ADVA-MIB;
    

advaFspR7Tc MODULE-IDENTITY

    LAST-UPDATED "201105220000Z"

    ORGANIZATION "ADVA Optical Networking"

    CONTACT-INFO "EMEA Support
                  Phone : +49 89 89 0665 848
                  Fax   : +49 89 89 0665 22848
                  Email : support@advaoptical.com

                  North American Support
                  Phone : 886 442 ADVA (2382) (toll-free within the US, Canada and Mexico)
                  Fax   : + 1 806 741 8529 (elsewhere)
                  Email : support-usa@advaoptical.com

                  Asia Pacific Support
                  Phone : + 1 866 442 2382 (other toll-free numbers available in some countries)
                  Email : support-asia@advaoptical.com"

    DESCRIPTION   "This is a MIB definition for ADVA AG Optical Networking entity management."

    REVISION      "201105220000Z"
    DESCRIPTION   "FSP3000 F7 Release 11.2 MIB."
    ::= { fspR7 8 }


ConnectionNotation ::= TEXTUAL-CONVENTION
  STATUS        current
  DESCRIPTION
         "Connection notation" 
  SYNTAX        INTEGER
                {
                  undefined(0),
                  fromToNotation(1),
                  toFromNotation(2)
                }

EntityClassName ::= TEXTUAL-CONVENTION
  STATUS        current
  DESCRIPTION
         "Entity Class Name" 
  SYNTAX        INTEGER
                {
                  undefined(0),
                  ne(1),
                  ptp(12),
                  ch(16),
                  vch(18),
                  otl(37),
                  conn(42),
                  crsCh(47),
                  wch(49),
                  ech(69),
                  vtp(70),
                  vconn(73)
                }

FspR7AdminState ::= TEXTUAL-CONVENTION
  STATUS        current
  DESCRIPTION
         "The Adminstrative State will be displayed in the GUI with full
         name values; it will be differently displayed in TL1 syntax according
         to TL1 display rules. The transaction into the UAS state requires
         a special destroy/delete function." 
  SYNTAX        INTEGER
                {
                  undefined(0),
                  uas(1),
                  is(2),
                  ains(3),
                  mgt(4),
                  mt(5),
                  dsbld(6),
                  pps(7)
                }

FspR7AdminStateCaps ::= TEXTUAL-CONVENTION
  STATUS        current
  DESCRIPTION
         "The Adminstrative State will be displayed in the GUI with full
         name values; it will be differently displayed in TL1 syntax according
         to TL1 display rules. The transaction into the UAS state requires
         a special destroy/delete function." 
  SYNTAX        BITS
                {
                  capUndefined(0),
                  capUas(1),
                  capIs(2),
                  capAins(3),
                  capMgt(4),
                  capMt(5),
                  capDsbld(6),
                  capPps(7)
                }

FspR7AlarmListType ::= TEXTUAL-CONVENTION
  STATUS        current
  DESCRIPTION
         "List of standing condition alarms supported by ADVA-FSPR7-MIB" 
  SYNTAX        INTEGER
                {
                  undefined(0),
                  terminalLoopback(5),
                  oosDisabled(6),
                  oosManagement(7),
                  oosMaintenance(8),
                  oosAins(9),
                  removed(10),
                  lossOfSignal(11),
                  optInputPwrReceivedTooLow(12),
                  optInputPwrReceivedTooHigh(13),
                  laserTemperatureTooHigh(14),
                  laserTemperatureTooLow(15),
                  optOutputPowerTransTooLow(16),
                  optOutputPowerTransTooHigh(17),
                  autoShutdownToHighTemp(18),
                  autoShutdownToHighTxPwr(19),
                  laserEndOfLife(20),
                  serverSignalFailureVf(21),
                  equalizationProgress(22),
                  uPortFailure(23),
                  autoShutdownBlock(24),
                  autoPowerShutdown(25),
                  confOutPowerTransTooHigh(26),
                  confOutPowerTransTooLow(27),
                  optSignalFailure(28),
                  dsbdChannelPowerTooHigh(29),
                  lossOfSignalCPort(30),
                  lossOfSignalNPort(31),
                  outputPowerFault(32),
                  eqlzAdjust(33),
                  ampFailure(34),
                  eqptProvMismatch(35),
                  backreflectionTooHigh(36),
                  fiberConnLos(48),
                  fiberConnOptFault(49),
                  fiberConnInvalid(50),
                  fiberConnMismatch(51),
                  fiberConnCommError(52),
                  fiberConnProtocolFailure(53),
                  fiberConnDataFailure(54),
                  fiberAttenuationHigh(55),
                  laserBiasCurrAbnormal(57),
                  fiberConnInvalidTx(58),
                  fiberConnMismatchTx(59),
                  fiberAttenuationHighTx(60),
                  laserFailure(61),
                  lossOfReceiverClockRecovery(62),
                  fiberAttenuationCond(63),
                  channelMismatch(64)
                }

FspR7ChannelBandwidth ::= TEXTUAL-CONVENTION
  STATUS        current
  DESCRIPTION
         "Channel Bandwidth" 
  SYNTAX        INTEGER
                {
                  undefined(0),
                  band50G(1),
                  band75G(2),
                  band100G(3),
                  band125G(4),
                  band150G(5),
                  band175G(6),
                  band200G(7),
                  band225G(8),
                  band250G(9),
                  band275G(10),
                  band300G(11)
                }

FspR7ChannelBandwidthCaps ::= TEXTUAL-CONVENTION
  STATUS        current
  DESCRIPTION
         "Channel Bandwidth" 
  SYNTAX        BITS
                {
                  capUndefined(0),
                  capBand50G(1),
                  capBand75G(2),
                  capBand100G(3),
                  capBand125G(4),
                  capBand150G(5),
                  capBand175G(6),
                  capBand200G(7),
                  capBand225G(8),
                  capBand250G(9),
                  capBand275G(10),
                  capBand300G(11)
                }

FspR7ChannelIdentifier ::= TEXTUAL-CONVENTION
  STATUS        current
  DESCRIPTION
         "Channel" 
  SYNTAX        INTEGER
                {
                  undefined(0),
                  d01(1),  --196,00THz 1529,55nm
                  d02(2),  --195,90THz 1530,33nm
                  d03(3),  --195,80THz 1531,12nm
                  d04(4),  --195,70THz 1531,90nm
                  d05(5),  --195,50THz 1533,47nm
                  d06(6),  --195,40THz 1534,25nm
                  d07(7),  --195,30THz 1535,04nm
                  d08(8),  --195,20THz 1535,82nm
                  d09(9),  --195,00THz 1537,40nm
                  d10(10),  --194,90THz 1538,19nm
                  d11(11),  --194,80THz 1538,98nm
                  d12(12),  --194,70THz 1539,77nm
                  d13(13),  --194,50THz 1541,35nm
                  d14(14),  --194,40THz 1542,14nm
                  d15(15),  --194,30THz 1542,94nm
                  d16(16),  --194,20THz 1543,73nm
                  d17(17),  --193,80THz 1546,92nm
                  d18(18),  --193,70THz 1547,72nm
                  d19(19),  --193,60THz 1548,51nm
                  d20(20),  --193,50THz 1549,32nm
                  d21(21),  --193,30THz 1550,92nm
                  d22(22),  --193,20THz 1551,72nm
                  d23(23),  --193,10THz 1552,52nm
                  d24(24),  --193,00THz 1553,33nm
                  d25(25),  --192,80THz 1554,94nm
                  d26(26),  --192,70THz 1555,75nm
                  d27(27),  --192,60THz 1556,55nm
                  d28(28),  --192,50THz 1557,36nm
                  d29(29),  --192,30THz 1558,98nm
                  d30(30),  --192,20THz 1559,79nm
                  d31(31),  --192,10THz 1560,61nm
                  d32(32),  --192,00THz 1561,42nm
                  d33(33),  --191,00THz 1569,59nm
                  d34(34),  --190,90THz 1570,42nm
                  d35(35),  --190,80THz 1571,24nm
                  d36(36),  --190,70THz 1572,06nm
                  d37(37),  --190,50THz 1573,71nm
                  d38(38),  --190,40THz 1574,54nm
                  d39(39),  --190,30THz 1575,37nm
                  d40(40),  --190,20THz 1576,20nm
                  d41(41),  --190,00THz 1577,86nm
                  d42(42),  --189,90THz 1578,69nm
                  d43(43),  --189,80THz 1579,52nm
                  d44(44),  --189,70THz 1580,35nm
                  d45(45),  --189,50THz 1582,02nm
                  d46(46),  --189,40THz 1582,85nm
                  d47(47),  --189,30THz 1583,69nm
                  d48(48),  --189,20THz 1584,53nm
                  d49(49),  --188,80THz 1587,88nm
                  d50(50),  --188,70THz 1588,73nm
                  d51(51),  --188,60THz 1589,57nm
                  d52(52),  --188,50THz 1590,41nm
                  d53(53),  --188,30THz 1592,10nm
                  d54(54),  --188,20THz 1592,95nm
                  d55(55),  --188,10THz 1593,79nm
                  d56(56),  --188,00THz 1594,64nm
                  d57(57),  --187,80THz 1596,34nm
                  d58(58),  --187,70THz 1597,19nm
                  d59(59),  --187,60THz 1598,04nm
                  d60(60),  --187,50THz 1598,89nm
                  d61(61),  --187,30THz 1600,60nm
                  d62(62),  --187,20THz 1601,56nm
                  d63(63),  --187,10THz 1602,31nm
                  d64(64),  --187,00THz 1603,17nm
                  dc1(65),  --195,60THz 1532,68nm
                  dc2(66),  --195,10THz 1536,61nm
                  dc3(67),  --194,60THz 1540,56nm
                  dc4(68),  --194,10THz 1544,53nm
                  dc5(69),  --193,90THz 1546,12nm
                  dc6(70),  --193,40THz 1550,12nm
                  dc7(71),  --192,90THz 1554,13nm
                  dc8(72),  --192,40THz 1558,17nm
                  dl1(73),  --190,60THz 1572,89nm
                  dl2(74),  --190,10THz 1577,03nm
                  dl3(75),  --189,60THz 1581,18nm
                  dl4(76),  --189,10THz 1585,36nm
                  dl5(77),  --188,90THz 1587,04nm
                  dl6(78),  --188,40THz 1591,26nm
                  dl7(79),  --187,90THz 1595,49nm
                  dl8(80),  --187,40THz 1599,75nm
                  dc9(81),  --194,00THz 1545,322nm
                  dl9(82),  --189,00THz 1586,203nm
                  c1470(91),  --1470,00nm
                  c1490(92),  --1490,00nm
                  c1510(93),  --1510,00nm
                  c1530(94),  --1530,00nm
                  c1550(95),  --1550,00nm
                  c1570(96),  --1570,00nm
                  c1590(97),  --1590,00nm
                  c1610(98),  --1610,00nm
                  s1310(99),  --1310,00nm OSC
                  s1630(100),  --1630,00nm OSC
                  g850(101),  --850,00nm
                  g1310(102),  --1310,00nm
                  g1550(103),  --1550,00nm
                  -- any(104),
                  notInGrid(105),
                  s1510(106),  --1510,00nm OSC
                  f19610(107),  --196,10THz  1528,7734nm
                  f19595(108),  --195,95THz  1529,9436nm
                  f19585(109),  --195,85THz  1530,7248nm
                  f19575(110),  --195,75THz  1531,5068nm
                  f19565(111),  --195,65THz  1532,2896nm
                  f19555(112),  --195,55THz  1533,0732nm
                  f19545(113),  --195,45THz  1533,8575nm
                  f19535(114),  --195,35THz  1534,6427nm
                  f19525(115),  --195,25THz  1535,4287nm
                  f19515(116),  --195,15THz  1536,2155nm
                  f19505(117),  --195,05THz  1537,0031nm
                  f19495(118),  --194,95THz  1537,7915nm
                  f19485(119),  --194,85THz  1538,5807nm
                  f19475(120),  --194,75THz  1539,3708nm
                  f19465(121),  --194,65THz  1540,1616nm
                  f19455(122),  --194,55THz  1540,9533nm
                  f19445(123),  --194,45THz  1541,7457nm
                  f19435(124),  --194,35THz  1542,5390nm
                  f19425(125),  --194,25THz  1543,3331nm
                  f19415(126),  --194,15THz  1544,1280nm
                  f19405(127),  --194,05THz  1544,9238nm
                  f19395(128),  --193,95THz  1545,7203nm
                  f19385(129),  --193,85THz  1546,5177nm
                  f19375(130),  --193,75THz  1547,3159nm
                  f19365(131),  --193,65THz  1548,1149nm
                  f19355(132),  --193,55THz  1548,9148nm
                  f19345(133),  --193,45THz  1549,7155nm
                  f19335(134),  --193,35THz  1550,5170nm
                  f19325(135),  --193,25THz  1551,3193nm
                  f19315(136),  --193,15THz  1552,1225nm
                  f19305(137),  --193,05THz  1552,9265nm
                  f19295(138),  --192,95THz  1553,7313nm
                  f19285(139),  --192,85THz  1554,5370nm
                  f19275(140),  --192,75THz  1555,3435nm
                  f19265(141),  --192,65THz  1556,1508nm
                  f19255(142),  --192,55THz  1556,9590nm
                  f19245(143),  --192,45THz  1557,7680nm
                  f19235(144),  --192,35THz  1558,5779nm
                  f19225(145),  --192,25THz  1559,3886nm
                  f19215(146),  --192,15THz  1560,2001nm
                  f19205(147),  --192,05THz  1561,0125nm
                  f19600(148),  --196,00THz 1529,55nm D01
                  f19590(149),  --195,90THz 1530,33nm D02
                  f19580(150),  --195,80THz 1531,12nm D03
                  f19570(151),  --195,70THz 1531,90nm D04
                  f19560(152),  --195,60THz 1532,68nm DC1
                  f19550(153),  --195,50THz 1533,47nm D05
                  f19540(154),  --195,40THz 1534,25nm D06
                  f19530(155),  --195,30THz 1535,04nm D07
                  f19520(156),  --195,20THz 1535,82nm D08
                  f19510(157),  --195,10THz 1536,60nm DC2
                  f19500(158),  --195,00THz 1537,40nm D09
                  f19490(159),  --194,90THz 1538,19nm D10
                  f19480(160),  --194,80THz 1538,98nm D11
                  f19470(161),  --194,70THz 1539,77nm D12
                  f19460(162),  --194,60THz 1540,55nm DC3
                  f19450(163),  --194,50THz 1541,35nm D13
                  f19440(164),  --194,40THz 1542,14nm D14
                  f19430(165),  --194,30THz 1542,94nm D15
                  f19420(166),  --194,20THz 1543,73nm D16
                  f19410(167),  --194,10THz 1544,52nm DC4
                  f19400(168),  --194,00THz 1545,32nm DC9
                  f19390(169),  --193,90THz 1546,11nm DC5
                  f19380(170),  --193,80THz 1546,92nm D17
                  f19370(171),  --193,70THz 1547,72nm D18
                  f19360(172),  --193,60THz 1548,51nm D19
                  f19350(173),  --193,50THz 1549,32nm D20
                  f19340(174),  --193,40THz 1550,11nm DC6
                  f19330(175),  --193,30THz 1550,92nm D21
                  f19320(176),  --193,20THz 1551,72nm D22
                  f19310(177),  --193,10THz 1552,52nm D23
                  f19300(178),  --193,00THz 1553,33nm D24
                  f19290(179),  --192,90THz 1554,13nm DC7
                  f19280(180),  --192,80THz 1554,94nm D25
                  f19270(181),  --192,70THz 1555,75nm D26
                  f19260(182),  --192,60THz 1556,55nm D27
                  f19250(183),  --192,50THz 1557,36nm D28
                  f19240(184),  --192,40THz 1558,17nm DC8
                  f19230(185),  --192,30THz 1558,98nm D29
                  f19220(186),  --192,20THz 1559,79nm D30
                  f19210(187),  --192,10THz 1560,61nm D31
                  f19200(188),  --192,00THz 1561,42nm D32
                  c1270(189),  --1270,00nm
                  c1290(190),  --1290,00nm
                  c1310(191),  --1310,00nm
                  c1330(192),  --1330,00nm
                  c1350(193),  --1350,00nm
                  c1370(194),  --1370,00nm
                  c1430(195),  --1430,00nm
                  c1450(196),  --1450,00nm
                  s1610(197),  --1610,00nm OSC
                  t1650(198),  --1650,00nm OTDR
                  s1490(199),  --1490,00nm OSC
                  f19598(200),  --195.9875THz , 1529.6509nm
                  f19597(201),  --195.975THz , 1529.7485nm
                  f19596(202),  --195.9625THz , 1529.8461nm
                  f19593(203),  --195.9375THz , 1530.0413nm
                  f19592(204),  --195.925THz , 1530.1389nm
                  f19591(205),  --195.9125THz , 1530.2365nm
                  f19588(206),  --195.8875THz , 1530.4318nm
                  f19587(207),  --195.875THz , 1530.5295nm
                  f19586(208),  --195.8625THz , 1530.6271nm
                  f19583(209),  --195.8375THz , 1530.8225nm
                  f19582(210),  --195.825THz , 1530.9203nm
                  f19581(211),  --195.8125THz , 1531.018nm
                  f19578(212),  --195.7875THz , 1531.2135nm
                  f19577(213),  --195.775THz , 1531.3112nm
                  f19576(214),  --195.7625THz , 1531.409nm
                  f19573(215),  --195.7375THz , 1531.6046nm
                  f19572(216),  --195.725THz , 1531.7024nm
                  f19571(217),  --195.7125THz , 1531.8003nm
                  f19568(218),  --195.6875THz , 1531.996nm
                  f19567(219),  --195.675THz , 1532.0938nm
                  f19566(220),  --195.6625THz , 1532.1917nm
                  f19563(221),  --195.6375THz , 1532.3875nm
                  f19562(222),  --195.625THz , 1532.4854nm
                  f19561(223),  --195.6125THz , 1532.5833nm
                  f19558(224),  --195.5875THz , 1532.7792nm
                  f19557(225),  --195.575THz , 1532.8772nm
                  f19556(226),  --195.5625THz , 1532.9752nm
                  f19553(227),  --195.5375THz , 1533.1712nm
                  f19552(228),  --195.525THz , 1533.2692nm
                  f19551(229),  --195.5125THz , 1533.3672nm
                  f19548(230),  --195.4875THz , 1533.5633nm
                  f19547(231),  --195.475THz , 1533.6614nm
                  f19546(232),  --195.4625THz , 1533.7595nm
                  f19543(233),  --195.4375THz , 1533.9557nm
                  f19542(234),  --195.425THz , 1534.0538nm
                  f19541(235),  --195.4125THz , 1534.1519nm
                  f19538(236),  --195.3875THz , 1534.3482nm
                  f19537(237),  --195.375THz , 1534.4464nm
                  f19536(238),  --195.3625THz , 1534.5445nm
                  f19533(239),  --195.3375THz , 1534.7409nm
                  f19532(240),  --195.325THz , 1534.8392nm
                  f19531(241),  --195.3125THz , 1534.9374nm
                  f19528(242),  --195.2875THz , 1535.1339nm
                  f19527(243),  --195.275THz , 1535.2321nm
                  f19526(244),  --195.2625THz , 1535.3304nm
                  f19523(245),  --195.2375THz , 1535.527nm
                  f19522(246),  --195.225THz , 1535.6253nm
                  f19521(247),  --195.2125THz , 1535.7237nm
                  f19518(248),  --195.1875THz , 1535.9204nm
                  f19517(249),  --195.175THz , 1536.0187nm
                  f19516(250),  --195.1625THz , 1536.1171nm
                  f19513(251),  --195.1375THz , 1536.3139nm
                  f19512(252),  --195.125THz , 1536.4123nm
                  f19511(253),  --195.1125THz , 1536.5108nm
                  f19508(254),  --195.0875THz , 1536.7077nm
                  f19507(255),  --195.075THz , 1536.8061nm
                  f19506(256),  --195.0625THz , 1536.9046nm
                  f19503(257),  --195.0375THz , 1537.1016nm
                  f19502(258),  --195.025THz , 1537.2001nm
                  f19501(259),  --195.0125THz , 1537.2987nm
                  f19498(260),  --194.9875THz , 1537.4958nm
                  f19497(261),  --194.975THz , 1537.5943nm
                  f19496(262),  --194.9625THz , 1537.6929nm
                  f19493(263),  --194.9375THz , 1537.8901nm
                  f19492(264),  --194.925THz , 1537.9888nm
                  f19491(265),  --194.9125THz , 1538.0874nm
                  f19488(266),  --194.8875THz , 1538.2847nm
                  f19487(267),  --194.875THz , 1538.3834nm
                  f19486(268),  --194.8625THz , 1538.482nm
                  f19483(269),  --194.8375THz , 1538.6795nm
                  f19482(270),  --194.825THz , 1538.7782nm
                  f19481(271),  --194.8125THz , 1538.8769nm
                  f19478(272),  --194.7875THz , 1539.0744nm
                  f19477(273),  --194.775THz , 1539.1732nm
                  f19476(274),  --194.7625THz , 1539.272nm
                  f19473(275),  --194.7375THz , 1539.4696nm
                  f19472(276),  --194.725THz , 1539.5684nm
                  f19471(277),  --194.7125THz , 1539.6672nm
                  f19468(278),  --194.6875THz , 1539.865nm
                  f19467(279),  --194.675THz , 1539.9638nm
                  f19466(280),  --194.6625THz , 1540.0627nm
                  f19463(281),  --194.6375THz , 1540.2605nm
                  f19462(282),  --194.625THz , 1540.3595nm
                  f19461(283),  --194.6125THz , 1540.4584nm
                  f19458(284),  --194.5875THz , 1540.6563nm
                  f19457(285),  --194.575THz , 1540.7553nm
                  f19456(286),  --194.5625THz , 1540.8543nm
                  f19453(287),  --194.5375THz , 1541.0523nm
                  f19452(288),  --194.525THz , 1541.1513nm
                  f19451(289),  --194.5125THz , 1541.2503nm
                  f19448(290),  --194.4875THz , 1541.4485nm
                  f19447(291),  --194.475THz , 1541.5475nm
                  f19446(292),  --194.4625THz , 1541.6466nm
                  f19443(293),  --194.4375THz , 1541.8448nm
                  f19442(294),  --194.425THz , 1541.944nm
                  f19441(295),  --194.4125THz , 1542.0431nm
                  f19438(296),  --194.3875THz , 1542.2414nm
                  f19437(297),  --194.375THz , 1542.3406nm
                  f19436(298),  --194.3625THz , 1542.4398nm
                  f19433(299),  --194.3375THz , 1542.6382nm
                  f19432(300),  --194.325THz , 1542.7375nm
                  f19431(301),  --194.3125THz , 1542.8367nm
                  f19428(302),  --194.2875THz , 1543.0352nm
                  f19427(303),  --194.275THz , 1543.1345nm
                  f19426(304),  --194.2625THz , 1543.2338nm
                  f19423(305),  --194.2375THz , 1543.4324nm
                  f19422(306),  --194.225THz , 1543.5318nm
                  f19421(307),  --194.2125THz , 1543.6311nm
                  f19418(308),  --194.1875THz , 1543.8298nm
                  f19417(309),  --194.175THz , 1543.9292nm
                  f19416(310),  --194.1625THz , 1544.0286nm
                  f19413(311),  --194.1375THz , 1544.2275nm
                  f19412(312),  --194.125THz , 1544.3269nm
                  f19411(313),  --194.1125THz , 1544.4263nm
                  f19408(314),  --194.0875THz , 1544.6253nm
                  f19407(315),  --194.075THz , 1544.7248nm
                  f19406(316),  --194.0625THz , 1544.8243nm
                  f19403(317),  --194.0375THz , 1545.0233nm
                  f19402(318),  --194.025THz , 1545.1228nm
                  f19401(319),  --194.0125THz , 1545.2224nm
                  f19398(320),  --193.9875THz , 1545.4215nm
                  f19397(321),  --193.975THz , 1545.5211nm
                  f19396(322),  --193.9625THz , 1545.6207nm
                  f19393(323),  --193.9375THz , 1545.82nm
                  f19392(324),  --193.925THz , 1545.9196nm
                  f19391(325),  --193.9125THz , 1546.0193nm
                  f19388(326),  --193.8875THz , 1546.2186nm
                  f19387(327),  --193.875THz , 1546.3183nm
                  f19386(328),  --193.8625THz , 1546.418nm
                  f19383(329),  --193.8375THz , 1546.6174nm
                  f19382(330),  --193.825THz , 1546.7172nm
                  f19381(331),  --193.8125THz , 1546.8169nm
                  f19378(332),  --193.7875THz , 1547.0165nm
                  f19377(333),  --193.775THz , 1547.1163nm
                  f19376(334),  --193.7625THz , 1547.2161nm
                  f19373(335),  --193.7375THz , 1547.4157nm
                  f19372(336),  --193.725THz , 1547.5156nm
                  f19371(337),  --193.7125THz , 1547.6155nm
                  f19368(338),  --193.6875THz , 1547.8152nm
                  f19367(339),  --193.675THz , 1547.9151nm
                  f19366(340),  --193.6625THz , 1548.015nm
                  f19363(341),  --193.6375THz , 1548.2149nm
                  f19362(342),  --193.625THz , 1548.3148nm
                  f19361(343),  --193.6125THz , 1548.4148nm
                  f19358(344),  --193.5875THz , 1548.6148nm
                  f19357(345),  --193.575THz , 1548.7148nm
                  f19356(346),  --193.5625THz , 1548.8148nm
                  f19353(347),  --193.5375THz , 1549.0148nm
                  f19352(348),  --193.525THz , 1549.1149nm
                  f19351(349),  --193.5125THz , 1549.2149nm
                  f19348(350),  --193.4875THz , 1549.4151nm
                  f19347(351),  --193.475THz , 1549.5152nm
                  f19346(352),  --193.4625THz , 1549.6153nm
                  f19343(353),  --193.4375THz , 1549.8156nm
                  f19342(354),  --193.425THz , 1549.9158nm
                  f19341(355),  --193.4125THz , 1550.0159nm
                  f19338(356),  --193.3875THz , 1550.2163nm
                  f19337(357),  --193.375THz , 1550.3165nm
                  f19336(358),  --193.3625THz , 1550.4167nm
                  f19333(359),  --193.3375THz , 1550.6172nm
                  f19332(360),  --193.325THz , 1550.7175nm
                  f19331(361),  --193.3125THz , 1550.8178nm
                  f19328(362),  --193.2875THz , 1551.0183nm
                  f19327(363),  --193.275THz , 1551.1187nm
                  f19326(364),  --193.2625THz , 1551.219nm
                  f19323(365),  --193.2375THz , 1551.4197nm
                  f19322(366),  --193.225THz , 1551.52nm
                  f19321(367),  --193.2125THz , 1551.6204nm
                  f19318(368),  --193.1875THz , 1551.8212nm
                  f19317(369),  --193.175THz , 1551.9216nm
                  f19316(370),  --193.1625THz , 1552.022nm
                  f19313(371),  --193.1375THz , 1552.2229nm
                  f19312(372),  --193.125THz , 1552.3234nm
                  f19311(373),  --193.1125THz , 1552.4239nm
                  f19296(382),  --192.9625THz , 1553.6307nm
                  f19293(383),  --192.9375THz , 1553.832nm
                  f19292(384),  --192.925THz , 1553.9327nm
                  f19291(385),  --192.9125THz , 1554.0333nm
                  f19288(386),  --192.8875THz , 1554.2348nm
                  f19287(387),  --192.875THz , 1554.3355nm
                  f19286(388),  --192.8625THz , 1554.4362nm
                  f19283(389),  --192.8375THz , 1554.6378nm
                  f19282(390),  --192.825THz , 1554.7385nm
                  f19278(392),  --192.7875THz , 1555.041nm
                  f19277(393),  --192.775THz , 1555.1418nm
                  f19276(394),  --192.7625THz , 1555.2426nm
                  f19273(395),  --192.7375THz , 1555.4444nm
                  f19272(396),  --192.725THz , 1555.5452nm
                  f19271(397),  --192.7125THz , 1555.6461nm
                  f19268(398),  --192.6875THz , 1555.848nm
                  f19267(399),  --192.675THz , 1555.9489nm
                  f19266(400),  --192.6625THz , 1556.0499nm
                  f19263(401),  --192.6375THz , 1556.2518nm
                  f19262(402),  --192.625THz , 1556.3528nm
                  f19261(403),  --192.6125THz , 1556.4538nm
                  f19258(404),  --192.5875THz , 1556.6558nm
                  f19257(405),  --192.575THz , 1556.7569nm
                  f19256(406),  --192.5625THz , 1556.8579nm
                  f19253(407),  --192.5375THz , 1557.0601nm
                  f19252(408),  --192.525THz , 1557.1612nm
                  f19251(409),  --192.5125THz , 1557.2623nm
                  f19248(410),  --192.4875THz , 1557.4646nm
                  f19247(411),  --192.475THz , 1557.5657nm
                  f19246(412),  --192.4625THz , 1557.6669nm
                  f19243(413),  --192.4375THz , 1557.8692nm
                  f19242(414),  --192.425THz , 1557.9704nm
                  f19241(415),  --192.4125THz , 1558.0716nm
                  f19238(416),  --192.3875THz , 1558.2741nm
                  f19237(417),  --192.375THz , 1558.3754nm
                  f19236(418),  --192.3625THz , 1558.4766nm
                  f19233(419),  --192.3375THz , 1558.6792nm
                  f19232(420),  --192.325THz , 1558.7805nm
                  f19231(421),  --192.3125THz , 1558.8818nm
                  f19228(422),  --192.2875THz , 1559.0845nm
                  f19227(423),  --192.275THz , 1559.1858nm
                  f19226(424),  --192.2625THz , 1559.2872nm
                  f19223(425),  --192.2375THz , 1559.49nm
                  f19222(426),  --192.225THz , 1559.5914nm
                  f19221(427),  --192.2125THz , 1559.6928nm
                  f19218(428),  --192.1875THz , 1559.8957nm
                  f19217(429),  --192.175THz , 1559.9972nm
                  f19216(430),  --192.1625THz , 1560.0987nm
                  f19213(431),  --192.1375THz , 1560.3016nm
                  f19212(432),  --192.125THz , 1560.4032nm
                  f19211(433),  --192.1125THz , 1560.5047nm
                  f19208(434),  --192.0875THz , 1560.7078nm
                  f19207(435),  --192.075THz , 1560.8094nm
                  f19206(436),  --192.0625THz , 1560.9109nm
                  f19203(437),  --192.0375THz , 1561.1141nm
                  f19202(438),  --192.025THz , 1561.2158nm
                  f19201(439),  --192.0125THz , 1561.3174nm
                  f19198(440),  --191.9875THz , 1561.5207nm
                  f19197(441),  --191.975THz , 1561.6224nm
                  f19196(442),  --191.9625THz , 1561.7241nm
                  f19195(443),  --191.95THz , 1561.8258nm
                  f19193(444),  --191.9375THz , 1561.9275nm
                  f19192(445),  --191.925THz , 1562.0292nm
                  f19191(446),  --191.9125THz , 1562.131nm
                  f19190(447),  --191.9THz , 1562.2327nm
                  f19188(448),  --191.8875THz , 1562.3345nm
                  f19187(449),  --191.875THz , 1562.4363nm
                  f19186(450),  --191.8625THz , 1562.5381nm
                  f19185(451),  --191.85THz , 1562.6399nm
                  f19183(452),  --191.8375THz , 1562.7417nm
                  f19182(453),  --191.825THz , 1562.8435nm
                  f19181(454),  --191.8125THz , 1562.9454nm
                  f19180(455),  --191.8THz , 1563.0472nm
                  f19178(456),  --191.7875THz , 1563.1491nm
                  f19177(457),  --191.775THz , 1563.251nm
                  f19176(458),  --191.7625THz , 1563.3529nm
                  f19175(459),  --191.75THz , 1563.4548nm
                  f19173(460),  --191.7375THz , 1563.5567nm
                  f19172(461),  --191.725THz , 1563.6587nm
                  f19171(462),  --191.7125THz , 1563.7606nm
                  f19170(463),  --191.7THz , 1563.8626nm
                  f19168(464),  --191.6875THz , 1563.9646nm
                  f19167(465),  --191.675THz , 1564.0666nm
                  f19166(466),  --191.6625THz , 1564.1686nm
                  f19165(467),  --191.65THz , 1564.2706nm
                  f19163(468),  --191.6375THz , 1564.3726nm
                  f19162(469),  --191.625THz , 1564.4747nm
                  f19161(470),  --191.6125THz , 1564.5767nm
                  f19160(471),  --191.6THz , 1564.6788nm
                  f19158(472),  --191.5875THz , 1564.7809nm
                  f19157(473),  --191.575THz , 1564.883nm
                  f19156(474),  --191.5625THz , 1564.9851nm
                  f19155(475),  --191.55THz , 1565.0872nm
                  f19153(476),  --191.5375THz , 1565.1894nm
                  f19152(477),  --191.525THz , 1565.2915nm
                  f19151(478),  --191.5125THz , 1565.3937nm
                  f19150(479),  --191.5THz , 1565.4959nm
                  f19148(480),  --191.4875THz , 1565.5981nm
                  f19147(481),  --191.475THz , 1565.7003nm
                  f19146(482),  --191.4625THz , 1565.8025nm
                  f19145(483),  --191.45THz , 1565.9047nm
                  f19143(484),  --191.4375THz , 1566.007nm
                  f19142(485),  --191.425THz , 1566.1092nm
                  f19141(486),  --191.4125THz , 1566.2115nm
                  f19140(487),  --191.4THz , 1566.3138nm
                  f19138(488),  --191.3875THz , 1566.4161nm
                  f19137(489),  --191.375THz , 1566.5184nm
                  f19136(490),  --191.3625THz , 1566.6207nm
                  f19135(491),  --191.35THz , 1566.7231nm
                  f19133(492),  --191.3375THz , 1566.8254nm
                  f19132(493),  --191.325THz , 1566.9278nm
                  f19131(494),  --191.3125THz , 1567.0302nm
                  f19130(495),  --191.3THz , 1567.1326nm
                  f19128(496),  --191.2875THz , 1567.235nm
                  f19127(497),  --191.275THz , 1567.3374nm
                  f19126(498),  --191.2625THz , 1567.4398nm
                  f19125(499),  --191.25THz , 1567.5423nm
                  notDefined(500)
                }

FspR7ChannelIdentifierCaps ::= TEXTUAL-CONVENTION
  STATUS        current
  DESCRIPTION
         "Channel" 
  SYNTAX        BITS
                {
                  capUndefined(0),
                  capD01(1),
                  capD02(2),
                  capD03(3),
                  capD04(4),
                  capD05(5),
                  capD06(6),
                  capD07(7),
                  capD08(8),
                  capD09(9),
                  capD10(10),
                  capD11(11),
                  capD12(12),
                  capD13(13),
                  capD14(14),
                  capD15(15),
                  capD16(16),
                  capD17(17),
                  capD18(18),
                  capD19(19),
                  capD20(20),
                  capD21(21),
                  capD22(22),
                  capD23(23),
                  capD24(24),
                  capD25(25),
                  capD26(26),
                  capD27(27),
                  capD28(28),
                  capD29(29),
                  capD30(30),
                  capD31(31),
                  capD32(32),
                  capD33(33),
                  capD34(34),
                  capD35(35),
                  capD36(36),
                  capD37(37),
                  capD38(38),
                  capD39(39),
                  capD40(40),
                  capD41(41),
                  capD42(42),
                  capD43(43),
                  capD44(44),
                  capD45(45),
                  capD46(46),
                  capD47(47),
                  capD48(48),
                  capD49(49),
                  capD50(50),
                  capD51(51),
                  capD52(52),
                  capD53(53),
                  capD54(54),
                  capD55(55),
                  capD56(56),
                  capD57(57),
                  capD58(58),
                  capD59(59),
                  capD60(60),
                  capD61(61),
                  capD62(62),
                  capD63(63),
                  capD64(64),
                  capDc1(65),
                  capDc2(66),
                  capDc3(67),
                  capDc4(68),
                  capDc5(69),
                  capDc6(70),
                  capDc7(71),
                  capDc8(72),
                  capDl1(73),
                  capDl2(74),
                  capDl3(75),
                  capDl4(76),
                  capDl5(77),
                  capDl6(78),
                  capDl7(79),
                  capDl8(80),
                  capDc9(81),
                  capDl9(82),
                  capC1470(91),
                  capC1490(92),
                  capC1510(93),
                  capC1530(94),
                  capC1550(95),
                  capC1570(96),
                  capC1590(97),
                  capC1610(98),
                  capS1310(99),
                  capS1630(100),
                  capG850(101),
                  capG1310(102),
                  capG1550(103),
                  -- capAny(104),
                  capNotInGrid(105),
                  capS1510(106),
                  capF19610(107),
                  capF19595(108),
                  capF19585(109),
                  capF19575(110),
                  capF19565(111),
                  capF19555(112),
                  capF19545(113),
                  capF19535(114),
                  capF19525(115),
                  capF19515(116),
                  capF19505(117),
                  capF19495(118),
                  capF19485(119),
                  capF19475(120),
                  capF19465(121),
                  capF19455(122),
                  capF19445(123),
                  capF19435(124),
                  capF19425(125),
                  capF19415(126),
                  capF19405(127),
                  capF19395(128),
                  capF19385(129),
                  capF19375(130),
                  capF19365(131),
                  capF19355(132),
                  capF19345(133),
                  capF19335(134),
                  capF19325(135),
                  capF19315(136),
                  capF19305(137),
                  capF19295(138),
                  capF19285(139),
                  capF19275(140),
                  capF19265(141),
                  capF19255(142),
                  capF19245(143),
                  capF19235(144),
                  capF19225(145),
                  capF19215(146),
                  capF19205(147),
                  capF19600(148),
                  capF19590(149),
                  capF19580(150),
                  capF19570(151),
                  capF19560(152),
                  capF19550(153),
                  capF19540(154),
                  capF19530(155),
                  capF19520(156),
                  capF19510(157),
                  capF19500(158),
                  capF19490(159),
                  capF19480(160),
                  capF19470(161),
                  capF19460(162),
                  capF19450(163),
                  capF19440(164),
                  capF19430(165),
                  capF19420(166),
                  capF19410(167),
                  capF19400(168),
                  capF19390(169),
                  capF19380(170),
                  capF19370(171),
                  capF19360(172),
                  capF19350(173),
                  capF19340(174),
                  capF19330(175),
                  capF19320(176),
                  capF19310(177),
                  capF19300(178),
                  capF19290(179),
                  capF19280(180),
                  capF19270(181),
                  capF19260(182),
                  capF19250(183),
                  capF19240(184),
                  capF19230(185),
                  capF19220(186),
                  capF19210(187),
                  capF19200(188),
                  capC1270(189),
                  capC1290(190),
                  capC1310(191),
                  capC1330(192),
                  capC1350(193),
                  capC1370(194),
                  capC1430(195),
                  capC1450(196),
                  capS1610(197),
                  capT1650(198),
                  capS1490(199),
                  capF19598(200),
                  capF19597(201),
                  capF19596(202),
                  capF19593(203),
                  capF19592(204),
                  capF19591(205),
                  capF19588(206),
                  capF19587(207),
                  capF19586(208),
                  capF19583(209),
                  capF19582(210),
                  capF19581(211),
                  capF19578(212),
                  capF19577(213),
                  capF19576(214),
                  capF19573(215),
                  capF19572(216),
                  capF19571(217),
                  capF19568(218),
                  capF19567(219),
                  capF19566(220),
                  capF19563(221),
                  capF19562(222),
                  capF19561(223),
                  capF19558(224),
                  capF19557(225),
                  capF19556(226),
                  capF19553(227),
                  capF19552(228),
                  capF19551(229),
                  capF19548(230),
                  capF19547(231),
                  capF19546(232),
                  capF19543(233),
                  capF19542(234),
                  capF19541(235),
                  capF19538(236),
                  capF19537(237),
                  capF19536(238),
                  capF19533(239),
                  capF19532(240),
                  capF19531(241),
                  capF19528(242),
                  capF19527(243),
                  capF19526(244),
                  capF19523(245),
                  capF19522(246),
                  capF19521(247),
                  capF19518(248),
                  capF19517(249),
                  capF19516(250),
                  capF19513(251),
                  capF19512(252),
                  capF19511(253),
                  capF19508(254),
                  capF19507(255),
                  capF19506(256),
                  capF19503(257),
                  capF19502(258),
                  capF19501(259),
                  capF19498(260),
                  capF19497(261),
                  capF19496(262),
                  capF19493(263),
                  capF19492(264),
                  capF19491(265),
                  capF19488(266),
                  capF19487(267),
                  capF19486(268),
                  capF19483(269),
                  capF19482(270),
                  capF19481(271),
                  capF19478(272),
                  capF19477(273),
                  capF19476(274),
                  capF19473(275),
                  capF19472(276),
                  capF19471(277),
                  capF19468(278),
                  capF19467(279),
                  capF19466(280),
                  capF19463(281),
                  capF19462(282),
                  capF19461(283),
                  capF19458(284),
                  capF19457(285),
                  capF19456(286),
                  capF19453(287),
                  capF19452(288),
                  capF19451(289),
                  capF19448(290),
                  capF19447(291),
                  capF19446(292),
                  capF19443(293),
                  capF19442(294),
                  capF19441(295),
                  capF19438(296),
                  capF19437(297),
                  capF19436(298),
                  capF19433(299),
                  capF19432(300),
                  capF19431(301),
                  capF19428(302),
                  capF19427(303),
                  capF19426(304),
                  capF19423(305),
                  capF19422(306),
                  capF19421(307),
                  capF19418(308),
                  capF19417(309),
                  capF19416(310),
                  capF19413(311),
                  capF19412(312),
                  capF19411(313),
                  capF19408(314),
                  capF19407(315),
                  capF19406(316),
                  capF19403(317),
                  capF19402(318),
                  capF19401(319),
                  capF19398(320),
                  capF19397(321),
                  capF19396(322),
                  capF19393(323),
                  capF19392(324),
                  capF19391(325),
                  capF19388(326),
                  capF19387(327),
                  capF19386(328),
                  capF19383(329),
                  capF19382(330),
                  capF19381(331),
                  capF19378(332),
                  capF19377(333),
                  capF19376(334),
                  capF19373(335),
                  capF19372(336),
                  capF19371(337),
                  capF19368(338),
                  capF19367(339),
                  capF19366(340),
                  capF19363(341),
                  capF19362(342),
                  capF19361(343),
                  capF19358(344),
                  capF19357(345),
                  capF19356(346),
                  capF19353(347),
                  capF19352(348),
                  capF19351(349),
                  capF19348(350),
                  capF19347(351),
                  capF19346(352),
                  capF19343(353),
                  capF19342(354),
                  capF19341(355),
                  capF19338(356),
                  capF19337(357),
                  capF19336(358),
                  capF19333(359),
                  capF19332(360),
                  capF19331(361),
                  capF19328(362),
                  capF19327(363),
                  capF19326(364),
                  capF19323(365),
                  capF19322(366),
                  capF19321(367),
                  capF19318(368),
                  capF19317(369),
                  capF19316(370),
                  capF19313(371),
                  capF19312(372),
                  capF19311(373),
                  capF19296(382),
                  capF19293(383),
                  capF19292(384),
                  capF19291(385),
                  capF19288(386),
                  capF19287(387),
                  capF19286(388),
                  capF19283(389),
                  capF19282(390),
                  capF19278(392),
                  capF19277(393),
                  capF19276(394),
                  capF19273(395),
                  capF19272(396),
                  capF19271(397),
                  capF19268(398),
                  capF19267(399),
                  capF19266(400),
                  capF19263(401),
                  capF19262(402),
                  capF19261(403),
                  capF19258(404),
                  capF19257(405),
                  capF19256(406),
                  capF19253(407),
                  capF19252(408),
                  capF19251(409),
                  capF19248(410),
                  capF19247(411),
                  capF19246(412),
                  capF19243(413),
                  capF19242(414),
                  capF19241(415),
                  capF19238(416),
                  capF19237(417),
                  capF19236(418),
                  capF19233(419),
                  capF19232(420),
                  capF19231(421),
                  capF19228(422),
                  capF19227(423),
                  capF19226(424),
                  capF19223(425),
                  capF19222(426),
                  capF19221(427),
                  capF19218(428),
                  capF19217(429),
                  capF19216(430),
                  capF19213(431),
                  capF19212(432),
                  capF19211(433),
                  capF19208(434),
                  capF19207(435),
                  capF19206(436),
                  capF19203(437),
                  capF19202(438),
                  capF19201(439),
                  capF19198(440),
                  capF19197(441),
                  capF19196(442),
                  capF19195(443),
                  capF19193(444),
                  capF19192(445),
                  capF19191(446),
                  capF19190(447),
                  capF19188(448),
                  capF19187(449),
                  capF19186(450),
                  capF19185(451),
                  capF19183(452),
                  capF19182(453),
                  capF19181(454),
                  capF19180(455),
                  capF19178(456),
                  capF19177(457),
                  capF19176(458),
                  capF19175(459),
                  capF19173(460),
                  capF19172(461),
                  capF19171(462),
                  capF19170(463),
                  capF19168(464),
                  capF19167(465),
                  capF19166(466),
                  capF19165(467),
                  capF19163(468),
                  capF19162(469),
                  capF19161(470),
                  capF19160(471),
                  capF19158(472),
                  capF19157(473),
                  capF19156(474),
                  capF19155(475),
                  capF19153(476),
                  capF19152(477),
                  capF19151(478),
                  capF19150(479),
                  capF19148(480),
                  capF19147(481),
                  capF19146(482),
                  capF19145(483),
                  capF19143(484),
                  capF19142(485),
                  capF19141(486),
                  capF19140(487),
                  capF19138(488),
                  capF19137(489),
                  capF19136(490),
                  capF19135(491),
                  capF19133(492),
                  capF19132(493),
                  capF19131(494),
                  capF19130(495),
                  capF19128(496),
                  capF19127(497),
                  capF19126(498),
                  capF19125(499),
                  capNotDefined(500)
                }

FspR7Conn ::= TEXTUAL-CONVENTION
  STATUS        current
  DESCRIPTION
         "Bidirectional | Unidirectional" 
  SYNTAX        INTEGER
                {
                  undefined(0),
                  bi(1),
                  uni(2)
                }

FspR7ConnCaps ::= TEXTUAL-CONVENTION
  STATUS        current
  DESCRIPTION
         "Bidirectional | Unidirectional" 
  SYNTAX        BITS
                {
                  capUndefined(0),
                  capBi(1),
                  capUni(2)
                }

FspR7ConnectorType ::= TEXTUAL-CONVENTION
  STATUS        current
  DESCRIPTION
         "Connector Type" 
  SYNTAX        INTEGER
                {
                  undefined(0),
                  lc(1),
                  rj45(2),
                  mupc(3),
                  dsub8(4),
                  usbS(5),
                  dsub44hd(6),
                  fcApc(7),
                  mpo(8),  --MPO is the industry acronym for "Multi-Fiber Push On". A MPO Connector type is a Multi-fiber Connector, which is used for high density fiber interconnections.
                  mbnc(9),  --Micro-BNC
                  hdBnc(10),  --HD-BNC
                  din(11)  --DIN 1.0/2.3
                }

FspR7ConnectState ::= TEXTUAL-CONVENTION
  STATUS        current
  DESCRIPTION
         "Connection State" 
  SYNTAX        INTEGER
                {
                  undefined(0),
                  idle(1),
                  idleReceive(2),
                  idleTransmit(3),
                  busy(4)
                }

FspR7EntitySecondaryStates ::= TEXTUAL-CONVENTION
  STATUS        current
  DESCRIPTION
         "Variable for representing the secondary states of an entity." 
  SYNTAX        BITS

                {
                  ueq(0),
                  meaState(1),
                  sgeo(2),
                  lpbkState(3),
                  lkdo(4),
                  frcdState(5),
                  faf(6),
                  flt(7),
                  act(8),
                  stbyh(9),
                  psi(10),
                  pri(11),
                  dgn(12),
                  busy(13),
                  idleState(14),
                  receiveIdleState(15),
                  transmitIdleState(16),
                  sgeoSrv(17),
                  farEndPlugOutage(18),
                  aseTableBuildState(19),
                  testState(20),
                  testFailed(21),
                  stby(22),
                  stbyInh(23),
                  noBackup(24)
                }

FspR7EntityType ::= TEXTUAL-CONVENTION
  STATUS        current
  DESCRIPTION
         "Parameter which consists of following parts:" 
  SYNTAX        INTEGER
                {
                  undefined(0),
                  eqpSh1hu(1),
                  eqpSh1huDc(2),
                  eqpSh3hu(3),
                  eqpSh7hu(4),
                  eqpF2kSh5hu(5),
                  eqpF2kSh6hu(6),
                  eqpDcm(7),
                  eqpSh9hu(8),
                  eqpUnknown(19),
                  eqpNcu(20),
                  eqpNcutif(21),
                  eqpScu(22),
                  eqpScue(23),
                  eqpR6cu(24),
                  eqpPsu1huac(25),
                  eqpPsu7huac(26),
                  eqpPsu7hudc(27),
                  eqpFcu7hu(28),
                  eqp2clsmd(29),
                  eqp2absmc(30),
                  eqp2bsmd(31),
                  eqp1Gsmud(32),
                  eqp4gsmd(33),
                  eqp8gsmd(34),
                  eqp1csmuc(35),
                  eqp1csmuewc(36),
                  eqp4csmd(37),
                  eqp4csmud(38),
                  eqp4csmc(39),
                  eqpOsfm(40),
                  eqp1pm(41),
                  eqp2pm(42),
                  eqp40csmd(43),
                  eqpDcf(44),
                  eqpEdfas(45),
                  eqpEdfasgc(46),
                  eqpEdfadgc(47),
                  eqpRaman(48),
                  eqp4tcc2g5(49),
                  eqp4tcc2g5d(50),
                  eqp4tcc10gd(51),
                  eqp4tcc10gc(52),
                  eqpWcc10gd(53),
                  eqpWcc10gc(54),
                  eqpWcc2g71N(55),
                  eqpWcc2g7d(56),
                  eqp2tcm2g5(57),
                  eqp2tca2g5(58),
                  eqp8tca10gd(59),
                  eqp8tca10gc(60),
                  eqpWca10gd(61),
                  eqpWca10gc(62),
                  eqp4tca4gd(63),
                  eqp4tca4gc(64),
                  eqpwca2g5(65),
                  eqp4tca1g3d(66),
                  eqp4tca1g3c(67),
                  eqp8tce2g5d(68),
                  eqp8tce2g5c(69),
                  eqpWcelsd(70),
                  eqpWcelsc(71),
                  eqpVsm(72),
                  eqpRsmolm(73),
                  eqpRsmsf(74),
                  eqpOscm(75),
                  eqp2oscm(76),
                  eqpDrm(77),
                  eqpXfpG(78),
                  eqpsfpd(79),
                  eqpSfpc(80),
                  eqpSfpg(81),
                  eqpSfpe(82),
                  eqpSh1hudcm(83),
                  eqpCustomc(84),
                  eqpCustomd(85),
                  eqpPsu1hudc(86),
                  eqpWcc2g7c(87),
                  eqp1csmuEwD(88),
                  eqp1csmuG(89),
                  eqp3BsmC(90),
                  eqp2Tca2g5s(91),
                  eqp8Csmuc(92),
                  eqpEdfaDgcb(93),
                  eqpOscmPn(94),
                  eqp4Tcc10gtd(95),
                  eqp4Tca4g(96),
                  eqpDcg(97),
                  eqp2Tcm2g5d(98),
                  eqp2Tcm2g5c(99),
                  eqpWcm2g5d(100),
                  eqpWcm2g5c(101),
                  eqpEdfmSgc(102),
                  eqpF2kDemiV2(103),
                  eqpPsm(104),
                  eqpNcu2e(105),
                  eqp8TceGl2g5d(106),
                  eqp8TceGl2g5c(107),
                  eqpDcf1hu(108),
                  eqp10tcc10gtd(109),
                  eqp10tcc10gd(110),
                  eqp10tcc10gc(111),
                  eqp16csmSfd(112),
                  eqpOsfmSf(113),
                  eqp2clsmSfd(114),
                  eqp3bsmEwc(115),
                  eqpEdfaSgcb(116),
                  eqpEdfaDgcv(117),
                  eqpWcc10gtd(118),
                  eqp2csmuEwc(119),
                  eqpEroadmDc(120),
                  eqpScuS(122),
                  eqp4opcm(123),
                  eqpUtm(124),
                  eqpPscu(125),
                  eqp40Csm2hu(126),
                  eqp2Twcc2g7(127),
                  eqp2Wca10g(130),
                  eqpNcuHp(131),
                  eqpNcu20085hu(132),
                  eqp20Pca10G(133),
                  eqpXfpC(137),
                  eqpXfpD(138),
                  eqpWcc40gtd(140),
                  eqpIlm(141),
                  eqpNcuII(142),
                  eqpCem9hu(143),
                  eqp8roadmC40(148),
                  eqp4Tcc40gtd(149),
                  eqp2pca10g(150),
                  eqp10pca10g(151),
                  eqp1csmuD(152),
                  eqpSfpOsC(153),
                  eqpSfpOdC(154),
                  eqpSfpOsG(155),
                  eqpSfpOdG(156),
                  eqpRoadmC80(157),
                  eqpccm8(158),
                  eqpPsu9hudc(159),
                  eqp4tca4gus(160),
                  eqp40Csm3huD(161),
                  eqp5psm(162),
                  eqpFan9hu(163),
                  eqp5tce10gtd(164),
                  eqp10tccs10gtd(165),
                  eqp40Csm3hudcD(166),
                  eqp40Csm3hudcDi(167),
                  eqp5gsmD(169),
                  eqp8csmD(170),
                  eqp2otfm(171),
                  eqp8otdr3hu(172),
                  eqpXfptD(173),
                  eqp40Csm3huDi(174),
                  eqp8CcmC80(175),
                  eqpEdfaD27(176),
                  eqp2Wcc10g(177),
                  eqp8RoadmC80(178),
                  eqp2Wcc10gAes(180),
                  eqp5tce10gtaesd(182),
                  eqpSh1hupf(183),
                  eqpFan1hu(185),
                  eqp10tcc10g(186),
                  eqpXfpOtnD(187),
                  eqpNcu2p(188),
                  eqpPsu9huac(190),
                  eqp2Raman(192),
                  eqpEdfaS26(193),
                  eqp5tces10gtd(194),
                  eqpScuII(195),
                  eqp11RoadmC96(196),
                  eqp8AdmC96(197),
                  eqp8CxmC96(198),
                  eqp8Shm(199),
                  eqpAmpShgcv(200),
                  eqpAmpSlgcv(201),
                  eqp2RamanC15(202),
                  eqpWcc100gtD(203),
                  eqpCfp4g(204),
                  eqpCfp10g(205),
                  eqpXfpTlnD(213),
                  eqp5tces10gtaesd(214),
                  eqp10tce100g(215),
                  eqp96Csm4HuD(216),
                  eqp4CfptD(217),
                  eqp2psm(218),
                  eqpWce100G(219),
                  eqp9RoadmC96(224),
                  eqp4Wce16g(225),
                  eqpSfpCdrG(227),
                  eqp10tce100gGf(228),
                  eqpPtp(499),
                  ifTypeOtu1(501),
                  ifTypeOtu2(502),
                  ifType10GbE(503),
                  ifTypeOc192(504),
                  ifTypeOc48(505),
                  ifTypeStm16(506),
                  ifTypeStm64(507),
                  ifType10GFC(508),
                  ifTypeF1062(510),
                  ifTypeF1250(511),
                  ifTypeFC(512),
                  ifTypeF125(513),
                  ifTypeF200(514),
                  ifTypeF9953(515),
                  ifTypeF10312(516),
                  ifTypeF10518(517),
                  ifTypeF2488(518),
                  ifTypeGfpF(519),
                  ifTypeGfpT(520),
                  ifTypeDccL(521),
                  ifTypeDccS(522),
                  ifTypeDccP(523),
                  ifTypeOdu1(524),
                  ifTypeGcc0(525),
                  ifTypeGcc1(526),
                  ifTypeGcc2(527),
                  ifTypeoch(528),
                  ifTypeOm(529),
                  ifTypeOt(534),
                  ifTypeE10or100bt(536),
                  ifTypeE100fx(537),
                  ifTypeCl(538),
                  ifType2GFC(539),
                  ifType2GCL(540),
                  ifType1GbE(541),
                  ifTypeEoc(542),
                  ifTypeSwitch(543),
                  ifTypePassive(544),
                  ifTypeF2500(545),
                  ifTypeSc(546),
                  ifTypeUch(547),
                  ifTypeF155(548),
                  ifTypeF622(549),
                  ifTypeF2125(550),
                  ifTypeF2666(551),
                  ifTypeF4250(552),
                  ifTypeF10709(554),
                  ifTypeF11095(555),
                  ifTypeF11318(556),
                  ifTypeLs(557),
                  ifType4Gfc(558),
                  ifTypeGcc0S(559),
                  ifType2R(560),
                  ifTypePppIp(561),
                  ifTypeLanIp(562),
                  ifTypeSerial(564),
                  ifTypeModem(565),
                  ifTypeAdapt(566),
                  ifTypeAdaptd(567),
                  ifTypeGBEFR(569),
                  ifTypeVc4(570),
                  ifTypeVc3(571),
                  ifTypeSts1(572),
                  ifTypeEdfa(573),
                  ifTypeEdfaMid(574),
                  ifType10Gdw(575),
                  ifTypeOtu2Lan(576),
                  ifTypeOtu1Lan(577),
                  ifTypeOtu1Fc(578),
                  ifTypeOtu1Fc2G(579),
                  ifTypeF197(580),
                  ifTypeTif(581),
                  ifTypeSts3c(582),
                  ifTypeVs1(583),
                  ifType1GbETH(584),
                  ifTypeStm1(585),
                  ifTypeStm4(586),
                  ifTypeOc3(587),
                  ifTypeOc12(588),
                  ifTypeOtu1Stm1(589),
                  ifTypeOtu1Stm4(590),
                  ifTypeF166(591),
                  ifTypeF666(592),
                  ifTypeI2C(593),
                  ifTypeLifIP(594),
                  ifTypeSts24c(595),
                  ifTypeSts48c(596),
                  ifTypeLifte(597),
                  ifTypeRaman(598),
                  ifTypeIpWhiteList(599),
                  ifTypeOspfIp(600),
                  ifTypeEncapIp(601),
                  ifTypeOtu3(602),
                  ifTypeStm256(603),
                  ifTypeOc768(604),
                  ifTypeF10664(605),
                  ifTypeOdu2(606),
                  ifTypeF39813(607),
                  ifTypeVc4c8(608),
                  ifTypeVc4c16(609),
                  ifTypeF8500(610),
                  ifTypePb(611),
                  ifTypePolicer(612),
                  ifTypeQueue(613),
                  ifTypeFlowPoint(614),
                  ifTypeLag(615),
                  ifTypeElinePPP(616),
                  ifTypeEtree(617),
                  ifTypeEline(618),
                  ifTypeElan(619),
                  ifTypeCtrans(620),
                  ifTypeVs0(621),
                  ifTypeTug(622),
                  ifTypeMd(623),
                  ifTypeMa(624),
                  ifTypeDownMep(625),
                  ifTypeFMep(626),
                  ifType8Gfc(627),
                  ifType10Gib(628),
                  ifTypeF10000(629),
                  ifTypeOtu2pFC8(630),
                  ifTypeOtu2pIB(631),
                  ifTypeOtu2pFC(632),
                  ifTypeOtu2pLAN(633),
                  ifTypeOtu2p(634),
                  ifTypeUpMep(635),
                  ifTypeOtdrCh(636),
                  ifTypeMaNet(637),
                  ifTypeMaComp(638),
                  ifTypeBridge(639),
                  ifType1000BaseT(640),
                  ifTypeOtu2E(641),
                  ifTypeOtu1E(642),
                  ifTypeOtu2F(643),
                  ifTypeF11049(644),
                  ifTypeLifteNum(645),
                  ifTypeLifteUnn(646),
                  ifTypeLifPbNum(647),
                  ifTypeLifSubUnn(648),
                  ifType5Gib(649),
                  ifTypeF5000(650),
                  ifTypeOtu2eEth(651),
                  ifTypeOdu0(652),
                  ifTypeFcu(653),
                  ifTypeOtu4(654),
                  ifType100GbE(660),
                  ifTypeOptical(661),
                  ifType10GbEWan(662),
                  ifType10GbELan(663),
                  ifTypeOduFlx(664),
                  ifTypeOtlc(665),
                  ifTypeOtu2ps(667),
                  ifTypeLifVTeNum(673),
                  ifTypeLifVTeUnn(674),
                  ifTypeF14025(678),
                  grpffpCh(1000),
                  grpffpOm(1001),
                  grpCrsDcn(1002),
                  grpLanDcn(1003),
                  grpConn(1004),
                  grpffpVchN(1005),
                  grpVirtualConn(1006),
                  conFanContainer(1101),
                  conModContainer(1102),
                  conPlugContainer(1103),
                  grpCrsCh(1104),
                  physTermPoint(1105),
                  virtualTermPoint(1106),
                  fanContainer(1107)
                }

FspR7EqlzAdminState ::= TEXTUAL-CONVENTION
  STATUS        current
  DESCRIPTION
         "Scheduled Equalization Administration" 
  SYNTAX        INTEGER
                {
                  undefined(0),
                  enabled(1),
                  disabled(2)
                }

FspR7EqlzAdminStateCaps ::= TEXTUAL-CONVENTION
  STATUS        current
  DESCRIPTION
         "Scheduled Equalization Administration" 
  SYNTAX        BITS
                {
                  capUndefined(0),
                  capEnabled(1),
                  capDisabled(2)
                }

FspR7FecType ::= TEXTUAL-CONVENTION
  STATUS        current
  DESCRIPTION
         "Forward Error Correction (Only relevant where TYPE = OTU#)" 
  SYNTAX        INTEGER
                {
                  undefined(0),
                  gFec(1),  --G709 Standard FEC
                  eFec(2),  --Enhanced FEC
                  noFec(3),  --No FEC
                  eFec1(4),  --Enhanced FEC (INTEL)
                  eFec2(5),  --Enhanced FEC (AMCC)
                  eFec3(6),  --Enhanced FEC (CORE)
                  eFec4(7),  --Enhanced FEC (Acacia)
                  eFecX(8)  --Variable Coding Gain
                }

FspR7FecTypeCaps ::= TEXTUAL-CONVENTION
  STATUS        current
  DESCRIPTION
         "Forward Error Correction (Only relevant where TYPE = OTU#)" 
  SYNTAX        BITS
                {
                  capUndefined(0),
                  capGFec(1),
                  capEFec(2),
                  capNoFec(3),
                  capEFec1(4),
                  capEFec2(5),
                  capEFec3(6),
                  capEFec4(7),
                  capEFecX(8)
                }

FspR7FiberDetect ::= TEXTUAL-CONVENTION
  STATUS        current
  DESCRIPTION
         "Fiber Detect" 
  SYNTAX        INTEGER
                {
                  undefined(0),
                  enabled(1),
                  disabled(2)
                }

FspR7FiberDetectCaps ::= TEXTUAL-CONVENTION
  STATUS        current
  DESCRIPTION
         "Fiber Detect" 
  SYNTAX        BITS
                {
                  capUndefined(0),
                  capEnabled(1),
                  capDisabled(2)
                }

FspR7FrameFormat ::= TEXTUAL-CONVENTION
  STATUS        current
  DESCRIPTION
         "Frame Format" 
  SYNTAX        INTEGER
                {
                  undefined(0),
                  otn(1),
                  sdh(2),
                  sonet(3),
                  ethernet(4),
                  fiberchannel(5),
                  infiniband(6),
                  couplinglink(7),
                  transparent(8),
                  notDefined(99)
                }

FspR7FrameFormatCaps ::= TEXTUAL-CONVENTION
  STATUS        current
  DESCRIPTION
         "Frame Format" 
  SYNTAX        BITS
                {
                  capUndefined(0),
                  capOtn(1),
                  capSdh(2),
                  capSonet(3),
                  capEthernet(4),
                  capFiberchannel(5),
                  capInfiniband(6),
                  capCouplinglink(7),
                  capTransparent(8),
                  capNotDefined(99)
                }

FspR7FunctionCrs ::= TEXTUAL-CONVENTION
  STATUS        current
  DESCRIPTION
         "Describes the Cross Connect Functionality" 
  SYNTAX        INTEGER
                {
                  undefined(0),
                  add(1),
                  drop(2),
                  pass(3),
                  hairpin(4),
                  select(5),
                  addDrop(6)
                }

FspR7FunctionCrsCaps ::= TEXTUAL-CONVENTION
  STATUS        current
  DESCRIPTION
         "Describes the Cross Connect Functionality" 
  SYNTAX        BITS
                {
                  capUndefined(0),
                  capAdd(1),
                  capDrop(2),
                  capPass(3),
                  capHairpin(4),
                  capSelect(5),
                  capAddDrop(6)
                }

FspR7InitEqualization ::= TEXTUAL-CONVENTION
  STATUS        current
  DESCRIPTION
         "Initiate Equalization" 
  SYNTAX        INTEGER
                {
                  undefined(0),
                  rls(1),
                  opr(2)
                }

FspR7InitEqualizationCaps ::= TEXTUAL-CONVENTION
  STATUS        current
  DESCRIPTION
         "Initiate Equalization" 
  SYNTAX        BITS
                {
                  capUndefined(0),
                  capRls(1),
                  capOpr(2)
                }

FspR7Integer32Caps ::= TEXTUAL-CONVENTION
  DISPLAY-HINT "4d:4d"
  STATUS        current
  DESCRIPTION
         "A FspR7Integer32Caps specification.
         1..4 bytes - minValue(Integer32),
         5..8 bytes - maxValue(Integer32)." 
  SYNTAX        OCTET STRING (SIZE(0..8))

FspR7InterfaceFunction ::= TEXTUAL-CONVENTION
  STATUS        current
  DESCRIPTION
         "Interface Function" 
  SYNTAX        INTEGER
                {
                  undefined(0),
                  transport(1),
                  switch(2),
                  edfa(3),
                  super(4),
                  passive(5),
                  active(6),
                  raman(7),
                  physicalTerm(8)
                }

FspR7InterfaceType ::= TEXTUAL-CONVENTION
  STATUS        current
  DESCRIPTION
         "The TYPE defines the transport service type as wrapper with wrapper layer termination OR else as payload" 
  SYNTAX        INTEGER
                {
                  undefined(0),
                  ifTypeOtu1(1),
                  ifTypeOtu2(2),
                  ifType10GbE(3),
                  ifTypeOc192(4),
                  ifTypeOc48(5),
                  ifTypeStm16(6),
                  ifTypeStm64(7),
                  ifType10GFC(8),
                  ifTypeF1062(10),
                  ifTypeF1250(11),
                  ifTypeFC(12),
                  ifTypeF125(13),
                  ifTypeF200(14),
                  ifTypeF9953(15),
                  ifTypeF10312(16),
                  ifTypeF10518(17),
                  ifTypeF2488(18),
                  ifTypeGfpF(19),
                  ifTypeGfpT(20),
                  ifTypeDccL(21),
                  ifTypeDccS(22),
                  ifTypeDccP(23),
                  ifTypeOdu1(24),
                  ifTypeGcc0(25),
                  ifTypeGcc1(26),
                  ifTypeGcc2(27),
                  ifTypeoch(28),
                  ifTypeOm(29),
                  ifTypeOt(34),
                  ifTypeE10or100bt(36),
                  ifTypeE100fx(37),
                  ifTypeCl(38),
                  ifType2GFC(39),
                  ifType2GCL(40),
                  ifType1GbE(41),
                  ifTypeEoc(42),
                  ifTypeSwitch(43),
                  ifTypePassive(44),
                  ifTypeF2500(45),
                  ifTypeSc(46),
                  ifTypeUch(47),
                  ifTypeF155(48),
                  ifTypeF622(49),
                  ifTypeF2125(50),
                  ifTypeF2666(51),
                  ifTypeF4250(52),
                  ifTypeF10709(54),
                  ifTypeF11095(55),
                  ifTypeF11318(56),
                  ifTypeLs(57),
                  ifType4Gfc(58),
                  ifTypeGcc0S(59),
                  ifType2R(60),
                  ifTypePppIp(61),
                  ifTypeLanIp(62),
                  ifTypeSerial(64),
                  ifTypeModem(65),
                  ifTypeAdapt(66),  --Any rate (inside of the limits) is allowed
                  ifTypeAdaptd(67),  --Different, but known fixed rates are allowed
                  ifTypeGBEFR(69),
                  ifTypeVc4(70),
                  ifTypeVc3(71),
                  ifTypeSts1(72),
                  ifTypeEdfa(73),
                  ifTypeEdfaMid(74),
                  ifType10Gdw(75),
                  ifTypeOtu2Lan(76),
                  ifTypeOtu1Lan(77),
                  ifTypeOtu1Fc(78),
                  ifTypeOtu1Fc2G(79),
                  ifTypeF197(80),
                  ifTypeTif(81),  --Telemetrie Interface
                  ifTypeSts3c(82),
                  ifTypeVs1(83),
                  ifType1GbETH(84),
                  ifTypeStm1(85),
                  ifTypeStm4(86),
                  ifTypeOc3(87),
                  ifTypeOc12(88),
                  ifTypeOtu1Stm1(89),
                  ifTypeOtu1Stm4(90),
                  ifTypeF166(91),
                  ifTypeF666(92),
                  ifTypeI2C(93),
                  ifTypeLifIP(94),
                  ifTypeSts24c(95),
                  ifTypeSts48c(96),
                  ifTypeLifte(97),
                  ifTypeRaman(98),
                  ifTypeIpWhiteList(99),
                  ifTypeOspfIp(100),
                  ifTypeEncapIp(101),
                  ifTypeOtu3(102),
                  ifTypeStm256(103),
                  ifTypeOc768(104),
                  ifTypeF10664(105),
                  ifTypeOdu2(106),
                  ifTypeF39813(107),
                  ifTypeVc4c8(108),
                  ifTypeVc4c16(109),
                  ifTypeF8500(110),
                  ifTypePb(111),
                  ifTypePolicer(112),
                  ifTypeQueue(113),
                  ifTypeFlowPoint(114),
                  ifTypeLag(115),
                  ifTypeElinePPP(116),
                  ifTypeEtree(117),
                  ifTypeEline(118),
                  ifTypeElan(119),
                  ifTypeCtrans(120),
                  ifTypeVs0(121),
                  ifTypeTug(122),
                  ifTypeMd(123),
                  ifTypeMa(124),
                  ifTypeDownMep(125),
                  ifTypeFMep(126),
                  ifType8Gfc(127),
                  ifType10Gib(128),
                  ifTypeF10000(129),
                  ifTypeOtu2pFC8(130),  --OTU2 proprietary with 8G Fiber Channel payload
                  ifTypeOtu2pIB(131),  --OTU2 proprietary with 10G Infiniband payload
                  ifTypeOtu2pFC(132),  --OTU2 proprietary with 10G Fiber Channel payload
                  ifTypeOtu2pLAN(133),  --OTU2 proprietary with 10GbE payload
                  ifTypeOtu2p(134),  --OTU2 proprietary with multiplexed signal payload
                  ifTypeUpMep(135),
                  ifTypeOtdrCh(136),
                  ifTypeMaNet(137),
                  ifTypeMaComp(138),
                  ifTypeBridge(139),
                  ifType1000BaseT(140),
                  ifTypeOtu2E(141),  --OTU2 overclocked with 10GBE payload
                  ifTypeOtu1E(142),  --OTU1 overclocked with 10GBE payload
                  ifTypeOtu2F(143),  --OTU2 with 10GFC payload
                  ifTypeF11049(144),
                  ifTypeLifteNum(145),
                  ifTypeLifteUnn(146),
                  ifTypeLifPbNum(147),
                  ifTypeLifSubUnn(148),
                  ifType5Gib(149),
                  ifTypeF5000(150),
                  ifTypeOtu2eEth(151),
                  ifTypeOdu0(152),
                  ifTypeFcu(153),
                  ifTypeOtu4(154),
                  ifType100GbE(160),
                  ifTypeOptical(161),
                  ifType10GbEWan(162),  --9.9533 Gb/s
                  ifType10GbELan(163),  --10.3125 Gb/s
                  ifTypeOduFlx(164),
                  ifTypeOtlc(165),  --Optical taransport lane carrier (G.709)
                  ifTypeOtu2ps(167),  --OTU2 proprietary with fixed 9.953G signal payload
                  ifTypeLifVTeNum(173),
                  ifTypeLifVTeUnn(174),
                  ifTypeF14025(178)
                }

FspR7InterfaceTypeCaps ::= TEXTUAL-CONVENTION
  STATUS        current
  DESCRIPTION
         "The TYPE defines the transport service type as wrapper with wrapper layer termination OR else as payload" 
  SYNTAX        BITS
                {
                  capUndefined(0),
                  capIfTypeOtu1(1),
                  capIfTypeOtu2(2),
                  capIfType10GbE(3),
                  capIfTypeOc192(4),
                  capIfTypeOc48(5),
                  capIfTypeStm16(6),
                  capIfTypeStm64(7),
                  capIfType10GFC(8),
                  capIfTypeF1062(10),
                  capIfTypeF1250(11),
                  capIfTypeFC(12),
                  capIfTypeF125(13),
                  capIfTypeF200(14),
                  capIfTypeF9953(15),
                  capIfTypeF10312(16),
                  capIfTypeF10518(17),
                  capIfTypeF2488(18),
                  capIfTypeGfpF(19),
                  capIfTypeGfpT(20),
                  capIfTypeDccL(21),
                  capIfTypeDccS(22),
                  capIfTypeDccP(23),
                  capIfTypeOdu1(24),
                  capIfTypeGcc0(25),
                  capIfTypeGcc1(26),
                  capIfTypeGcc2(27),
                  capIfTypeoch(28),
                  capIfTypeOm(29),
                  capIfTypeOt(34),
                  capIfTypeE10or100bt(36),
                  capIfTypeE100fx(37),
                  capIfTypeCl(38),
                  capIfType2GFC(39),
                  capIfType2GCL(40),
                  capIfType1GbE(41),
                  capIfTypeEoc(42),
                  capIfTypeSwitch(43),
                  capIfTypePassive(44),
                  capIfTypeF2500(45),
                  capIfTypeSc(46),
                  capIfTypeUch(47),
                  capIfTypeF155(48),
                  capIfTypeF622(49),
                  capIfTypeF2125(50),
                  capIfTypeF2666(51),
                  capIfTypeF4250(52),
                  capIfTypeF10709(54),
                  capIfTypeF11095(55),
                  capIfTypeF11318(56),
                  capIfTypeLs(57),
                  capIfType4Gfc(58),
                  capIfTypeGcc0S(59),
                  capIfType2R(60),
                  capIfTypePppIp(61),
                  capIfTypeLanIp(62),
                  capIfTypeSerial(64),
                  capIfTypeModem(65),
                  capIfTypeAdapt(66),
                  capIfTypeAdaptd(67),
                  capIfTypeGBEFR(69),
                  capIfTypeVc4(70),
                  capIfTypeVc3(71),
                  capIfTypeSts1(72),
                  capIfTypeEdfa(73),
                  capIfTypeEdfaMid(74),
                  capIfType10Gdw(75),
                  capIfTypeOtu2Lan(76),
                  capIfTypeOtu1Lan(77),
                  capIfTypeOtu1Fc(78),
                  capIfTypeOtu1Fc2G(79),
                  capIfTypeF197(80),
                  capIfTypeTif(81),
                  capIfTypeSts3c(82),
                  capIfTypeVs1(83),
                  capIfType1GbETH(84),
                  capIfTypeStm1(85),
                  capIfTypeStm4(86),
                  capIfTypeOc3(87),
                  capIfTypeOc12(88),
                  capIfTypeOtu1Stm1(89),
                  capIfTypeOtu1Stm4(90),
                  capIfTypeF166(91),
                  capIfTypeF666(92),
                  capIfTypeI2C(93),
                  capIfTypeLifIP(94),
                  capIfTypeSts24c(95),
                  capIfTypeSts48c(96),
                  capIfTypeLifte(97),
                  capIfTypeRaman(98),
                  capIfTypeIpWhiteList(99),
                  capIfTypeOspfIp(100),
                  capIfTypeEncapIp(101),
                  capIfTypeOtu3(102),
                  capIfTypeStm256(103),
                  capIfTypeOc768(104),
                  capIfTypeF10664(105),
                  capIfTypeOdu2(106),
                  capIfTypeF39813(107),
                  capIfTypeVc4c8(108),
                  capIfTypeVc4c16(109),
                  capIfTypeF8500(110),
                  capIfTypePb(111),
                  capIfTypePolicer(112),
                  capIfTypeQueue(113),
                  capIfTypeFlowPoint(114),
                  capIfTypeLag(115),
                  capIfTypeElinePPP(116),
                  capIfTypeEtree(117),
                  capIfTypeEline(118),
                  capIfTypeElan(119),
                  capIfTypeCtrans(120),
                  capIfTypeVs0(121),
                  capIfTypeTug(122),
                  capIfTypeMd(123),
                  capIfTypeMa(124),
                  capIfTypeDownMep(125),
                  capIfTypeFMep(126),
                  capIfType8Gfc(127),
                  capIfType10Gib(128),
                  capIfTypeF10000(129),
                  capIfTypeOtu2pFC8(130),
                  capIfTypeOtu2pIB(131),
                  capIfTypeOtu2pFC(132),
                  capIfTypeOtu2pLAN(133),
                  capIfTypeOtu2p(134),
                  capIfTypeUpMep(135),
                  capIfTypeOtdrCh(136),
                  capIfTypeMaNet(137),
                  capIfTypeMaComp(138),
                  capIfTypeBridge(139),
                  capIfType1000BaseT(140),
                  capIfTypeOtu2E(141),
                  capIfTypeOtu1E(142),
                  capIfTypeOtu2F(143),
                  capIfTypeF11049(144),
                  capIfTypeLifteNum(145),
                  capIfTypeLifteUnn(146),
                  capIfTypeLifPbNum(147),
                  capIfTypeLifSubUnn(148),
                  capIfType5Gib(149),
                  capIfTypeF5000(150),
                  capIfTypeOtu2eEth(151),
                  capIfTypeOdu0(152),
                  capIfTypeFcu(153),
                  capIfTypeOtu4(154),
                  capIfType100GbE(160),
                  capIfTypeOptical(161),
                  capIfType10GbEWan(162),
                  capIfType10GbELan(163),
                  capIfTypeOduFlx(164),
                  capIfTypeOtlc(165),
                  capIfTypeOtu2ps(167),
                  capIfTypeLifVTeNum(173),
                  capIfTypeLifVTeUnn(174),
                  capIfTypeF14025(178)
                }

FspR7LineCoding ::= TEXTUAL-CONVENTION
  STATUS        current
  DESCRIPTION
         "Line Coding" 
  SYNTAX        INTEGER
                {
                  undefined(0),
                  ookNrz(1),
                  dpsk(2),
                  qpsk(3),
                  dpQpsk(4),
                  odbPsbt(5),
                  mQam(6),
                  ofdm(7),
                  notDefined(99)
                }

FspR7LineCodingCaps ::= TEXTUAL-CONVENTION
  STATUS        current
  DESCRIPTION
         "Line Coding" 
  SYNTAX        BITS
                {
                  capUndefined(0),
                  capOokNrz(1),
                  capDpsk(2),
                  capQpsk(3),
                  capDpQpsk(4),
                  capOdbPsbt(5),
                  capMQam(6),
                  capOfdm(7),
                  capNotDefined(99)
                }

FspR7MaxBitErrorRate ::= TEXTUAL-CONVENTION
  STATUS        current
  DESCRIPTION
         "Maximum Bit Error Rate" 
  SYNTAX        INTEGER
                {
                  undefined(0),
                  ber1e2(1),
                  ber1e3(2),
                  ber1e4(3),
                  ber1e5(4),
                  ber1e6(5),
                  ber1e7(6),
                  ber1e8(7),
                  ber1e9(8),
                  ber1e10(9),
                  ber1e11(10),
                  ber1e12(11),
                  ber1e13(12),
                  ber1e14(13),
                  ber1e15(14)
                }

FspR7MaxBitErrorRateCaps ::= TEXTUAL-CONVENTION
  STATUS        current
  DESCRIPTION
         "Maximum Bit Error Rate" 
  SYNTAX        BITS
                {
                  capUndefined(0),
                  capBer1e2(1),
                  capBer1e3(2),
                  capBer1e4(3),
                  capBer1e5(4),
                  capBer1e6(5),
                  capBer1e7(6),
                  capBer1e8(7),
                  capBer1e9(8),
                  capBer1e10(9),
                  capBer1e11(10),
                  capBer1e12(11),
                  capBer1e13(12),
                  capBer1e14(13),
                  capBer1e15(14)
                }

FspR7NumberOfChannels ::= TEXTUAL-CONVENTION
  STATUS        current
  DESCRIPTION
         "Number of channels supported by an entity" 
  SYNTAX        INTEGER
                {
                  undefined(0),
                  channels20(1),
                  channels40(2),
                  channels80(3),
                  channels96(4)
                }

FspR7OperState ::= TEXTUAL-CONVENTION
  STATUS        current
  DESCRIPTION
         "The Operational State will be displayed on the
         GUI with full name values; it will be differently
         displayed in TL1 syntax according to TL1 display rules." 
  SYNTAX        INTEGER
                {
                  undefined(0),
                  nr(1),
                  anr(2),
                  out(3),
                  un(4)
                }

FspR7OpticalBand ::= TEXTUAL-CONVENTION
  STATUS        current
  DESCRIPTION
         "OM Band - Inventory. BAND__PROVISION references to this." 
  SYNTAX        INTEGER
                {
                  undefined(0),
                  bandC(1),
                  bandL(2),
                  bandA(3),
                  bandB(4),
                  -- bandAny(5),
                  bandCi(5),
                  bandCandCi(6)
                }

FspR7OpticalFiberType ::= TEXTUAL-CONVENTION
  STATUS        current
  DESCRIPTION
         "Fiber of Optical Interface - Inventory. FIBER references to this." 
  SYNTAX        INTEGER
                {
                  undefined(0),
                  singleMode(1),
                  multiMode(2),
                  any(3)
                }

FspR7OpticalGroup ::= TEXTUAL-CONVENTION
  STATUS        current
  DESCRIPTION
         "Channel Group read from the hardware" 
  SYNTAX        INTEGER
                {
                  undefined(0),
                  d01d04(1),
                  d05d08(2),
                  d09d12(3),
                  d13d16(4),
                  d17d20(5),
                  d21d24(6),
                  d25d28(7),
                  d29d32(8),
                  d33d36(9),
                  d37d40(10),
                  d41d44(11),
                  d45d48(12),
                  d49d52(13),
                  d53d56(14),
                  d57d60(15),
                  d61d64(16),
                  -- any(17),
                  f19590f19560(17),
                  f19550f19520(18),
                  f19510f19480(19),
                  f19470f19440(20),
                  f19430f19400(21),
                  f19390f19360(22),
                  f19350f19320(23),
                  f19310f19280(24),
                  f19270f19240(25),
                  f19230f19200(26),
                  f19590f19520(27),  --D02-D04, DC1, D05-D08
                  f19510f19440(28),  --DC2, D09-D12, DC3, D13-D14
                  f19430f19360(29),  --D15-D16, DC4, DC9, D17-D19
                  f19350f19280(30),  --D2, DC6, D21-D24, DC7, D25
                  f19270f19200(31)  --D26-D28, DC8, D29-D32
                }

FspR7OpticalInterfaceReach ::= TEXTUAL-CONVENTION
  STATUS        current
  DESCRIPTION
         "Reach" 
  SYNTAX        INTEGER
                {
                  undefined(0),
                  intra(1),  --0 - <5 km
                  short(2),  --5 - <30 km
                  long(4),  --30 - <70 km
                  vlong(5),  --70 - <110 km
                  ulong(6),  --110 - <165 km
                  reg(7),  --290 - <360 km
                  xlong(8),  --360 - <600 km
                  -- any(9),
                  longn(10),  --30 - <70 km
                  extended(11),  --165 - <220 km
                  hyperlong(12),  --220 - <290 km
                  longNR(13),  --30 - <70 km
                  ulongHaul(14)  --500 - <2500 km 
                }

FspR7OpticalMultiplexLevel ::= TEXTUAL-CONVENTION
  STATUS        current
  DESCRIPTION
         "Optical Multiplex Level" 
  SYNTAX        INTEGER
                {
                  undefined(0),
                  levelOm1D(1),
                  levelOm1C(2),
                  levelOm4D(3),
                  levelOm4C(4),
                  levelOm16D(5),
                  levelOm32D(6),
                  levelOm40D(7),
                  levelOmC(9),
                  levelOmD(10),
                  levelOtD(11),
                  levelOtC(12),
                  levelOt(13)
                }

FspR7OpticalSubBand ::= TEXTUAL-CONVENTION
  STATUS        current
  DESCRIPTION
         "Subband - Inventory" 
  SYNTAX        INTEGER
                {
                  undefined(0),
                  d01d16(1),
                  d17d32(2),
                  d33d48(3),
                  d49d64(4)
                  -- subBandAny(5)
                }

FspR7PathNode ::= TEXTUAL-CONVENTION
  STATUS        current
  DESCRIPTION
         "Node count along a signal path on a unidirectional basis from the client signal ingress to egress" 
  SYNTAX        INTEGER
                {
                  undefined(0),
                  node1(1),
                  node2(2),
                  node3(3),
                  node4(4),
                  node5(5),
                  node6(6),
                  node7(7),
                  node8(8),
                  node9(9),
                  node10(10),
                  node11(11),
                  node12(12),
                  node13(13),
                  node14(14),
                  node15(15),
                  node16(16),
                  node17(17),
                  node18(18),
                  node19(19),
                  node20(20),
                  node21(21),
                  node22(22),
                  node23(23),
                  node24(24),
                  node25(25),
                  node26(26),
                  node27(27),
                  node28(28),
                  node29(29),
                  node30(30),
                  node31(31),
                  node32(32),
                  node33(33),
                  node34(34),
                  node35(35),
                  node36(36),
                  node37(37),
                  node38(38),
                  node39(39),
                  node40(40),
                  node41(41),
                  node42(42),
                  node43(43),
                  node44(44),
                  node45(45),
                  node46(46),
                  node47(47),
                  node48(48),
                  node49(49),
                  node50(50),
                  node51(51),
                  node52(52),
                  node53(53),
                  node54(54),
                  node55(55),
                  node56(56),
                  node57(57),
                  node58(58),
                  node59(59),
                  node60(60),
                  node61(61),
                  node62(62),
                  node63(63),
                  node64(64),
                  node65(65),
                  node66(66),
                  node67(67),
                  node68(68),
                  node69(69),
                  node70(70),
                  node71(71),
                  node72(72),
                  node73(73),
                  node74(74),
                  node75(75),
                  node76(76),
                  node77(77),
                  node78(78),
                  node79(79),
                  node80(80),
                  node81(81),
                  node82(82),
                  node83(83),
                  node84(84),
                  node85(85),
                  node86(86),
                  node87(87),
                  node88(88),
                  node89(89),
                  node90(90),
                  node91(91),
                  node92(92),
                  node93(93),
                  node94(94),
                  node95(95),
                  node96(96),
                  node97(97),
                  node98(98),
                  node99(99),
                  node100(100),
                  node101(101),
                  node102(102),
                  node103(103),
                  node104(104),
                  node105(105),
                  node106(106),
                  node107(107),
                  node108(108),
                  node109(109),
                  node110(110),
                  node111(111),
                  node112(112),
                  node113(113),
                  node114(114),
                  node115(115),
                  node116(116),
                  node117(117),
                  node118(118)
                }

FspR7PathNodeCaps ::= TEXTUAL-CONVENTION
  STATUS        current
  DESCRIPTION
         "Node count along a signal path on a unidirectional basis from the client signal ingress to egress" 
  SYNTAX        BITS
                {
                  capUndefined(0),
                  capNode1(1),
                  capNode2(2),
                  capNode3(3),
                  capNode4(4),
                  capNode5(5),
                  capNode6(6),
                  capNode7(7),
                  capNode8(8),
                  capNode9(9),
                  capNode10(10),
                  capNode11(11),
                  capNode12(12),
                  capNode13(13),
                  capNode14(14),
                  capNode15(15),
                  capNode16(16),
                  capNode17(17),
                  capNode18(18),
                  capNode19(19),
                  capNode20(20),
                  capNode21(21),
                  capNode22(22),
                  capNode23(23),
                  capNode24(24),
                  capNode25(25),
                  capNode26(26),
                  capNode27(27),
                  capNode28(28),
                  capNode29(29),
                  capNode30(30),
                  capNode31(31),
                  capNode32(32),
                  capNode33(33),
                  capNode34(34),
                  capNode35(35),
                  capNode36(36),
                  capNode37(37),
                  capNode38(38),
                  capNode39(39),
                  capNode40(40),
                  capNode41(41),
                  capNode42(42),
                  capNode43(43),
                  capNode44(44),
                  capNode45(45),
                  capNode46(46),
                  capNode47(47),
                  capNode48(48),
                  capNode49(49),
                  capNode50(50),
                  capNode51(51),
                  capNode52(52),
                  capNode53(53),
                  capNode54(54),
                  capNode55(55),
                  capNode56(56),
                  capNode57(57),
                  capNode58(58),
                  capNode59(59),
                  capNode60(60),
                  capNode61(61),
                  capNode62(62),
                  capNode63(63),
                  capNode64(64),
                  capNode65(65),
                  capNode66(66),
                  capNode67(67),
                  capNode68(68),
                  capNode69(69),
                  capNode70(70),
                  capNode71(71),
                  capNode72(72),
                  capNode73(73),
                  capNode74(74),
                  capNode75(75),
                  capNode76(76),
                  capNode77(77),
                  capNode78(78),
                  capNode79(79),
                  capNode80(80),
                  capNode81(81),
                  capNode82(82),
                  capNode83(83),
                  capNode84(84),
                  capNode85(85),
                  capNode86(86),
                  capNode87(87),
                  capNode88(88),
                  capNode89(89),
                  capNode90(90),
                  capNode91(91),
                  capNode92(92),
                  capNode93(93),
                  capNode94(94),
                  capNode95(95),
                  capNode96(96),
                  capNode97(97),
                  capNode98(98),
                  capNode99(99),
                  capNode100(100),
                  capNode101(101),
                  capNode102(102),
                  capNode103(103),
                  capNode104(104),
                  capNode105(105),
                  capNode106(106),
                  capNode107(107),
                  capNode108(108),
                  capNode109(109),
                  capNode110(110),
                  capNode111(111),
                  capNode112(112),
                  capNode113(113),
                  capNode114(114),
                  capNode115(115),
                  capNode116(116),
                  capNode117(117),
                  capNode118(118)
                }

FspR7PmSnapshotStatus ::= TEXTUAL-CONVENTION
  STATUS        current
  DESCRIPTION
         "Reference value Status" 
  SYNTAX        INTEGER
                {
                  undefined(0),
                  none(1),
                  inProgress(2),
                  success(3),
                  error(4)
                }

FspR7PmSnapshotParameterTypes ::= TEXTUAL-CONVENTION
  STATUS        current
  DESCRIPTION
         "List of PM Snapshot parameters" 
  SYNTAX        INTEGER
                {
                  undefined(0),
                  outputPower(1),
                  inputPower(2),
                  attenuation(3),
                  attenuationOfVoa(4),
                  oscGain(5),
                  backreflectionPowerReceived(6),
                  ramanPumpPower(7),
                  oscPowerReceived(8),
                  variableGain(9),
                  txLineAttenuation(10),
                  rxLineAttenuation(11)
                }

FspR7RedLinedState ::= TEXTUAL-CONVENTION
  STATUS        current
  DESCRIPTION
         "will be set by higher level software to act as a barrier to deletion" 
  SYNTAX        INTEGER
                {
                  undefined(0),
                  yes(1),
                  no(2)
                }

FspR7RedLinedStateCaps ::= TEXTUAL-CONVENTION
  STATUS        current
  DESCRIPTION
         "will be set by higher level software to act as a barrier to deletion" 
  SYNTAX        BITS
                {
                  capUndefined(0),
                  capYes(1),
                  capNo(2)
                }

FspR7RowStatus ::= TEXTUAL-CONVENTION
  STATUS        current
  DESCRIPTION
         "RowStatus" 
  SYNTAX        INTEGER
                {
                  undefined(0),
                  active(1),
                  notInService(2),
                  notReady(3),
                  createAndGo(4),
                  createAndWait(5),
                  destroy(6)
                }

FspR7RowStatusCaps ::= TEXTUAL-CONVENTION
  STATUS        current
  DESCRIPTION
         "RowStatus" 
  SYNTAX        BITS
                {
                  capUndefined(0),
                  capActive(1),
                  capNotInService(2),
                  capNotReady(3),
                  capCreateAndGo(4),
                  capCreateAndWait(5),
                  capDestroy(6)
                }

FspR7SingleFiberLocation ::= TEXTUAL-CONVENTION
  STATUS        current
  DESCRIPTION
         "determines the location (A or B) for Single Fiber applications" 
  SYNTAX        INTEGER
                {
                  undefined(0),
                  locationA(1),  --location A for SF applications
                  locationB(2)  --location B for SF applications
                }

FspR7StartPmSnapshot ::= TEXTUAL-CONVENTION
  STATUS        current
  DESCRIPTION
         "Apply reference values" 
  SYNTAX        INTEGER
                {
                  undefined(0),
                  none(1),
                  apply(2)
                }

FspR7StateConnection ::= TEXTUAL-CONVENTION
  STATUS        current
  DESCRIPTION
         "State of the Physical Connection" 
  SYNTAX        INTEGER
                {
                  undefined(0),
                  standard(1),
                  mismatchEquipment(2),
                  mismatchConnection(3),
                  mismatchChannel(4),
                  mismatchPhysical(5),
                  invalidConfig(6),
                  nonStandard(7),
                  standardSpeq(8)
                }

FspR7TrapModeLegacy ::= TEXTUAL-CONVENTION
  STATUS        current
  DESCRIPTION
         "Trap Mode Legacy" 
  SYNTAX        INTEGER
                {
                  undefined(0),
                  false(1),
                  true(2)
                }

FspR7TypeConnection ::= TEXTUAL-CONVENTION
  STATUS        current
  DESCRIPTION
         "Type of equipment connection" 
  SYNTAX        INTEGER
                {
                  undefined(0),
                  connection1Way(1),
                  connection2Way(2)
                }

FspR7TypeConnectionCaps ::= TEXTUAL-CONVENTION
  STATUS        current
  DESCRIPTION
         "Type of equipment connection" 
  SYNTAX        BITS
                {
                  capUndefined(0),
                  capConnection1Way(1),
                  capConnection2Way(2)
                }

FspR7TypeCrs ::= TEXTUAL-CONVENTION
  STATUS        current
  DESCRIPTION
         "Type of Cross-Connect" 
  SYNTAX        INTEGER
                {
                  undefined(0),
                  connection1Way(1),  --Unidirectional CRS
                  connection2Way(2)  --Bidirectional CRS
                }

FspR7TypeCrsCaps ::= TEXTUAL-CONVENTION
  STATUS        current
  DESCRIPTION
         "Type of Cross-Connect" 
  SYNTAX        BITS
                {
                  capUndefined(0),
                  capConnection1Way(1),
                  capConnection2Way(2)
                }

FspR7Unsigned32Caps ::= TEXTUAL-CONVENTION
  DISPLAY-HINT "4d:4d"
  STATUS        current
  DESCRIPTION
         "A FspR7Unsigned32Caps specification.
         1..4 bytes - minValue(Unsigned32),
         5..8 bytes - maxValue(Unsigned32)." 
  SYNTAX        OCTET STRING (SIZE(0..8))


END
