FspR7-MIB DEFINITIONS ::= BEGIN

IMPORTS
    DisplayString,
    TestAndIncr,
    TimeStamp,
    RowStatus,
    RowPointer,
    DateAndTime,
    TruthValue,
    TEXTUAL-CONVENTION,
    MacAddress
                                        FROM  SNMPv2-TC
    MODULE-COMPLIANCE,
    NOTIFICATION-GROUP,
    OBJECT-GROUP
                                        FROM  SNMPv2-CONF
    Counter32,
    MODULE-IDENTITY,
    NOTIFICATION-TYPE,
    OBJECT-TYPE,
    OBJECT-IDENTITY,
    TimeTicks,
    mib-2,
    snmpModules,
    enterprises,
    Unsigned32,
    Integer32,
    IpAddress
                                        FROM  SNMPv2-SMI
    entPhysicalIndex
                                        FROM  ENTITY-MIB
    SnmpAdminString
                                        FROM  SNMP-FRAMEWORK-MIB
    FspR7EntityType
                                        FROM  ADVA-FSPR7-TC-MIB
    fspR7,
    TrapAlarmSeverity,
    ServiceImpairment,
    neEventLogTimeStamp,
    neEventLogIdentityTranslation,
    config,
    EnableState,
    OnOff,
    neTrapsinkAddress,
    Counter64String,
    EnableStateCaps,
    entityIndex,
    entityClass,
    entityContainedIn,
    controlPlaneWdmEntityIndex,
    controlPlaneEthEntityIndex,
    controlPlaneOtnEntityIndex,
    ptpEntityIndex,
    ptpEntityClass,
    ptpEntityContainedIn,
    LoopConfig,
    EthDuplexMode,
    EthDuplexModeCaps,
    SonetTimingSource,
    EntityIndex,
    VirtualContainerType,
    SonetVcBundleAllocation,
    SonetVcBundleAllocationCaps,
    ProtectionMech,
    ProtectionMechCaps,
    OtnPayloadType,
    OtnPayloadTypeCaps,
    VirtualContainerTypeCaps,
    OhTerminationLevel,
    OhTerminationLevelCaps,
    Grade,
    ApsHoldoffTime,
    OtnTcmLevel,
    SonetTimingSourceCaps,
    OtnTcmLevelCaps,
    ApsHoldoffTimeCaps,
    LoopConfigCaps,
    SonetTraceForm,
    TimMode,
    SonetTraceFormCaps,
    TimModeCaps,
    LogicalIfTransportCaps,
    snmpProxyEntrySingleTargetOutNodeAgentStatus,
    snmpProxyServerSynchroStage,
    vtpEntityIndex,
    FspR7EquipmentType,
    FspR7EquipmentTypeCaps,
    neRestoreConfig
                                        FROM  ADVA-MIB;
    

fspR7MIB MODULE-IDENTITY

    LAST-UPDATED "201703230000Z"

    ORGANIZATION "ADVA AG Optical Networking"

    CONTACT-INFO "
              ADVA AG Optical Networking
              Justus-von-Liebig-Str. 7
              12489 Berlin, Germany

              Support Europe:
              Phone:  +49 89 89 0665 848
              Fax:    +49 89 89 0665 22848
              e-mail: support@advaoptical.com

              Support USA:
              Phone:  +1 201 995 0080
              Fax:    +1 201 995 0081
              e-mail: support-usa@advaoptical.com

              Support Asia:
              Phone:  +81 3 5408 5891
              Fax:    +81 3 5408 5899
              e-mail: support-asia@advaoptical.com
            "

    DESCRIPTION   "The FSP3000R7 MIB.."

    REVISION      "201703230000Z"
    DESCRIPTION   "FSP3000 F7 Release 16.2.1 MIB."

    REVISION      "201606010000Z"
    DESCRIPTION   "FSP3000 F7 Release 16.1.2 MIB."

    REVISION      "201604010000Z"
    DESCRIPTION   "FSP3000 F7 Release 16.1.1 MIB."

    REVISION      "201512100000Z"
    DESCRIPTION   "FSP3000 F7 Release 15.2.1 MIB."

    REVISION      "201509030000Z"
    DESCRIPTION   "FSP3000 F7 Release 15.1.1 MIB."

    REVISION      "201503200000Z"
    DESCRIPTION   "FSP3000 F7 Release 13.3.1 MIB."

    REVISION      "201409290000Z"
    DESCRIPTION   "FSP3000 F7 Release 13.2.1 MIB."

    REVISION      "201308200000Z"
    DESCRIPTION   "FSP3000 F7 Release 12.1.1 MIB."

    REVISION      "201305010000Z"
    DESCRIPTION   "FSP3000 F7 Release 11.2.3 MIB."

    REVISION      "201209200000Z"
    DESCRIPTION   "FSP3000 F7 Release 11.2.1 MIB."

    REVISION      "201010290000Z"
    DESCRIPTION   "FSP3000 F7 Release 10.2.1 MIB."

    REVISION      "201010220000Z"
    DESCRIPTION   "FSP3000 F7 Release 10.2.0 MIB."

    REVISION      "201008310000Z"
    DESCRIPTION   "FSP3000 F7 Release 10.1.1 MIB."

    REVISION      "201006140000Z"
    DESCRIPTION   "FSP3000 F7 Release 9.4.1 MIB."

    REVISION      "201003240000Z"
    DESCRIPTION   "FSP3000 F7 Release 9.3.1 MIB."

    REVISION      "200911200000Z"
    DESCRIPTION   "FSP3000 F7 Release 9.2.1 MIB."

    REVISION      "200906050000Z"
    DESCRIPTION   "FSP3000 F7 Release 9.1.1 MIB."

    REVISION      "200901310000Z"
    DESCRIPTION   "FSP3000 F7 Release 8.3.0 MIB."

    REVISION      "200808280000Z"
    DESCRIPTION   "FSP3000 F7 Release 8.2.0 MIB."

    REVISION      "200710040000Z"
    DESCRIPTION   "FSP3000 F7 Release 8.1.1 MIB."

    REVISION      "200709240000Z"
    DESCRIPTION   "FSP3000 F7 Release 8.1 MIB."

    REVISION      "200705070000Z"
    DESCRIPTION   "FSP3000 F7 Release 7.1.5 MIB."

    REVISION      "200701030000Z"
    DESCRIPTION   "FSP3000 F7 Release 7.1.0 MIB."

    REVISION      "200611280000Z"
    DESCRIPTION   "FSP3000 F7 Release 7.0.6H MIB"

    REVISION      "200609050000Z"
    DESCRIPTION   "FSP3000 F7 Release 7.0.6D MIB."

    REVISION      "200606140000Z"
    DESCRIPTION   "FSP3000 F7 Release 7.0.6 MIB."

    REVISION      "200605040000Z"
    DESCRIPTION   "FSP3000 F7 Release 7.0.2 MIB."
    ::= { fspR7 2 }



adminMIB
    OBJECT IDENTIFIER ::= { fspR7MIB 2 }


neAdmin
    OBJECT IDENTIFIER ::= { adminMIB 1 }

neTimeConfig
    OBJECT IDENTIFIER ::= { neAdmin 30 }

routingMIB
    OBJECT IDENTIFIER ::= { adminMIB 2 }

fspUser
    OBJECT IDENTIFIER ::= { adminMIB 3 }

srvSyslog
    OBJECT IDENTIFIER ::= { adminMIB 4 }

channelTrace
    OBJECT IDENTIFIER ::= { adminMIB 5 }

dcnOspf
    OBJECT IDENTIFIER ::= { adminMIB 6 }

haMIB
    OBJECT IDENTIFIER ::= { adminMIB 7 }

radius
    OBJECT IDENTIFIER ::= { adminMIB 8 }

snmpCommunityMIB
    OBJECT IDENTIFIER ::= { adminMIB 9 }

profileMIB
    OBJECT IDENTIFIER ::= { adminMIB 10 }

conditionMIB
    OBJECT IDENTIFIER ::= { fspR7MIB 1 }


conditionFilters
    OBJECT IDENTIFIER ::= { conditionMIB 1 }

currentConditions
    OBJECT IDENTIFIER ::= { conditionMIB 2 }

alarmProfileConfig
    OBJECT IDENTIFIER ::= { conditionMIB 3 }

trapMIB
    OBJECT IDENTIFIER ::= { fspR7MIB 3 }


trapMibPrefix
    OBJECT IDENTIFIER ::= { trapMIB 0 }

trapVariables
    OBJECT IDENTIFIER ::= { trapMIB 1 }

configAndStatusMIB
    OBJECT IDENTIFIER ::= { fspR7MIB 4 }


commonConfigAndStatus
    OBJECT IDENTIFIER ::= { configAndStatusMIB 1 }

equipmentConfigAndStatus
    OBJECT IDENTIFIER ::= { configAndStatusMIB 2 }

interfaceConfigAndStatus
    OBJECT IDENTIFIER ::= { configAndStatusMIB 3 }

serviceConfigAndStatus
    OBJECT IDENTIFIER ::= { configAndStatusMIB 4 }

gfpServiceConfigAndStatus
    OBJECT IDENTIFIER ::= { serviceConfigAndStatus 1 }

connectionConfigAndStatus
    OBJECT IDENTIFIER ::= { configAndStatusMIB 5 }

systemConfigAndStatus
    OBJECT IDENTIFIER ::= { configAndStatusMIB 6 }

controlPlaneConfigAndStatus
    OBJECT IDENTIFIER ::= { configAndStatusMIB 7 }

deploymentProvisioningMIB
    OBJECT IDENTIFIER ::= { fspR7MIB 5 }


shelfDeployProv
    OBJECT IDENTIFIER ::= { deploymentProvisioningMIB 1 }

moduleDeployProv
    OBJECT IDENTIFIER ::= { deploymentProvisioningMIB 2 }

plugDeployProv
    OBJECT IDENTIFIER ::= { deploymentProvisioningMIB 3 }

facilityDeployProv
    OBJECT IDENTIFIER ::= { deploymentProvisioningMIB 4 }

connectionDeployProv
    OBJECT IDENTIFIER ::= { deploymentProvisioningMIB 5 }

crossConnectionDeployProv
    OBJECT IDENTIFIER ::= { deploymentProvisioningMIB 6 }

cloningEntitiesDeployProv
    OBJECT IDENTIFIER ::= { deploymentProvisioningMIB 7 }

controlPlaneDeployProv
    OBJECT IDENTIFIER ::= { deploymentProvisioningMIB 8 }

parameterCapabilities
    OBJECT IDENTIFIER ::= { deploymentProvisioningMIB 9 }

performanceMIB
    OBJECT IDENTIFIER ::= { fspR7MIB 6 }

performanceAdmin
    OBJECT IDENTIFIER ::= { performanceMIB 1 }

performanceMonitoring
    OBJECT IDENTIFIER ::= { performanceMIB 2 }

fspR7Conformance
    OBJECT IDENTIFIER ::= { fspR7MIB 7 }

fspR7VendorTypes
    OBJECT IDENTIFIER ::= { fspR7MIB 8 }

fspR7Products
    OBJECT IDENTIFIER ::= { fspR7 1 }


fspR7V1 OBJECT-IDENTITY
    STATUS      current
    DESCRIPTION   "This object uniquely identifies a Network Element using the current FspR7MIB release. V1 will be used
         for all releases until major changes require a new sysObjectID to assure backward compatibility."
    ::= { fspR7Products 1 }

ots1000 OBJECT-IDENTITY
    STATUS      current
    DESCRIPTION   "OTS1000 System."
    ::= { fspR7Products 2 }

ApsDirection ::= TEXTUAL-CONVENTION
  STATUS        current
  DESCRIPTION
         "Bi-Directional | Unidirectional setup used in protection setup: Not to be used by others" 
  SYNTAX        INTEGER
                {
                  undefined(0),
                  bidirectional(1),  --bidirectional
                  unidirectional(2)  --unidirectional
                }

ApsDirectionCaps ::= TEXTUAL-CONVENTION
  STATUS        current
  DESCRIPTION
         "Bi-Directional | Unidirectional setup used in protection setup: Not to be used by others" 
  SYNTAX        BITS
                {
                  capUndefined(0),
                  capBidirectional(1),
                  capUnidirectional(2)
                }

ApsRevertMode ::= TEXTUAL-CONVENTION
  STATUS        current
  DESCRIPTION
         "Revertive Protection Switching" 
  SYNTAX        INTEGER
                {
                  undefined(0),
                  nonrevertive(1),  --Revertive Protection Switching disabled
                  revertive(2)  --Revertive Protection Switching enabled
                }

ApsRevertModeCaps ::= TEXTUAL-CONVENTION
  STATUS        current
  DESCRIPTION
         "Revertive Protection Switching" 
  SYNTAX        BITS
                {
                  capUndefined(0),
                  capNonrevertive(1),
                  capRevertive(2)
                }

ApsType ::= TEXTUAL-CONVENTION
  STATUS        current
  DESCRIPTION
         "Type of Automatic Protection Switching; triggered by standing conditions" 
  SYNTAX        INTEGER
                {
                  undefined(0),
                  line(2),  --SONET Linear APS, SDH Multiplex Section Protection
                  sncN(3),  --OTN subnetwork connection Non-intrusive
                  sncI(4),  --OTN subnetwork connection Inherent
                  sncS(5),  --OTN subnetwork connection Sublayer (TCM)
                  eth(6),  --Ethernet
                  phys(7),  --Switching based on physical layer only
                  sncNPM(8),  --OTN subnetwork connection Non-intrusive Path Monitoring
                  sncNTCM(9),  --OTN subnetwork connection Non-intrusive TCM
                  sncISM(10),  --OTN subnetwork connection Inherent Section Monitoring
                  mux(11),  --ADVA proprietary
                  pcs(12),  --Physical Conversion Sublayer
                  ethSncI(13),  --ETH VLAN G.8031 protection
                  ethSncN(14),  --ETH VLAN G.8031 protection
                  ethSncS(15),  --ETH VLAN G.8031 protection
                  ethSncT(16),  --ETH VLAN G.8031 protection
                  sncNLine(18),  --if facility TYPE is OTN (OTU# / ODU#) payload SDH/SONET
                  sncNPath(19),  --if facility TYPE is OTN (OTU# / ODU#) payload SDH/SONET
                  path(20)  --SONET APS performed at Path layer
                }

ApsTypeCaps ::= TEXTUAL-CONVENTION
  STATUS        current
  DESCRIPTION
         "Type of Automatic Protection Switching; triggered by standing conditions" 
  SYNTAX        BITS
                {
                  capUndefined(0),
                  capLine(2),
                  capSncN(3),
                  capSncI(4),
                  capSncS(5),
                  capEth(6),
                  capPhys(7),
                  capSncNPM(8),
                  capSncNTCM(9),
                  capSncISM(10),
                  capMux(11),
                  capPcs(12),
                  capEthSncI(13),
                  capEthSncN(14),
                  capEthSncS(15),
                  capEthSncT(16),
                  capSncNLine(18),
                  capSncNPath(19),
                  capPath(20)
                }

Counter64StringCaps ::= TEXTUAL-CONVENTION
  STATUS        current
  DESCRIPTION
         "" 
  SYNTAX        OCTET STRING (SIZE(0..16))

FspR7AccessLevel ::= TEXTUAL-CONVENTION
  STATUS        current
  DESCRIPTION
         "Maximum allowed file access attribute." 
  SYNTAX        INTEGER
                {
                  undefined(0),
                  ro(1),
                  rw(2)
                }

FspR7AccessProtocol ::= TEXTUAL-CONVENTION
  STATUS        current
  DESCRIPTION
         "Possible services accross F7 system" 
  SYNTAX        INTEGER
                {
                  undefined(0),
                  none(1),
                  serialCraft(2),
                  telnetCraft(3),
                  telnetTl1(4),
                  sshTl1(5),
                  sshCraft(6),
                  sshNetconf(7),
                  http(8),
                  httpsNed(9),
                  httpsRestconf(10),
                  httpsCprest(11),
                  httpNi(12),
                  ftp(13),
                  snmp(14),
                  other(15)
                }

FspR7AccessStatus ::= TEXTUAL-CONVENTION
  STATUS        current
  DESCRIPTION
         "Indication whether security operation was succesful/unsuccessful." 
  SYNTAX        INTEGER
                {
                  undefined(0),
                  none(1),
                  success(2),
                  authenticationError(3),
                  sessionError(4)
                }

FspR7AccountFlag ::= TEXTUAL-CONVENTION
  STATUS        current
  DESCRIPTION
         "" 
  SYNTAX        INTEGER
                {
                  undefined(0),
                  none(1),
                  authForced(2)
                }

FspR7AccState ::= TEXTUAL-CONVENTION
  STATUS        current
  DESCRIPTION
         "" 
  SYNTAX        INTEGER
                {
                  undefined(0),
                  unlocked(1),
                  locked(2),
                  inactivityLock(3),
                  failLoginlock(4),
                  expired(5)
                }

FspR7AccStateCaps ::= TEXTUAL-CONVENTION
  STATUS        current
  DESCRIPTION
         "" 
  SYNTAX        BITS
                {
                  capUndefined(0),
                  capUnlocked(1),
                  capLocked(2),
                  capInactivityLock(3),
                  capFailLoginlock(4),
                  capExpired(5)
                }

FspR7Action ::= TEXTUAL-CONVENTION
  STATUS        current
  DESCRIPTION
         "The action to take when a filtering rule applies" 
  SYNTAX        INTEGER
                {
                  undefined(0),
                  accept(1),
                  drop(2),
                  jump(3)
                }

FspR7ActionCaps ::= TEXTUAL-CONVENTION
  STATUS        current
  DESCRIPTION
         "The action to take when a filtering rule applies" 
  SYNTAX        BITS
                {
                  capUndefined(0),
                  capAccept(1),
                  capDrop(2),
                  capJump(3)
                }

FspR7AdminState ::= TEXTUAL-CONVENTION
  STATUS        current
  DESCRIPTION
         "Administrative State is displayed in the GUI and Craft. Transition to Unassigend requires the entity to be deleted." 
  SYNTAX        INTEGER
                {
                  undefined(0),
                  uas(1),
                  is(2),
                  ains(3),
                  mgt(4),
                  mt(5),
                  dsbld(6),
                  pps(7)
                }

FspR7AdminStateCaps ::= TEXTUAL-CONVENTION
  STATUS        current
  DESCRIPTION
         "Administrative State is displayed in the GUI and Craft. Transition to Unassigend requires the entity to be deleted." 
  SYNTAX        BITS
                {
                  capUndefined(0),
                  capUas(1),
                  capIs(2),
                  capAins(3),
                  capMgt(4),
                  capMt(5),
                  capDsbld(6),
                  capPps(7)
                }

FspR7AidType ::= TEXTUAL-CONVENTION
  STATUS        current
  DESCRIPTION
         "Type of Access Identifier" 
  SYNTAX        INTEGER
                {
                  undefined(0),
                  none(1),
                  sys(2),
                  eqpt(3),
                  ch(4),
                  dcn(5),
                  ol(6),
                  om(7),
                  sts1(8),
                  sts3c(9),
                  sts24c(10),
                  sts48c(11),
                  vc3(12),
                  vc4(13),
                  vs1(14),
                  vs4c(15),
                  sh(16),
                  lif(17),
                  lifCp(18),
                  tnlWdm(19),
                  vc4c8(20),
                  vc4c16(21),
                  otl(22),
                  tnlEth(24),
                  tnlOtn(25)
                }

FspR7AlsHoldoff ::= TEXTUAL-CONVENTION
  STATUS        current
  DESCRIPTION
         "Hold-Off Period for ALS Consequent Action" 
  SYNTAX        INTEGER
                {
                  undefined(0),
                  del0ms(1),  --Channel (Card) Protection or CLIENTP/BKTOBK Deployment or Regenerator
                  del250ms(2),  --Unprotected or Versatail Switched Protection (RSM,VSM)
                  del550ms(3)  --SDH/SONET ALS Hold-Off Time
                }

FspR7AlsHoldoffCaps ::= TEXTUAL-CONVENTION
  STATUS        current
  DESCRIPTION
         "Hold-Off Period for ALS Consequent Action" 
  SYNTAX        BITS
                {
                  capUndefined(0),
                  capDel0ms(1),
                  capDel250ms(2),
                  capDel550ms(3)
                }

FspR7AlsMode ::= TEXTUAL-CONVENTION
  STATUS        current
  DESCRIPTION
         "Determines the reaction in backward direction in response to a LOS
         on the same Interface: on a Network Interface connected to the DWDM
         this is a matter of laser safety" 
  SYNTAX        INTEGER
                {
                  undefined(0),
                  advaALS(1),  --ALS is implemented on a Network-Side facility in backward direction to ensure laser safety
                  sonetALS(2),  --Typical of Client-Side behavior, - where so desired, - with long laser pulses but without ensuring laser safety if on the network side
                  noALS(3),  --Typical of Client-Side behavior, - where so desired, - without ensuring laser safety if on the network side
                  fastAls(4)  --Fast ALS; special quick version of SDH-ALS generally applied to the network port
                }

FspR7AlsModeCaps ::= TEXTUAL-CONVENTION
  STATUS        current
  DESCRIPTION
         "Determines the reaction in backward direction in response to a LOS
         on the same Interface: on a Network Interface connected to the DWDM
         this is a matter of laser safety" 
  SYNTAX        BITS
                {
                  capUndefined(0),
                  capAdvaALS(1),
                  capSonetALS(2),
                  capNoALS(3),
                  capFastAls(4)
                }

FspR7ApplyAlarmProfile ::= TEXTUAL-CONVENTION
  STATUS        current
  DESCRIPTION
         "Apply Alarm Profile to all existing entities" 
  SYNTAX        INTEGER
                {
                  undefined(0),
                  none(1),
                  apply(2),
                  notDefinedToAP(3),
                  notDefinedToSpecific(4)
                }

FspR7ApplyAlarmProfileCaps ::= TEXTUAL-CONVENTION
  STATUS        current
  DESCRIPTION
         "Apply Alarm Profile to all existing entities" 
  SYNTAX        BITS
                {
                  capUndefined(0),
                  capNone(1),
                  capApply(2),
                  capNotDefinedToAP(3),
                  capNotDefinedToSpecific(4)
                }

FspR7APSCommand ::= TEXTUAL-CONVENTION
  STATUS        current
  DESCRIPTION
         "Protection Switch commands: Manual or Release.
         The 'Manual Switch' switches manually from addressed facility to
         the partner but does not force the traffic onto a broken fiber and
         it does not block the subsequent automatic functioning of the switch.
         The 'Release Switch' releases the current switch command.
         For 'Manual Switch' relevant only if revertivity is supported." 
  SYNTAX        INTEGER
                {
                  undefined(0),
                  release(1),
                  manualSwitch(2),
                  clear(3),
                  exercise(13),
                  manualSwitchToWorking(15),
                  manualSwitchToProtect(16),
                  forcedSwitchToProtect(20),
                  forcedSwitchToWorking(21),
                  lockout(23)
                }

FspR7APSCommandCaps ::= TEXTUAL-CONVENTION
  STATUS        current
  DESCRIPTION
         "Protection Switch commands: Manual or Release.
         The 'Manual Switch' switches manually from addressed facility to
         the partner but does not force the traffic onto a broken fiber and
         it does not block the subsequent automatic functioning of the switch.
         The 'Release Switch' releases the current switch command.
         For 'Manual Switch' relevant only if revertivity is supported." 
  SYNTAX        BITS
                {
                  capUndefined(0),
                  capRelease(1),
                  capManualSwitch(2),
                  capClear(3),
                  capExercise(13),
                  capManualSwitchToWorking(15),
                  capManualSwitchToProtect(16),
                  capForcedSwitchToProtect(20),
                  capForcedSwitchToWorking(21),
                  capLockout(23)
                }

FspR7AseTabOpr ::= TEXTUAL-CONVENTION
  STATUS        current
  DESCRIPTION
         "ASE Table creation in process" 
  SYNTAX        INTEGER
                {
                  undefined(0),
                  rls(1),
                  build(2)
                }

FspR7AseTabOprCaps ::= TEXTUAL-CONVENTION
  STATUS        current
  DESCRIPTION
         "ASE Table creation in process" 
  SYNTAX        BITS
                {
                  capUndefined(0),
                  capRls(1),
                  capBuild(2)
                }

FspR7AutopLif ::= TEXTUAL-CONVENTION
  STATUS        current
  DESCRIPTION
         "Automatic Provisioning of LIF-CP" 
  SYNTAX        INTEGER
                {
                  undefined(0),
                  yes(1),
                  no(2)
                }

FspR7AutopLifCaps ::= TEXTUAL-CONVENTION
  STATUS        current
  DESCRIPTION
         "Automatic Provisioning of LIF-CP" 
  SYNTAX        BITS
                {
                  capUndefined(0),
                  capYes(1),
                  capNo(2)
                }

FspR7AutoThresReset ::= TEXTUAL-CONVENTION
  STATUS        current
  DESCRIPTION
         "Adaptive Threshold Control Reset" 
  SYNTAX        INTEGER
                {
                  undefined(0),
                  rls(1),
                  rtf(2)  --Manual reset of receiver threshold to default value
                }

FspR7AutoThresResetCaps ::= TEXTUAL-CONVENTION
  STATUS        current
  DESCRIPTION
         "Adaptive Threshold Control Reset" 
  SYNTAX        BITS
                {
                  capUndefined(0),
                  capRls(1),
                  capRtf(2)
                }

FspR7Baund ::= TEXTUAL-CONVENTION
  STATUS        current
  DESCRIPTION
         "Baud rate of the serial interface" 
  SYNTAX        INTEGER
                {
                  undefined(0),
                  baud2400(1),
                  baud4800(2),
                  baud9600(3),
                  baud19200(4),
                  baud38400(5),
                  baud57600(6),
                  baud115200(7)
                }

FspR7BaundCaps ::= TEXTUAL-CONVENTION
  STATUS        current
  DESCRIPTION
         "Baud rate of the serial interface" 
  SYNTAX        BITS
                {
                  capUndefined(0),
                  capBaud2400(1),
                  capBaud4800(2),
                  capBaud9600(3),
                  capBaud19200(4),
                  capBaud38400(5),
                  capBaud57600(6),
                  capBaud115200(7)
                }

FspR7BERThreshold ::= TEXTUAL-CONVENTION
  STATUS        current
  DESCRIPTION
         "Bit-Error-Based Degradation Definition for SONET (standard integration period)" 
  SYNTAX        INTEGER
                {
                  undefined(0),
                  exp5(1),
                  exp6(2),
                  exp7(3),
                  exp8(4),
                  exp9(5)
                }

FspR7BERThresholdCaps ::= TEXTUAL-CONVENTION
  STATUS        current
  DESCRIPTION
         "Bit-Error-Based Degradation Definition for SONET (standard integration period)" 
  SYNTAX        BITS
                {
                  capUndefined(0),
                  capExp5(1),
                  capExp6(2),
                  capExp7(3),
                  capExp8(4),
                  capExp9(5)
                }

FspR7BERThresholdSection ::= TEXTUAL-CONVENTION
  STATUS        current
  DESCRIPTION
         "Bit-Error-Based Degradation Definition for SONET (standard integration period)" 
  SYNTAX        INTEGER
                {
                  undefined(0),
                  exp7(3),
                  exp8(4),
                  exp9(5)
                }

FspR7BERThresholdSectionCaps ::= TEXTUAL-CONVENTION
  STATUS        current
  DESCRIPTION
         "Bit-Error-Based Degradation Definition for SONET (standard integration period)" 
  SYNTAX        BITS
                {
                  capUndefined(0),
                  capExp7(3),
                  capExp8(4),
                  capExp9(5)
                }

FspR7BidirectionalChannel ::= TEXTUAL-CONVENTION
  STATUS        current
  DESCRIPTION
         "Bidirectional Channel Rates from Provisioning" 
  SYNTAX        INTEGER
                {
                  undefined(0),
                  tx1310rx1490(1),
                  tx1490rx1310(2),
                  tx1310rx1550(3),
                  tx1550rx1310(4),
                  tx1270rx1330(5),
                  tx1330rx1270(6),
                  tx1266rx1275(7),
                  tx1275rx1266(8),
                  tx1286rx1295(9),
                  tx1295rx1286(10),
                  tx1306rx1315(11),
                  tx1315tx1306(12),
                  tx1326rx1335(13),
                  tx1335rx1326(14),
                  tx1346rx1355(15),
                  tx1355rx1346(16),
                  tx1366rx1375(17),
                  tx1375rx1366(18),
                  tx1426rx1435(19),
                  tx1435rx1426(20),
                  tx1446rx1455(21),
                  tx1455rx1446(22),
                  tx1466rx1475(23),
                  tx1475rx1466(24),
                  tx1486rx1495(25),
                  tx1495rx1486(26),
                  tx1506rx1515(27),
                  tx1515rx1506(28),
                  tx1526rx1535(29),
                  tx1535rx1526(30),
                  tx1546rx1555(31),
                  tx1555rx1546(32),
                  tx1566rx1575(33),
                  tx1575rx1566(34),
                  tx1586rx1595(35),
                  tx1595rx1586(36),
                  tx1606rx1615(37),
                  tx1615rx1606(38)
                }

FspR7BidirectionalChannelCaps ::= TEXTUAL-CONVENTION
  STATUS        current
  DESCRIPTION
         "Bidirectional Channel Rates from Provisioning" 
  SYNTAX        BITS
                {
                  capUndefined(0),
                  capTx1310rx1490(1),
                  capTx1490rx1310(2),
                  capTx1310rx1550(3),
                  capTx1550rx1310(4),
                  capTx1270rx1330(5),
                  capTx1330rx1270(6),
                  capTx1266rx1275(7),
                  capTx1275rx1266(8),
                  capTx1286rx1295(9),
                  capTx1295rx1286(10),
                  capTx1306rx1315(11),
                  capTx1315tx1306(12),
                  capTx1326rx1335(13),
                  capTx1335rx1326(14),
                  capTx1346rx1355(15),
                  capTx1355rx1346(16),
                  capTx1366rx1375(17),
                  capTx1375rx1366(18),
                  capTx1426rx1435(19),
                  capTx1435rx1426(20),
                  capTx1446rx1455(21),
                  capTx1455rx1446(22),
                  capTx1466rx1475(23),
                  capTx1475rx1466(24),
                  capTx1486rx1495(25),
                  capTx1495rx1486(26),
                  capTx1506rx1515(27),
                  capTx1515rx1506(28),
                  capTx1526rx1535(29),
                  capTx1535rx1526(30),
                  capTx1546rx1555(31),
                  capTx1555rx1546(32),
                  capTx1566rx1575(33),
                  capTx1575rx1566(34),
                  capTx1586rx1595(35),
                  capTx1595rx1586(36),
                  capTx1606rx1615(37),
                  capTx1615rx1606(38)
                }

FspR7Bip ::= TEXTUAL-CONVENTION
  STATUS        current
  DESCRIPTION
         "Bit Interleaved Parity" 
  SYNTAX        INTEGER
                {
                  undefined(0),
                  transparent(1),
                  terminate(2)
                }

FspR7BipCaps ::= TEXTUAL-CONVENTION
  STATUS        current
  DESCRIPTION
         "Bit Interleaved Parity" 
  SYNTAX        BITS
                {
                  capUndefined(0),
                  capTransparent(1),
                  capTerminate(2)
                }

FspR7Bitrate ::= TEXTUAL-CONVENTION
  STATUS        current
  DESCRIPTION
         "Provisioned data rate" 
  SYNTAX        INTEGER
                {
                  undefined(0),
                  bitrate10(1),
                  bitrate100(2),
                  bitrate1000(3),
                  bitrate10000(4)
                }

FspR7BitrateCaps ::= TEXTUAL-CONVENTION
  STATUS        current
  DESCRIPTION
         "Provisioned data rate" 
  SYNTAX        BITS
                {
                  capUndefined(0),
                  capBitrate10(1),
                  capBitrate100(2),
                  capBitrate1000(3),
                  capBitrate10000(4)
                }

FspR7BootloaderAccess ::= TEXTUAL-CONVENTION
  STATUS        current
  DESCRIPTION
         "NCU boot loader access via serial line" 
  SYNTAX        INTEGER
                {
                  undefined(0),
                  enable(1),
                  disable(2)
                }

FspR7CapInventory ::= TEXTUAL-CONVENTION
  STATUS        current
  DESCRIPTION
         "Capability level reported by HW" 
  SYNTAX        INTEGER
                {
                  undefined(0),
                  level0(1),  --This level represents the basic functionality;
                  level1(2),
                  level2(3),
                  level3(4),
                  level4(5),
                  level5(6),
                  unknown(50)  --This level represents the functionality unknown to system;
                }

FspR7CapInventoryCaps ::= TEXTUAL-CONVENTION
  STATUS        current
  DESCRIPTION
         "Capability level reported by HW" 
  SYNTAX        BITS
                {
                  capUndefined(0),
                  capLevel0(1),
                  capLevel1(2),
                  capLevel2(3),
                  capLevel3(4),
                  capLevel4(5),
                  capLevel5(6),
                  capUnknown(50)
                }

FspR7Category ::= TEXTUAL-CONVENTION
  STATUS        current
  DESCRIPTION
         "Used For Internal Purposes (and possibly for pre-selection in GUI)" 
  SYNTAX        INTEGER
                {
                  undefined(0),
                  shelf(1),
                  channelMod(2),
                  plug(3),
                  filter(4),
                  amplifier(5),
                  dcm(6),
                  switch(7),
                  oscm(8),
                  dummy(9),
                  common(10),
                  att(11),
                  jumper(12),
                  accessory(13),
                  fiber(14),
                  protectionMod(15),
                  any(16),
                  roadm(17),
                  ethernetMod(18),
                  powerSplitter(19),
                  adm(20),
                  xc(21)
                }

FspR7ChannelBandwidth ::= TEXTUAL-CONVENTION
  STATUS        current
  DESCRIPTION
         "Channel Bandwidth" 
  SYNTAX        INTEGER
                {
                  undefined(0),
                  band50G(1),
                  band75G(2),
                  band100G(3),
                  band125G(4),
                  band150G(5),
                  band175G(6),
                  band200G(7),
                  band225G(8),
                  band250G(9),
                  band275G(10),
                  band300G(11),
                  band20nm(12),
                  band325G(13),
                  band350G(14),
                  band375G(15),
                  band400G(16),
                  band37G5(17)
                }

FspR7ChannelBandwidthCaps ::= TEXTUAL-CONVENTION
  STATUS        current
  DESCRIPTION
         "Channel Bandwidth" 
  SYNTAX        BITS
                {
                  capUndefined(0),
                  capBand50G(1),
                  capBand75G(2),
                  capBand100G(3),
                  capBand125G(4),
                  capBand150G(5),
                  capBand175G(6),
                  capBand200G(7),
                  capBand225G(8),
                  capBand250G(9),
                  capBand275G(10),
                  capBand300G(11),
                  capBand20nm(12),
                  capBand325G(13),
                  capBand350G(14),
                  capBand375G(15),
                  capBand400G(16),
                  capBand37G5(17)
                }

FspR7ChannelIdentifier ::= TEXTUAL-CONVENTION
  STATUS        current
  DESCRIPTION
         "Channel" 
  SYNTAX        INTEGER
                {
                  undefined(0),
                  d01(1),  --196,00THz 1529,55nm
                  d02(2),  --195,90THz 1530,33nm
                  d03(3),  --195,80THz 1531,12nm
                  d04(4),  --195,70THz 1531,90nm
                  d05(5),  --195,50THz 1533,47nm
                  d06(6),  --195,40THz 1534,25nm
                  d07(7),  --195,30THz 1535,04nm
                  d08(8),  --195,20THz 1535,82nm
                  d09(9),  --195,00THz 1537,40nm
                  d10(10),  --194,90THz 1538,19nm
                  d11(11),  --194,80THz 1538,98nm
                  d12(12),  --194,70THz 1539,77nm
                  d13(13),  --194,50THz 1541,35nm
                  d14(14),  --194,40THz 1542,14nm
                  d15(15),  --194,30THz 1542,94nm
                  d16(16),  --194,20THz 1543,73nm
                  d17(17),  --193,80THz 1546,92nm
                  d18(18),  --193,70THz 1547,72nm
                  d19(19),  --193,60THz 1548,51nm
                  d20(20),  --193,50THz 1549,32nm
                  d21(21),  --193,30THz 1550,92nm
                  d22(22),  --193,20THz 1551,72nm
                  d23(23),  --193,10THz 1552,52nm
                  d24(24),  --193,00THz 1553,33nm
                  d25(25),  --192,80THz 1554,94nm
                  d26(26),  --192,70THz 1555,75nm
                  d27(27),  --192,60THz 1556,55nm
                  d28(28),  --192,50THz 1557,36nm
                  d29(29),  --192,30THz 1558,98nm
                  d30(30),  --192,20THz 1559,79nm
                  d31(31),  --192,10THz 1560,61nm
                  d32(32),  --192,00THz 1561,42nm
                  d33(33),  --191,00THz 1569,59nm
                  d34(34),  --190,90THz 1570,42nm
                  d35(35),  --190,80THz 1571,24nm
                  d36(36),  --190,70THz 1572,06nm
                  d37(37),  --190,50THz 1573,71nm
                  d38(38),  --190,40THz 1574,54nm
                  d39(39),  --190,30THz 1575,37nm
                  d40(40),  --190,20THz 1576,20nm
                  d41(41),  --190,00THz 1577,86nm
                  d42(42),  --189,90THz 1578,69nm
                  d43(43),  --189,80THz 1579,52nm
                  d44(44),  --189,70THz 1580,35nm
                  d45(45),  --189,50THz 1582,02nm
                  d46(46),  --189,40THz 1582,85nm
                  d47(47),  --189,30THz 1583,69nm
                  d48(48),  --189,20THz 1584,53nm
                  d49(49),  --188,80THz 1587,88nm
                  d50(50),  --188,70THz 1588,73nm
                  d51(51),  --188,60THz 1589,57nm
                  d52(52),  --188,50THz 1590,41nm
                  d53(53),  --188,30THz 1592,10nm
                  d54(54),  --188,20THz 1592,95nm
                  d55(55),  --188,10THz 1593,79nm
                  d56(56),  --188,00THz 1594,64nm
                  d57(57),  --187,80THz 1596,34nm
                  d58(58),  --187,70THz 1597,19nm
                  d59(59),  --187,60THz 1598,04nm
                  d60(60),  --187,50THz 1598,89nm
                  d61(61),  --187,30THz 1600,60nm
                  d62(62),  --187,20THz 1601,56nm
                  d63(63),  --187,10THz 1602,31nm
                  d64(64),  --187,00THz 1603,17nm
                  dc1(65),  --195,60THz 1532,68nm
                  dc2(66),  --195,10THz 1536,61nm
                  dc3(67),  --194,60THz 1540,56nm
                  dc4(68),  --194,10THz 1544,53nm
                  dc5(69),  --193,90THz 1546,12nm
                  dc6(70),  --193,40THz 1550,12nm
                  dc7(71),  --192,90THz 1554,13nm
                  dc8(72),  --192,40THz 1558,17nm
                  dl1(73),  --190,60THz 1572,89nm
                  dl2(74),  --190,10THz 1577,03nm
                  dl3(75),  --189,60THz 1581,18nm
                  dl4(76),  --189,10THz 1585,36nm
                  dl5(77),  --188,90THz 1587,04nm
                  dl6(78),  --188,40THz 1591,26nm
                  dl7(79),  --187,90THz 1595,49nm
                  dl8(80),  --187,40THz 1599,75nm
                  dc9(81),  --194,00THz 1545,322nm
                  dl9(82),  --189,00THz 1586,203nm
                  f19640(83),  --196.40THz 1526.44nm
                  f19635(84),  --196.35THz 1526.83nm
                  f19630(85),  --196.30THz 1527.22nm
                  f19625(86),  --196.25THz 1527.60nm
                  f19620(87),  --196.20THz 1527.99nm
                  f19615(88),  --196.15THz 1528.38nm
                  f19605(89),  --196.05THz 1529.16nm
                  c1470(91),  --1470,00nm
                  c1490(92),  --1490,00nm
                  c1510(93),  --1510,00nm
                  c1530(94),  --1530,00nm
                  c1550(95),  --1550,00nm
                  c1570(96),  --1570,00nm
                  c1590(97),  --1590,00nm
                  c1610(98),  --1610,00nm
                  s1310(99),  --1310,00nm OSC
                  s1630(100),  --1630,00nm OSC
                  g850(101),  --850,00nm
                  g1310(102),  --1310,00nm
                  g1550(103),  --1550,00nm
                  -- any(104),
                  notInGrid(105),
                  s1510(106),  --1510,00nm OSC
                  f19610(107),  --196,10THz  1528,7734nm
                  f19595(108),  --195,95THz  1529,9436nm
                  f19585(109),  --195,85THz  1530,7248nm
                  f19575(110),  --195,75THz  1531,5068nm
                  f19565(111),  --195,65THz  1532,2896nm
                  f19555(112),  --195,55THz  1533,0732nm
                  f19545(113),  --195,45THz  1533,8575nm
                  f19535(114),  --195,35THz  1534,6427nm
                  f19525(115),  --195,25THz  1535,4287nm
                  f19515(116),  --195,15THz  1536,2155nm
                  f19505(117),  --195,05THz  1537,0031nm
                  f19495(118),  --194,95THz  1537,7915nm
                  f19485(119),  --194,85THz  1538,5807nm
                  f19475(120),  --194,75THz  1539,3708nm
                  f19465(121),  --194,65THz  1540,1616nm
                  f19455(122),  --194,55THz  1540,9533nm
                  f19445(123),  --194,45THz  1541,7457nm
                  f19435(124),  --194,35THz  1542,5390nm
                  f19425(125),  --194,25THz  1543,3331nm
                  f19415(126),  --194,15THz  1544,1280nm
                  f19405(127),  --194,05THz  1544,9238nm
                  f19395(128),  --193,95THz  1545,7203nm
                  f19385(129),  --193,85THz  1546,5177nm
                  f19375(130),  --193,75THz  1547,3159nm
                  f19365(131),  --193,65THz  1548,1149nm
                  f19355(132),  --193,55THz  1548,9148nm
                  f19345(133),  --193,45THz  1549,7155nm
                  f19335(134),  --193,35THz  1550,5170nm
                  f19325(135),  --193,25THz  1551,3193nm
                  f19315(136),  --193,15THz  1552,1225nm
                  f19305(137),  --193,05THz  1552,9265nm
                  f19295(138),  --192,95THz  1553,7313nm
                  f19285(139),  --192,85THz  1554,5370nm
                  f19275(140),  --192,75THz  1555,3435nm
                  f19265(141),  --192,65THz  1556,1508nm
                  f19255(142),  --192,55THz  1556,9590nm
                  f19245(143),  --192,45THz  1557,7680nm
                  f19235(144),  --192,35THz  1558,5779nm
                  f19225(145),  --192,25THz  1559,3886nm
                  f19215(146),  --192,15THz  1560,2001nm
                  f19205(147),  --192,05THz  1561,0125nm
                  f19600(148),  --196,00THz 1529,55nm D01
                  f19590(149),  --195,90THz 1530,33nm D02
                  f19580(150),  --195,80THz 1531,12nm D03
                  f19570(151),  --195,70THz 1531,90nm D04
                  f19560(152),  --195,60THz 1532,68nm DC1
                  f19550(153),  --195,50THz 1533,47nm D05
                  f19540(154),  --195,40THz 1534,25nm D06
                  f19530(155),  --195,30THz 1535,04nm D07
                  f19520(156),  --195,20THz 1535,82nm D08
                  f19510(157),  --195,10THz 1536,60nm DC2
                  f19500(158),  --195,00THz 1537,40nm D09
                  f19490(159),  --194,90THz 1538,19nm D10
                  f19480(160),  --194,80THz 1538,98nm D11
                  f19470(161),  --194,70THz 1539,77nm D12
                  f19460(162),  --194,60THz 1540,55nm DC3
                  f19450(163),  --194,50THz 1541,35nm D13
                  f19440(164),  --194,40THz 1542,14nm D14
                  f19430(165),  --194,30THz 1542,94nm D15
                  f19420(166),  --194,20THz 1543,73nm D16
                  f19410(167),  --194,10THz 1544,52nm DC4
                  f19400(168),  --194,00THz 1545,32nm DC9
                  f19390(169),  --193,90THz 1546,11nm DC5
                  f19380(170),  --193,80THz 1546,92nm D17
                  f19370(171),  --193,70THz 1547,72nm D18
                  f19360(172),  --193,60THz 1548,51nm D19
                  f19350(173),  --193,50THz 1549,32nm D20
                  f19340(174),  --193,40THz 1550,11nm DC6
                  f19330(175),  --193,30THz 1550,92nm D21
                  f19320(176),  --193,20THz 1551,72nm D22
                  f19310(177),  --193,10THz 1552,52nm D23
                  f19300(178),  --193,00THz 1553,33nm D24
                  f19290(179),  --192,90THz 1554,13nm DC7
                  f19280(180),  --192,80THz 1554,94nm D25
                  f19270(181),  --192,70THz 1555,75nm D26
                  f19260(182),  --192,60THz 1556,55nm D27
                  f19250(183),  --192,50THz 1557,36nm D28
                  f19240(184),  --192,40THz 1558,17nm DC8
                  f19230(185),  --192,30THz 1558,98nm D29
                  f19220(186),  --192,20THz 1559,79nm D30
                  f19210(187),  --192,10THz 1560,61nm D31
                  f19200(188),  --192,00THz 1561,42nm D32
                  c1270(189),  --1270,00nm
                  c1290(190),  --1290,00nm
                  c1310(191),  --1310,00nm
                  c1330(192),  --1330,00nm
                  c1350(193),  --1350,00nm
                  c1370(194),  --1370,00nm
                  c1430(195),  --1430,00nm
                  c1450(196),  --1450,00nm
                  s1610(197),  --1610,00nm OSC
                  t1650(198),  --1650,00nm OTDR
                  s1490(199),  --1490,00nm OSC
                  f19598(200),  --195.9875THz , 1529.6509nm
                  f19597(201),  --195.975THz , 1529.7485nm
                  f19596(202),  --195.9625THz , 1529.8461nm
                  f19593(203),  --195.9375THz , 1530.0413nm
                  f19592(204),  --195.925THz , 1530.1389nm
                  f19591(205),  --195.9125THz , 1530.2365nm
                  f19588(206),  --195.8875THz , 1530.4318nm
                  f19587(207),  --195.875THz , 1530.5295nm
                  f19586(208),  --195.8625THz , 1530.6271nm
                  f19583(209),  --195.8375THz , 1530.8225nm
                  f19582(210),  --195.825THz , 1530.9203nm
                  f19581(211),  --195.8125THz , 1531.018nm
                  f19578(212),  --195.7875THz , 1531.2135nm
                  f19577(213),  --195.775THz , 1531.3112nm
                  f19576(214),  --195.7625THz , 1531.409nm
                  f19573(215),  --195.7375THz , 1531.6046nm
                  f19572(216),  --195.725THz , 1531.7024nm
                  f19571(217),  --195.7125THz , 1531.8003nm
                  f19568(218),  --195.6875THz , 1531.996nm
                  f19567(219),  --195.675THz , 1532.0938nm
                  f19566(220),  --195.6625THz , 1532.1917nm
                  f19563(221),  --195.6375THz , 1532.3875nm
                  f19562(222),  --195.625THz , 1532.4854nm
                  f19561(223),  --195.6125THz , 1532.5833nm
                  f19558(224),  --195.5875THz , 1532.7792nm
                  f19557(225),  --195.575THz , 1532.8772nm
                  f19556(226),  --195.5625THz , 1532.9752nm
                  f19553(227),  --195.5375THz , 1533.1712nm
                  f19552(228),  --195.525THz , 1533.2692nm
                  f19551(229),  --195.5125THz , 1533.3672nm
                  f19548(230),  --195.4875THz , 1533.5633nm
                  f19547(231),  --195.475THz , 1533.6614nm
                  f19546(232),  --195.4625THz , 1533.7595nm
                  f19543(233),  --195.4375THz , 1533.9557nm
                  f19542(234),  --195.425THz , 1534.0538nm
                  f19541(235),  --195.4125THz , 1534.1519nm
                  f19538(236),  --195.3875THz , 1534.3482nm
                  f19537(237),  --195.375THz , 1534.4464nm
                  f19536(238),  --195.3625THz , 1534.5445nm
                  f19533(239),  --195.3375THz , 1534.7409nm
                  f19532(240),  --195.325THz , 1534.8392nm
                  f19531(241),  --195.3125THz , 1534.9374nm
                  f19528(242),  --195.2875THz , 1535.1339nm
                  f19527(243),  --195.275THz , 1535.2321nm
                  f19526(244),  --195.2625THz , 1535.3304nm
                  f19523(245),  --195.2375THz , 1535.527nm
                  f19522(246),  --195.225THz , 1535.6253nm
                  f19521(247),  --195.2125THz , 1535.7237nm
                  f19518(248),  --195.1875THz , 1535.9204nm
                  f19517(249),  --195.175THz , 1536.0187nm
                  f19516(250),  --195.1625THz , 1536.1171nm
                  f19513(251),  --195.1375THz , 1536.3139nm
                  f19512(252),  --195.125THz , 1536.4123nm
                  f19511(253),  --195.1125THz , 1536.5108nm
                  f19508(254),  --195.0875THz , 1536.7077nm
                  f19507(255),  --195.075THz , 1536.8061nm
                  f19506(256),  --195.0625THz , 1536.9046nm
                  f19503(257),  --195.0375THz , 1537.1016nm
                  f19502(258),  --195.025THz , 1537.2001nm
                  f19501(259),  --195.0125THz , 1537.2987nm
                  f19498(260),  --194.9875THz , 1537.4958nm
                  f19497(261),  --194.975THz , 1537.5943nm
                  f19496(262),  --194.9625THz , 1537.6929nm
                  f19493(263),  --194.9375THz , 1537.8901nm
                  f19492(264),  --194.925THz , 1537.9888nm
                  f19491(265),  --194.9125THz , 1538.0874nm
                  f19488(266),  --194.8875THz , 1538.2847nm
                  f19487(267),  --194.875THz , 1538.3834nm
                  f19486(268),  --194.8625THz , 1538.482nm
                  f19483(269),  --194.8375THz , 1538.6795nm
                  f19482(270),  --194.825THz , 1538.7782nm
                  f19481(271),  --194.8125THz , 1538.8769nm
                  f19478(272),  --194.7875THz , 1539.0744nm
                  f19477(273),  --194.775THz , 1539.1732nm
                  f19476(274),  --194.7625THz , 1539.272nm
                  f19473(275),  --194.7375THz , 1539.4696nm
                  f19472(276),  --194.725THz , 1539.5684nm
                  f19471(277),  --194.7125THz , 1539.6672nm
                  f19468(278),  --194.6875THz , 1539.865nm
                  f19467(279),  --194.675THz , 1539.9638nm
                  f19466(280),  --194.6625THz , 1540.0627nm
                  f19463(281),  --194.6375THz , 1540.2605nm
                  f19462(282),  --194.625THz , 1540.3595nm
                  f19461(283),  --194.6125THz , 1540.4584nm
                  f19458(284),  --194.5875THz , 1540.6563nm
                  f19457(285),  --194.575THz , 1540.7553nm
                  f19456(286),  --194.5625THz , 1540.8543nm
                  f19453(287),  --194.5375THz , 1541.0523nm
                  f19452(288),  --194.525THz , 1541.1513nm
                  f19451(289),  --194.5125THz , 1541.2503nm
                  f19448(290),  --194.4875THz , 1541.4485nm
                  f19447(291),  --194.475THz , 1541.5475nm
                  f19446(292),  --194.4625THz , 1541.6466nm
                  f19443(293),  --194.4375THz , 1541.8448nm
                  f19442(294),  --194.425THz , 1541.944nm
                  f19441(295),  --194.4125THz , 1542.0431nm
                  f19438(296),  --194.3875THz , 1542.2414nm
                  f19437(297),  --194.375THz , 1542.3406nm
                  f19436(298),  --194.3625THz , 1542.4398nm
                  f19433(299),  --194.3375THz , 1542.6382nm
                  f19432(300),  --194.325THz , 1542.7375nm
                  f19431(301),  --194.3125THz , 1542.8367nm
                  f19428(302),  --194.2875THz , 1543.0352nm
                  f19427(303),  --194.275THz , 1543.1345nm
                  f19426(304),  --194.2625THz , 1543.2338nm
                  f19423(305),  --194.2375THz , 1543.4324nm
                  f19422(306),  --194.225THz , 1543.5318nm
                  f19421(307),  --194.2125THz , 1543.6311nm
                  f19418(308),  --194.1875THz , 1543.8298nm
                  f19417(309),  --194.175THz , 1543.9292nm
                  f19416(310),  --194.1625THz , 1544.0286nm
                  f19413(311),  --194.1375THz , 1544.2275nm
                  f19412(312),  --194.125THz , 1544.3269nm
                  f19411(313),  --194.1125THz , 1544.4263nm
                  f19408(314),  --194.0875THz , 1544.6253nm
                  f19407(315),  --194.075THz , 1544.7248nm
                  f19406(316),  --194.0625THz , 1544.8243nm
                  f19403(317),  --194.0375THz , 1545.0233nm
                  f19402(318),  --194.025THz , 1545.1228nm
                  f19401(319),  --194.0125THz , 1545.2224nm
                  f19398(320),  --193.9875THz , 1545.4215nm
                  f19397(321),  --193.975THz , 1545.5211nm
                  f19396(322),  --193.9625THz , 1545.6207nm
                  f19393(323),  --193.9375THz , 1545.82nm
                  f19392(324),  --193.925THz , 1545.9196nm
                  f19391(325),  --193.9125THz , 1546.0193nm
                  f19388(326),  --193.8875THz , 1546.2186nm
                  f19387(327),  --193.875THz , 1546.3183nm
                  f19386(328),  --193.8625THz , 1546.418nm
                  f19383(329),  --193.8375THz , 1546.6174nm
                  f19382(330),  --193.825THz , 1546.7172nm
                  f19381(331),  --193.8125THz , 1546.8169nm
                  f19378(332),  --193.7875THz , 1547.0165nm
                  f19377(333),  --193.775THz , 1547.1163nm
                  f19376(334),  --193.7625THz , 1547.2161nm
                  f19373(335),  --193.7375THz , 1547.4157nm
                  f19372(336),  --193.725THz , 1547.5156nm
                  f19371(337),  --193.7125THz , 1547.6155nm
                  f19368(338),  --193.6875THz , 1547.8152nm
                  f19367(339),  --193.675THz , 1547.9151nm
                  f19366(340),  --193.6625THz , 1548.015nm
                  f19363(341),  --193.6375THz , 1548.2149nm
                  f19362(342),  --193.625THz , 1548.3148nm
                  f19361(343),  --193.6125THz , 1548.4148nm
                  f19358(344),  --193.5875THz , 1548.6148nm
                  f19357(345),  --193.575THz , 1548.7148nm
                  f19356(346),  --193.5625THz , 1548.8148nm
                  f19353(347),  --193.5375THz , 1549.0148nm
                  f19352(348),  --193.525THz , 1549.1149nm
                  f19351(349),  --193.5125THz , 1549.2149nm
                  f19348(350),  --193.4875THz , 1549.4151nm
                  f19347(351),  --193.475THz , 1549.5152nm
                  f19346(352),  --193.4625THz , 1549.6153nm
                  f19343(353),  --193.4375THz , 1549.8156nm
                  f19342(354),  --193.425THz , 1549.9158nm
                  f19341(355),  --193.4125THz , 1550.0159nm
                  f19338(356),  --193.3875THz , 1550.2163nm
                  f19337(357),  --193.375THz , 1550.3165nm
                  f19336(358),  --193.3625THz , 1550.4167nm
                  f19333(359),  --193.3375THz , 1550.6172nm
                  f19332(360),  --193.325THz , 1550.7175nm
                  f19331(361),  --193.3125THz , 1550.8178nm
                  f19328(362),  --193.2875THz , 1551.0183nm
                  f19327(363),  --193.275THz , 1551.1187nm
                  f19326(364),  --193.2625THz , 1551.219nm
                  f19323(365),  --193.2375THz , 1551.4197nm
                  f19322(366),  --193.225THz , 1551.52nm
                  f19321(367),  --193.2125THz , 1551.6204nm
                  f19318(368),  --193.1875THz , 1551.8212nm
                  f19317(369),  --193.175THz , 1551.9216nm
                  f19316(370),  --193.1625THz , 1552.022nm
                  f19313(371),  --193.1375THz , 1552.2229nm
                  f19312(372),  --193.125THz , 1552.3234nm
                  f19311(373),  --193.1125THz , 1552.4239nm
                  f19308(374),  --193.0875THz , 1552.6249nm
                  f19307(375),  --193.075THz , 1552.7254nm
                  f19306(376),  --193.0625THz , 1552.8259nm
                  f19303(377),  --193.0375THz , 1553.027nm
                  f19302(378),  --193.025THz , 1553.1276nm
                  f19301(379),  --193.0125THz , 1553.2282nm
                  f19298(380),  --192.9875THz , 1553.4294nm
                  f19297(381),  --192.975THz , 1553.53nm
                  f19296(382),  --192.9625THz , 1553.6307nm
                  f19293(383),  --192.9375THz , 1553.832nm
                  f19292(384),  --192.925THz , 1553.9327nm
                  f19291(385),  --192.9125THz , 1554.0333nm
                  f19288(386),  --192.8875THz , 1554.2348nm
                  f19287(387),  --192.875THz , 1554.3355nm
                  f19286(388),  --192.8625THz , 1554.4362nm
                  f19283(389),  --192.8375THz , 1554.6378nm
                  f19282(390),  --192.825THz , 1554.7385nm
                  f19281(391),  --192.8125THz , 1554.8393nm
                  f19278(392),  --192.7875THz , 1555.041nm
                  f19277(393),  --192.775THz , 1555.1418nm
                  f19276(394),  --192.7625THz , 1555.2426nm
                  f19273(395),  --192.7375THz , 1555.4444nm
                  f19272(396),  --192.725THz , 1555.5452nm
                  f19271(397),  --192.7125THz , 1555.6461nm
                  f19268(398),  --192.6875THz , 1555.848nm
                  f19267(399),  --192.675THz , 1555.9489nm
                  f19266(400),  --192.6625THz , 1556.0499nm
                  f19263(401),  --192.6375THz , 1556.2518nm
                  f19262(402),  --192.625THz , 1556.3528nm
                  f19261(403),  --192.6125THz , 1556.4538nm
                  f19258(404),  --192.5875THz , 1556.6558nm
                  f19257(405),  --192.575THz , 1556.7569nm
                  f19256(406),  --192.5625THz , 1556.8579nm
                  f19253(407),  --192.5375THz , 1557.0601nm
                  f19252(408),  --192.525THz , 1557.1612nm
                  f19251(409),  --192.5125THz , 1557.2623nm
                  f19248(410),  --192.4875THz , 1557.4646nm
                  f19247(411),  --192.475THz , 1557.5657nm
                  f19246(412),  --192.4625THz , 1557.6669nm
                  f19243(413),  --192.4375THz , 1557.8692nm
                  f19242(414),  --192.425THz , 1557.9704nm
                  f19241(415),  --192.4125THz , 1558.0716nm
                  f19238(416),  --192.3875THz , 1558.2741nm
                  f19237(417),  --192.375THz , 1558.3754nm
                  f19236(418),  --192.3625THz , 1558.4766nm
                  f19233(419),  --192.3375THz , 1558.6792nm
                  f19232(420),  --192.325THz , 1558.7805nm
                  f19231(421),  --192.3125THz , 1558.8818nm
                  f19228(422),  --192.2875THz , 1559.0845nm
                  f19227(423),  --192.275THz , 1559.1858nm
                  f19226(424),  --192.2625THz , 1559.2872nm
                  f19223(425),  --192.2375THz , 1559.49nm
                  f19222(426),  --192.225THz , 1559.5914nm
                  f19221(427),  --192.2125THz , 1559.6928nm
                  f19218(428),  --192.1875THz , 1559.8957nm
                  f19217(429),  --192.175THz , 1559.9972nm
                  f19216(430),  --192.1625THz , 1560.0987nm
                  f19213(431),  --192.1375THz , 1560.3016nm
                  f19212(432),  --192.125THz , 1560.4032nm
                  f19211(433),  --192.1125THz , 1560.5047nm
                  f19208(434),  --192.0875THz , 1560.7078nm
                  f19207(435),  --192.075THz , 1560.8094nm
                  f19206(436),  --192.0625THz , 1560.9109nm
                  f19203(437),  --192.0375THz , 1561.1141nm
                  f19202(438),  --192.025THz , 1561.2158nm
                  f19201(439),  --192.0125THz , 1561.3174nm
                  f19198(440),  --191.9875THz , 1561.5207nm
                  f19197(441),  --191.975THz , 1561.6224nm
                  f19196(442),  --191.9625THz , 1561.7241nm
                  f19195(443),  --191.95THz , 1561.8258nm
                  f19193(444),  --191.9375THz , 1561.9275nm
                  f19192(445),  --191.925THz , 1562.0292nm
                  f19191(446),  --191.9125THz , 1562.131nm
                  f19190(447),  --191.9THz , 1562.2327nm
                  f19188(448),  --191.8875THz , 1562.3345nm
                  f19187(449),  --191.875THz , 1562.4363nm
                  f19186(450),  --191.8625THz , 1562.5381nm
                  f19185(451),  --191.85THz , 1562.6399nm
                  f19183(452),  --191.8375THz , 1562.7417nm
                  f19182(453),  --191.825THz , 1562.8435nm
                  f19181(454),  --191.8125THz , 1562.9454nm
                  f19180(455),  --191.8THz , 1563.0472nm
                  f19178(456),  --191.7875THz , 1563.1491nm
                  f19177(457),  --191.775THz , 1563.251nm
                  f19176(458),  --191.7625THz , 1563.3529nm
                  f19175(459),  --191.75THz , 1563.4548nm
                  f19173(460),  --191.7375THz , 1563.5567nm
                  f19172(461),  --191.725THz , 1563.6587nm
                  f19171(462),  --191.7125THz , 1563.7606nm
                  f19170(463),  --191.7THz , 1563.8626nm
                  f19168(464),  --191.6875THz , 1563.9646nm
                  f19167(465),  --191.675THz , 1564.0666nm
                  f19166(466),  --191.6625THz , 1564.1686nm
                  f19165(467),  --191.65THz , 1564.2706nm
                  f19163(468),  --191.6375THz , 1564.3726nm
                  f19162(469),  --191.625THz , 1564.4747nm
                  f19161(470),  --191.6125THz , 1564.5767nm
                  f19160(471),  --191.6THz , 1564.6788nm
                  f19158(472),  --191.5875THz , 1564.7809nm
                  f19157(473),  --191.575THz , 1564.883nm
                  f19156(474),  --191.5625THz , 1564.9851nm
                  f19155(475),  --191.55THz , 1565.0872nm
                  f19153(476),  --191.5375THz , 1565.1894nm
                  f19152(477),  --191.525THz , 1565.2915nm
                  f19151(478),  --191.5125THz , 1565.3937nm
                  f19150(479),  --191.5THz , 1565.4959nm
                  f19148(480),  --191.4875THz , 1565.5981nm
                  f19147(481),  --191.475THz , 1565.7003nm
                  f19146(482),  --191.4625THz , 1565.8025nm
                  f19145(483),  --191.45THz , 1565.9047nm
                  f19143(484),  --191.4375THz , 1566.007nm
                  f19142(485),  --191.425THz , 1566.1092nm
                  f19141(486),  --191.4125THz , 1566.2115nm
                  f19140(487),  --191.4THz , 1566.3138nm
                  f19138(488),  --191.3875THz , 1566.4161nm
                  f19137(489),  --191.375THz , 1566.5184nm
                  f19136(490),  --191.3625THz , 1566.6207nm
                  f19135(491),  --191.35THz , 1566.7231nm
                  f19133(492),  --191.3375THz , 1566.8254nm
                  f19132(493),  --191.325THz , 1566.9278nm
                  f19131(494),  --191.3125THz , 1567.0302nm
                  f19130(495),  --191.3THz , 1567.1326nm
                  f19128(496),  --191.2875THz , 1567.235nm
                  f19127(497),  --191.275THz , 1567.3374nm
                  f19126(498),  --191.2625THz , 1567.4398nm
                  f19125(499),  --191.25THz , 1567.5423nm
                  notDefined(500),
                  g1490(501),  --1490,00nm
                  f19123(502),  --191.2375THz , 1567.6447nm
                  f19122(503),  --191.225THz , 1567.7472nm
                  f19121(504),  --191.2125THz , 1567.8497nm
                  f19608(505),  --196.08750THz , 1528.8708nm
                  f19607(506),  --196.0750THz , 1528.9683nm
                  f19606(507),  --196.06250THz , 1529.0658nm
                  f19603(509),  --196.03750THz , 1529.2608nm
                  f19602(510),  --196.02500THz , 1529.3583nm
                  f19601(511),  --196.01250THz , 1529.4558nm
                  systemSelect(512)
                }

FspR7ChannelIdentifierCaps ::= TEXTUAL-CONVENTION
  STATUS        current
  DESCRIPTION
         "Channel" 
  SYNTAX        BITS
                {
                  capUndefined(0),
                  capD01(1),
                  capD02(2),
                  capD03(3),
                  capD04(4),
                  capD05(5),
                  capD06(6),
                  capD07(7),
                  capD08(8),
                  capD09(9),
                  capD10(10),
                  capD11(11),
                  capD12(12),
                  capD13(13),
                  capD14(14),
                  capD15(15),
                  capD16(16),
                  capD17(17),
                  capD18(18),
                  capD19(19),
                  capD20(20),
                  capD21(21),
                  capD22(22),
                  capD23(23),
                  capD24(24),
                  capD25(25),
                  capD26(26),
                  capD27(27),
                  capD28(28),
                  capD29(29),
                  capD30(30),
                  capD31(31),
                  capD32(32),
                  capD33(33),
                  capD34(34),
                  capD35(35),
                  capD36(36),
                  capD37(37),
                  capD38(38),
                  capD39(39),
                  capD40(40),
                  capD41(41),
                  capD42(42),
                  capD43(43),
                  capD44(44),
                  capD45(45),
                  capD46(46),
                  capD47(47),
                  capD48(48),
                  capD49(49),
                  capD50(50),
                  capD51(51),
                  capD52(52),
                  capD53(53),
                  capD54(54),
                  capD55(55),
                  capD56(56),
                  capD57(57),
                  capD58(58),
                  capD59(59),
                  capD60(60),
                  capD61(61),
                  capD62(62),
                  capD63(63),
                  capD64(64),
                  capDc1(65),
                  capDc2(66),
                  capDc3(67),
                  capDc4(68),
                  capDc5(69),
                  capDc6(70),
                  capDc7(71),
                  capDc8(72),
                  capDl1(73),
                  capDl2(74),
                  capDl3(75),
                  capDl4(76),
                  capDl5(77),
                  capDl6(78),
                  capDl7(79),
                  capDl8(80),
                  capDc9(81),
                  capDl9(82),
                  capF19640(83),
                  capF19635(84),
                  capF19630(85),
                  capF19625(86),
                  capF19620(87),
                  capF19615(88),
                  capF19605(89),
                  capC1470(91),
                  capC1490(92),
                  capC1510(93),
                  capC1530(94),
                  capC1550(95),
                  capC1570(96),
                  capC1590(97),
                  capC1610(98),
                  capS1310(99),
                  capS1630(100),
                  capG850(101),
                  capG1310(102),
                  capG1550(103),
                  -- capAny(104),
                  capNotInGrid(105),
                  capS1510(106),
                  capF19610(107),
                  capF19595(108),
                  capF19585(109),
                  capF19575(110),
                  capF19565(111),
                  capF19555(112),
                  capF19545(113),
                  capF19535(114),
                  capF19525(115),
                  capF19515(116),
                  capF19505(117),
                  capF19495(118),
                  capF19485(119),
                  capF19475(120),
                  capF19465(121),
                  capF19455(122),
                  capF19445(123),
                  capF19435(124),
                  capF19425(125),
                  capF19415(126),
                  capF19405(127),
                  capF19395(128),
                  capF19385(129),
                  capF19375(130),
                  capF19365(131),
                  capF19355(132),
                  capF19345(133),
                  capF19335(134),
                  capF19325(135),
                  capF19315(136),
                  capF19305(137),
                  capF19295(138),
                  capF19285(139),
                  capF19275(140),
                  capF19265(141),
                  capF19255(142),
                  capF19245(143),
                  capF19235(144),
                  capF19225(145),
                  capF19215(146),
                  capF19205(147),
                  capF19600(148),
                  capF19590(149),
                  capF19580(150),
                  capF19570(151),
                  capF19560(152),
                  capF19550(153),
                  capF19540(154),
                  capF19530(155),
                  capF19520(156),
                  capF19510(157),
                  capF19500(158),
                  capF19490(159),
                  capF19480(160),
                  capF19470(161),
                  capF19460(162),
                  capF19450(163),
                  capF19440(164),
                  capF19430(165),
                  capF19420(166),
                  capF19410(167),
                  capF19400(168),
                  capF19390(169),
                  capF19380(170),
                  capF19370(171),
                  capF19360(172),
                  capF19350(173),
                  capF19340(174),
                  capF19330(175),
                  capF19320(176),
                  capF19310(177),
                  capF19300(178),
                  capF19290(179),
                  capF19280(180),
                  capF19270(181),
                  capF19260(182),
                  capF19250(183),
                  capF19240(184),
                  capF19230(185),
                  capF19220(186),
                  capF19210(187),
                  capF19200(188),
                  capC1270(189),
                  capC1290(190),
                  capC1310(191),
                  capC1330(192),
                  capC1350(193),
                  capC1370(194),
                  capC1430(195),
                  capC1450(196),
                  capS1610(197),
                  capT1650(198),
                  capS1490(199),
                  capF19598(200),
                  capF19597(201),
                  capF19596(202),
                  capF19593(203),
                  capF19592(204),
                  capF19591(205),
                  capF19588(206),
                  capF19587(207),
                  capF19586(208),
                  capF19583(209),
                  capF19582(210),
                  capF19581(211),
                  capF19578(212),
                  capF19577(213),
                  capF19576(214),
                  capF19573(215),
                  capF19572(216),
                  capF19571(217),
                  capF19568(218),
                  capF19567(219),
                  capF19566(220),
                  capF19563(221),
                  capF19562(222),
                  capF19561(223),
                  capF19558(224),
                  capF19557(225),
                  capF19556(226),
                  capF19553(227),
                  capF19552(228),
                  capF19551(229),
                  capF19548(230),
                  capF19547(231),
                  capF19546(232),
                  capF19543(233),
                  capF19542(234),
                  capF19541(235),
                  capF19538(236),
                  capF19537(237),
                  capF19536(238),
                  capF19533(239),
                  capF19532(240),
                  capF19531(241),
                  capF19528(242),
                  capF19527(243),
                  capF19526(244),
                  capF19523(245),
                  capF19522(246),
                  capF19521(247),
                  capF19518(248),
                  capF19517(249),
                  capF19516(250),
                  capF19513(251),
                  capF19512(252),
                  capF19511(253),
                  capF19508(254),
                  capF19507(255),
                  capF19506(256),
                  capF19503(257),
                  capF19502(258),
                  capF19501(259),
                  capF19498(260),
                  capF19497(261),
                  capF19496(262),
                  capF19493(263),
                  capF19492(264),
                  capF19491(265),
                  capF19488(266),
                  capF19487(267),
                  capF19486(268),
                  capF19483(269),
                  capF19482(270),
                  capF19481(271),
                  capF19478(272),
                  capF19477(273),
                  capF19476(274),
                  capF19473(275),
                  capF19472(276),
                  capF19471(277),
                  capF19468(278),
                  capF19467(279),
                  capF19466(280),
                  capF19463(281),
                  capF19462(282),
                  capF19461(283),
                  capF19458(284),
                  capF19457(285),
                  capF19456(286),
                  capF19453(287),
                  capF19452(288),
                  capF19451(289),
                  capF19448(290),
                  capF19447(291),
                  capF19446(292),
                  capF19443(293),
                  capF19442(294),
                  capF19441(295),
                  capF19438(296),
                  capF19437(297),
                  capF19436(298),
                  capF19433(299),
                  capF19432(300),
                  capF19431(301),
                  capF19428(302),
                  capF19427(303),
                  capF19426(304),
                  capF19423(305),
                  capF19422(306),
                  capF19421(307),
                  capF19418(308),
                  capF19417(309),
                  capF19416(310),
                  capF19413(311),
                  capF19412(312),
                  capF19411(313),
                  capF19408(314),
                  capF19407(315),
                  capF19406(316),
                  capF19403(317),
                  capF19402(318),
                  capF19401(319),
                  capF19398(320),
                  capF19397(321),
                  capF19396(322),
                  capF19393(323),
                  capF19392(324),
                  capF19391(325),
                  capF19388(326),
                  capF19387(327),
                  capF19386(328),
                  capF19383(329),
                  capF19382(330),
                  capF19381(331),
                  capF19378(332),
                  capF19377(333),
                  capF19376(334),
                  capF19373(335),
                  capF19372(336),
                  capF19371(337),
                  capF19368(338),
                  capF19367(339),
                  capF19366(340),
                  capF19363(341),
                  capF19362(342),
                  capF19361(343),
                  capF19358(344),
                  capF19357(345),
                  capF19356(346),
                  capF19353(347),
                  capF19352(348),
                  capF19351(349),
                  capF19348(350),
                  capF19347(351),
                  capF19346(352),
                  capF19343(353),
                  capF19342(354),
                  capF19341(355),
                  capF19338(356),
                  capF19337(357),
                  capF19336(358),
                  capF19333(359),
                  capF19332(360),
                  capF19331(361),
                  capF19328(362),
                  capF19327(363),
                  capF19326(364),
                  capF19323(365),
                  capF19322(366),
                  capF19321(367),
                  capF19318(368),
                  capF19317(369),
                  capF19316(370),
                  capF19313(371),
                  capF19312(372),
                  capF19311(373),
                  capF19308(374),
                  capF19307(375),
                  capF19306(376),
                  capF19303(377),
                  capF19302(378),
                  capF19301(379),
                  capF19298(380),
                  capF19297(381),
                  capF19296(382),
                  capF19293(383),
                  capF19292(384),
                  capF19291(385),
                  capF19288(386),
                  capF19287(387),
                  capF19286(388),
                  capF19283(389),
                  capF19282(390),
                  capF19281(391),
                  capF19278(392),
                  capF19277(393),
                  capF19276(394),
                  capF19273(395),
                  capF19272(396),
                  capF19271(397),
                  capF19268(398),
                  capF19267(399),
                  capF19266(400),
                  capF19263(401),
                  capF19262(402),
                  capF19261(403),
                  capF19258(404),
                  capF19257(405),
                  capF19256(406),
                  capF19253(407),
                  capF19252(408),
                  capF19251(409),
                  capF19248(410),
                  capF19247(411),
                  capF19246(412),
                  capF19243(413),
                  capF19242(414),
                  capF19241(415),
                  capF19238(416),
                  capF19237(417),
                  capF19236(418),
                  capF19233(419),
                  capF19232(420),
                  capF19231(421),
                  capF19228(422),
                  capF19227(423),
                  capF19226(424),
                  capF19223(425),
                  capF19222(426),
                  capF19221(427),
                  capF19218(428),
                  capF19217(429),
                  capF19216(430),
                  capF19213(431),
                  capF19212(432),
                  capF19211(433),
                  capF19208(434),
                  capF19207(435),
                  capF19206(436),
                  capF19203(437),
                  capF19202(438),
                  capF19201(439),
                  capF19198(440),
                  capF19197(441),
                  capF19196(442),
                  capF19195(443),
                  capF19193(444),
                  capF19192(445),
                  capF19191(446),
                  capF19190(447),
                  capF19188(448),
                  capF19187(449),
                  capF19186(450),
                  capF19185(451),
                  capF19183(452),
                  capF19182(453),
                  capF19181(454),
                  capF19180(455),
                  capF19178(456),
                  capF19177(457),
                  capF19176(458),
                  capF19175(459),
                  capF19173(460),
                  capF19172(461),
                  capF19171(462),
                  capF19170(463),
                  capF19168(464),
                  capF19167(465),
                  capF19166(466),
                  capF19165(467),
                  capF19163(468),
                  capF19162(469),
                  capF19161(470),
                  capF19160(471),
                  capF19158(472),
                  capF19157(473),
                  capF19156(474),
                  capF19155(475),
                  capF19153(476),
                  capF19152(477),
                  capF19151(478),
                  capF19150(479),
                  capF19148(480),
                  capF19147(481),
                  capF19146(482),
                  capF19145(483),
                  capF19143(484),
                  capF19142(485),
                  capF19141(486),
                  capF19140(487),
                  capF19138(488),
                  capF19137(489),
                  capF19136(490),
                  capF19135(491),
                  capF19133(492),
                  capF19132(493),
                  capF19131(494),
                  capF19130(495),
                  capF19128(496),
                  capF19127(497),
                  capF19126(498),
                  capF19125(499),
                  capNotDefined(500),
                  capG1490(501),
                  capF19123(502),
                  capF19122(503),
                  capF19121(504),
                  capF19608(505),
                  capF19607(506),
                  capF19606(507),
                  capF19603(509),
                  capF19602(510),
                  capF19601(511),
                  capSystemSelect(512)
                }

FspR7ChannelNumber ::= TEXTUAL-CONVENTION
  STATUS        current
  DESCRIPTION
         "CWDM channels; DWDM frequencies (50 GHz grid according ITU-T" 
  SYNTAX        INTEGER
                {
                  undefined(0),
                  f19600(1),  --196,00THz 1529,55nm D01
                  f19590(2),  --195,90THz 1530,33nm D02
                  f19580(3),  --195,80THz 1531,12nm D03
                  f19570(4),  --195,70THz 1531,90nm D04
                  f19550(5),  --195,50THz 1533,47nm D05
                  f19540(6),  --195,40THz 1534,25nm D06
                  f19530(7),  --195,30THz 1535,04nm D07
                  f19520(8),  --195,20THz 1535,82nm D08
                  f19500(9),  --195,00THz 1537,40nm D09
                  f19490(10),  --194,90THz 1538,19nm D10
                  f19480(11),  --194,80THz 1538,98nm D11
                  f19470(12),  --194,70THz 1539,77nm D12
                  f19450(13),  --194,50THz 1541,35nm D13
                  f19440(14),  --194,40THz 1542,14nm D14
                  f19430(15),  --194,30THz 1542,94nm D15
                  f19420(16),  --194,20THz 1543,73nm D16
                  f19380(17),  --193,80THz 1546,92nm D17
                  f19370(18),  --193,70THz 1547,72nm D18
                  f19360(19),  --193,60THz 1548,51nm D19
                  f19350(20),  --193,50THz 1549,32nm D20
                  f19330(21),  --193,30THz 1550,92nm D21
                  f19320(22),  --193,20THz 1551,72nm D22
                  f19310(23),  --193,10THz 1552,52nm D23
                  f19300(24),  --193,00THz 1553,33nm D24
                  f19280(25),  --192,80THz 1554,94nm D25
                  f19270(26),  --192,70THz 1555,75nm D26
                  f19260(27),  --192,60THz 1556,55nm D27
                  f19250(28),  --192,50THz 1557,36nm D28
                  f19230(29),  --192,30THz 1558,98nm D29
                  f19220(30),  --192,20THz 1559,79nm D30
                  f19210(31),  --192,10THz 1560,61nm D31
                  f19200(32),  --192,00THz 1561,42nm D32
                  f19100(33),  --191,00THz 1569,59nm D33
                  f19090(34),  --190,90THz 1570,42nm D34
                  f19080(35),  --190,80THz 1571,24nm D35
                  f19070(36),  --190,70THz 1572,06nm D36
                  f19050(37),  --190,50THz 1573,71nm D37
                  f19040(38),  --190,40THz 1574,54nm D38
                  f19030(39),  --190,30THz 1575,37nm D39
                  f19020(40),  --190,20THz 1576,20nm D40
                  f19000(41),  --190,00THz 1577,86nm D41
                  f18990(42),  --189,90THz 1578,69nm D42
                  f18980(43),  --189,80THz 1579,52nm D43
                  f18970(44),  --189,70THz 1580,35nm D44
                  f18950(45),  --189,50THz 1582,02nm D45
                  f18940(46),  --189,40THz 1582,85nm D46
                  f18930(47),  --189,30THz 1583,69nm D47
                  f18920(48),  --189,20THz 1584,53nm D48
                  f18880(49),  --188,80THz 1587,88nm D49
                  f18870(50),  --188,70THz 1588,73nm D50
                  f18860(51),  --188,60THz 1589,57nm D51
                  f18850(52),  --188,50THz 1590,41nm D52
                  f18830(53),  --188,30THz 1592,10nm D53
                  f18820(54),  --188,20THz 1592,95nm D54
                  f18810(55),  --188,10THz 1593,79nm D55
                  f18800(56),  --188,00THz 1594,64nm D56
                  f18780(57),  --187,80THz 1596,34nm D57
                  f18770(58),  --187,70THz 1597,19nm D58
                  f18760(59),  --187,60THz 1598,04nm D59
                  f18750(60),  --187,50THz 1598,89nm D60
                  f18730(61),  --187,30THz 1600,60nm D61
                  f18720(62),  --187,20THz 1601,56nm D62
                  f18710(63),  --187,10THz 1602,31nm D63
                  f18700(64),  --187,00THz 1603,17nm D64
                  f19560(65),  --195,60THz 1532,68nm DC1
                  f19510(66),  --195,10THz 1536,61nm DC2
                  f19460(67),  --194,60THz 1540,56nm DC3
                  f19410(68),  --194,10THz 1544,53nm DC4
                  f19390(69),  --193,90THz 1546,12nm DC5
                  f19340(70),  --193,40THz 1550,12nm DC6
                  f19290(71),  --192,90THz 1554,13nm DC7
                  f19240(72),  --192,40THz 1558,17nm DC8
                  f19060(73),  --190,60THz 1572,89nm DL1
                  f19010(74),  --190,10THz 1577,03nm DL2
                  f18960(75),  --189,60THz 1581,18nm DL3
                  f18910(76),  --189,10THz 1585,36nm DL4
                  f18890(77),  --188,90THz 1587,04nm DL5
                  f18840(78),  --188,40THz 1591,26nm DL6
                  f18790(79),  --187,90THz 1595,49nm DL7
                  f18740(80),  --187,40THz 1599,75nm DL8
                  f19400(81),  --194,00THz 1545,322nm DC9
                  f18900(82),  --189,00THz 1586,203nm DL9
                  f19640(83),  --196.40THz 1526.44nm
                  f19635(84),  --196.35THz 1526.83nm
                  f19630(85),  --196.30THz 1527.22nm
                  f19625(86),  --196.25THz 1527.60nm
                  f19620(87),  --196.20THz 1527.99nm
                  f19615(88),  --196.15THz 1528.38nm
                  f19605(89),  --196.05THz 1529.16nm
                  c1470(90),  --1470,00nm
                  c1490(91),  --1490,00nm
                  c1510(92),  --1510,00nm
                  c1530(93),  --1530,00nm
                  c1550(94),  --1550,00nm
                  c1570(95),  --1570,00nm
                  c1590(96),  --1590,00nm
                  c1610(97),  --1610,00nm
                  s1310(98),  --1310,00nm
                  s1630(99),  --1630,00nm
                  g850(100),  --850,00nm
                  g1310(101),  --1310,00nm
                  g1550(102),  --1550,00nm
                  null(103),
                  nig(104),
                  s1510(105),  --1510,00nm
                  f19610(106),  --196,10THz  1528,7734nm
                  f19595(107),  --195,95THz  1529,9436nm
                  f19585(108),  --195,85THz  1530,7248nm
                  f19575(109),  --195,75THz  1531,5068nm
                  f19565(110),  --195,65THz  1532,2896nm
                  f19555(111),  --195,55THz  1533,0732nm
                  f19545(112),  --195,45THz  1533,8575nm
                  f19535(113),  --195,35THz  1534,6427nm
                  f19525(114),  --195,25THz  1535,4287nm
                  f19515(115),  --195,15THz  1536,2155nm
                  f19505(116),  --195,05THz  1537,0031nm
                  f19495(117),  --194,95THz  1537,7915nm
                  f19485(118),  --194,85THz  1538,5807nm
                  f19475(119),  --194,75THz  1539,3708nm
                  f19465(120),  --194,65THz  1540,1616nm
                  f19455(121),  --194,55THz  1540,9533nm
                  f19445(122),  --194,45THz  1541,7457nm
                  f19435(123),  --194,35THz  1542,5390nm
                  f19425(124),  --194,25THz  1543,3331nm
                  f19415(125),  --194,15THz  1544,1280nm
                  f19405(126),  --194,05THz  1544,9238nm
                  f19395(127),  --193,95THz  1545,7203nm
                  f19385(128),  --193,85THz  1546,5177nm
                  f19375(129),  --193,75THz  1547,3159nm
                  f19365(130),  --193,65THz  1548,1149nm
                  f19355(131),  --193,55THz  1548,9148nm
                  f19345(132),  --193,45THz  1549,7155nm
                  f19335(133),  --193,35THz  1550,5170nm
                  f19325(134),  --193,25THz  1551,3193nm
                  f19315(135),  --193,15THz  1552,1225nm
                  f19305(136),  --193,05THz  1552,9265nm
                  f19295(137),  --192,95THz  1553,7313nm
                  f19285(138),  --192,85THz  1554,5370nm
                  f19275(139),  --192,75THz  1555,3435nm
                  f19265(140),  --192,65THz  1556,1508nm
                  f19255(141),  --192,55THz  1556,9590nm
                  f19245(142),  --192,45THz  1557,7680nm
                  f19235(143),  --192,35THz  1558,5779nm
                  f19225(144),  --192,25THz  1559,3886nm
                  f19215(145),  --192,15THz  1560,2001nm
                  f19205(146),  --192,05THz  1561,0125nm
                  f19195(147),  --191.95THz 1561.83nm
                  f19190(148),  --191.90THz 1562.23nm
                  f19185(149),  --191.85THz 1562.64nm
                  f19180(150),  --191.80THz 1563.05nm
                  f19175(151),  --191.75THz 1563.45nm
                  f19170(152),  --191.70THz 1563.86nm
                  f19165(153),  --191.65THz 1564.27nm
                  f19160(154),  --191.60THz 1564.68nm
                  f19155(155),  --191.55THz 1565.09nm
                  f19150(156),  --191.50THz 1565.50nm
                  f19145(157),  --191.45THz 1565.90nm
                  f19140(158),  --191.40THz 1566.31nm
                  f19135(159),  --191.35THz 1566.72nm
                  f19130(160),  --191.30THz 1567.13nm
                  f19125(161),  --191.25THz 1567.54nm
                  f19120(162),  --191.20THz 1567.95nm
                  f19115(163),  --191.15THz 1568.36nm
                  f19110(164),  --191.10THz 1568.77nm
                  f19105(165),  --191.05THz 1569.18nm
                  f19095(166),  --190.95THz 1570.00nm
                  f19085(167),  --190.85THz 1570.83nm
                  f19075(168),  --190.75THz 1571.65nm
                  f19065(169),  --190.65THz 1572.48nm
                  f19055(170),  --190.55THz 1573.30nm
                  f19045(171),  --190.45THz 1574.13nm
                  f19035(172),  --190.35THz 1574.95nm
                  f19025(173),  --190.25THz 1575.78nm
                  f19015(174),  --190.15THz 1576.61nm
                  f19005(175),  --190.05THz 1577.44nm
                  f18995(176),  --189.95THz 1578.27nm
                  f18985(177),  --189.85THz 1579.10nm
                  f18975(178),  --189.75THz 1579.93nm
                  f18965(179),  --189.65THz 1580.77nm
                  f18955(180),  --189.55THz 1581.60nm
                  f18945(181),  --189.45THz 1582.44nm
                  f18935(182),  --189.35THz 1583.27nm
                  f18925(183),  --189.25THz 1584.11nm
                  f18915(184),  --189.15THz 1584.95nm
                  f18905(185),  --189.05THz 1585.78nm
                  f18895(186),  --188.95THz 1586.62nm
                  f18885(187),  --188.85THz 1587.46nm
                  f18875(188),  --188.75THz 1588.30nm
                  f18865(189),  --188.65THz 1589.15nm
                  f18855(190),  --188.55THz 1589.99nm
                  f18845(191),  --188.45THz 1590.83nm
                  f18835(192),  --188.35THz 1591.68nm
                  f18825(193),  --188.25THz 1592.52nm
                  f18815(194),  --188.15THz 1593.37nm
                  f18805(195),  --188.05THz 1594.22nm
                  f18795(196),  --187.95THz 1595.06nm
                  f18785(197),  --187.85THz 1595.91nm
                  f18775(198),  --187.75THz 1596.76nm
                  f18765(199),  --187.65THz 1597.61nm
                  f18755(200),  --187.55THz 1598.47nm
                  f18745(201),  --187.45THz 1599.32nm
                  f18735(202),  --187.35THz 1600.17nm
                  f18725(203),  --187.25THz 1601.03nm
                  f18715(204),  --187.15THz 1601.88nm
                  f18705(205),  --187.05THz 1602.74nm
                  c1270(206),  --1270,00nm
                  c1290(207),  --1290,00nm
                  c1310(208),  --1310,00nm
                  c1330(209),  --1330,00nm
                  c1350(210),  --1350,00nm
                  c1370(211),  --1370,00nm
                  c1430(212),  --1430,00nm
                  c1450(213),  --1450,00nm
                  t1650(214),  --1650,00nm OTDR
                  s1490(215),  --1490,00nm OSC
                  s1610(216),  --1610,00nm OSC
                  f19598(217),  --195.9875THz , 1529.6509nm
                  f19597(218),  --195.975THz , 1529.7485nm
                  f19596(219),  --195.9625THz , 1529.8461nm
                  f19593(220),  --195.9375THz , 1530.0413nm
                  f19592(221),  --195.925THz , 1530.1389nm
                  f19591(222),  --195.9125THz , 1530.2365nm
                  f19588(223),  --195.8875THz , 1530.4318nm
                  f19587(224),  --195.875THz , 1530.5295nm
                  f19586(225),  --195.8625THz , 1530.6271nm
                  f19583(226),  --195.8375THz , 1530.8225nm
                  f19582(227),  --195.825THz , 1530.9203nm
                  f19581(228),  --195.8125THz , 1531.018nm
                  f19578(229),  --195.7875THz , 1531.2135nm
                  f19577(230),  --195.775THz , 1531.3112nm
                  f19576(231),  --195.7625THz , 1531.409nm
                  f19573(232),  --195.7375THz , 1531.6046nm
                  f19572(233),  --195.725THz , 1531.7024nm
                  f19571(234),  --195.7125THz , 1531.8003nm
                  f19568(235),  --195.6875THz , 1531.996nm
                  f19567(236),  --195.675THz , 1532.0938nm
                  f19566(237),  --195.6625THz , 1532.1917nm
                  f19563(238),  --195.6375THz , 1532.3875nm
                  f19562(239),  --195.625THz , 1532.4854nm
                  f19561(240),  --195.6125THz , 1532.5833nm
                  f19558(241),  --195.5875THz , 1532.7792nm
                  f19557(242),  --195.575THz , 1532.8772nm
                  f19556(243),  --195.5625THz , 1532.9752nm
                  f19553(244),  --195.5375THz , 1533.1712nm
                  f19552(245),  --195.525THz , 1533.2692nm
                  f19551(246),  --195.5125THz , 1533.3672nm
                  f19548(247),  --195.4875THz , 1533.5633nm
                  f19547(248),  --195.475THz , 1533.6614nm
                  f19546(249),  --195.4625THz , 1533.7595nm
                  f19543(250),  --195.4375THz , 1533.9557nm
                  f19542(251),  --195.425THz , 1534.0538nm
                  f19541(252),  --195.4125THz , 1534.1519nm
                  f19538(253),  --195.3875THz , 1534.3482nm
                  f19537(254),  --195.375THz , 1534.4464nm
                  f19536(255),  --195.3625THz , 1534.5445nm
                  f19533(256),  --195.3375THz , 1534.7409nm
                  f19532(257),  --195.325THz , 1534.8392nm
                  f19531(258),  --195.3125THz , 1534.9374nm
                  f19528(259),  --195.2875THz , 1535.1339nm
                  f19527(260),  --195.275THz , 1535.2321nm
                  f19526(261),  --195.2625THz , 1535.3304nm
                  f19523(262),  --195.2375THz , 1535.527nm
                  f19522(263),  --195.225THz , 1535.6253nm
                  f19521(264),  --195.2125THz , 1535.7237nm
                  f19518(265),  --195.1875THz , 1535.9204nm
                  f19517(266),  --195.175THz , 1536.0187nm
                  f19516(267),  --195.1625THz , 1536.1171nm
                  f19513(268),  --195.1375THz , 1536.3139nm
                  f19512(269),  --195.125THz , 1536.4123nm
                  f19511(270),  --195.1125THz , 1536.5108nm
                  f19508(271),  --195.0875THz , 1536.7077nm
                  f19507(272),  --195.075THz , 1536.8061nm
                  f19506(273),  --195.0625THz , 1536.9046nm
                  f19503(274),  --195.0375THz , 1537.1016nm
                  f19502(275),  --195.025THz , 1537.2001nm
                  f19501(276),  --195.0125THz , 1537.2987nm
                  f19498(277),  --194.9875THz , 1537.4958nm
                  f19497(278),  --194.975THz , 1537.5943nm
                  f19496(279),  --194.9625THz , 1537.6929nm
                  f19493(280),  --194.9375THz , 1537.8901nm
                  f19492(281),  --194.925THz , 1537.9888nm
                  f19491(282),  --194.9125THz , 1538.0874nm
                  f19488(283),  --194.8875THz , 1538.2847nm
                  f19487(284),  --194.875THz , 1538.3834nm
                  f19486(285),  --194.8625THz , 1538.482nm
                  f19483(286),  --194.8375THz , 1538.6795nm
                  f19482(287),  --194.825THz , 1538.7782nm
                  f19481(288),  --194.8125THz , 1538.8769nm
                  f19478(289),  --194.7875THz , 1539.0744nm
                  f19477(290),  --194.775THz , 1539.1732nm
                  f19476(291),  --194.7625THz , 1539.272nm
                  f19473(292),  --194.7375THz , 1539.4696nm
                  f19472(293),  --194.725THz , 1539.5684nm
                  f19471(294),  --194.7125THz , 1539.6672nm
                  f19468(295),  --194.6875THz , 1539.865nm
                  f19467(296),  --194.675THz , 1539.9638nm
                  f19466(297),  --194.6625THz , 1540.0627nm
                  f19463(298),  --194.6375THz , 1540.2605nm
                  f19462(299),  --194.625THz , 1540.3595nm
                  f19461(300),  --194.6125THz , 1540.4584nm
                  f19458(301),  --194.5875THz , 1540.6563nm
                  f19457(302),  --194.575THz , 1540.7553nm
                  f19456(303),  --194.5625THz , 1540.8543nm
                  f19453(304),  --194.5375THz , 1541.0523nm
                  f19452(305),  --194.525THz , 1541.1513nm
                  f19451(306),  --194.5125THz , 1541.2503nm
                  f19448(307),  --194.4875THz , 1541.4485nm
                  f19447(308),  --194.475THz , 1541.5475nm
                  f19446(309),  --194.4625THz , 1541.6466nm
                  f19443(310),  --194.4375THz , 1541.8448nm
                  f19442(311),  --194.425THz , 1541.944nm
                  f19441(312),  --194.4125THz , 1542.0431nm
                  f19438(313),  --194.3875THz , 1542.2414nm
                  f19437(314),  --194.375THz , 1542.3406nm
                  f19436(315),  --194.3625THz , 1542.4398nm
                  f19433(316),  --194.3375THz , 1542.6382nm
                  f19432(317),  --194.325THz , 1542.7375nm
                  f19431(318),  --194.3125THz , 1542.8367nm
                  f19428(319),  --194.2875THz , 1543.0352nm
                  f19427(320),  --194.275THz , 1543.1345nm
                  f19426(321),  --194.2625THz , 1543.2338nm
                  f19423(322),  --194.2375THz , 1543.4324nm
                  f19422(323),  --194.225THz , 1543.5318nm
                  f19421(324),  --194.2125THz , 1543.6311nm
                  f19418(325),  --194.1875THz , 1543.8298nm
                  f19417(326),  --194.175THz , 1543.9292nm
                  f19416(327),  --194.1625THz , 1544.0286nm
                  f19413(328),  --194.1375THz , 1544.2275nm
                  f19412(329),  --194.125THz , 1544.3269nm
                  f19411(330),  --194.1125THz , 1544.4263nm
                  f19408(331),  --194.0875THz , 1544.6253nm
                  f19407(332),  --194.075THz , 1544.7248nm
                  f19406(333),  --194.0625THz , 1544.8243nm
                  f19403(334),  --194.0375THz , 1545.0233nm
                  f19402(335),  --194.025THz , 1545.1228nm
                  f19401(336),  --194.0125THz , 1545.2224nm
                  f19398(337),  --193.9875THz , 1545.4215nm
                  f19397(338),  --193.975THz , 1545.5211nm
                  f19396(339),  --193.9625THz , 1545.6207nm
                  f19393(340),  --193.9375THz , 1545.82nm
                  f19392(341),  --193.925THz , 1545.9196nm
                  f19391(342),  --193.9125THz , 1546.0193nm
                  f19388(343),  --193.8875THz , 1546.2186nm
                  f19387(344),  --193.875THz , 1546.3183nm
                  f19386(345),  --193.8625THz , 1546.418nm
                  f19383(346),  --193.8375THz , 1546.6174nm
                  f19382(347),  --193.825THz , 1546.7172nm
                  f19381(348),  --193.8125THz , 1546.8169nm
                  f19378(349),  --193.7875THz , 1547.0165nm
                  f19377(350),  --193.775THz , 1547.1163nm
                  f19376(351),  --193.7625THz , 1547.2161nm
                  f19373(352),  --193.7375THz , 1547.4157nm
                  f19372(353),  --193.725THz , 1547.5156nm
                  f19371(354),  --193.7125THz , 1547.6155nm
                  f19368(355),  --193.6875THz , 1547.8152nm
                  f19367(356),  --193.675THz , 1547.9151nm
                  f19366(357),  --193.6625THz , 1548.015nm
                  f19363(358),  --193.6375THz , 1548.2149nm
                  f19362(359),  --193.625THz , 1548.3148nm
                  f19361(360),  --193.6125THz , 1548.4148nm
                  f19358(361),  --193.5875THz , 1548.6148nm
                  f19357(362),  --193.575THz , 1548.7148nm
                  f19356(363),  --193.5625THz , 1548.8148nm
                  f19353(364),  --193.5375THz , 1549.0148nm
                  f19352(365),  --193.525THz , 1549.1149nm
                  f19351(366),  --193.5125THz , 1549.2149nm
                  f19348(367),  --193.4875THz , 1549.4151nm
                  f19347(368),  --193.475THz , 1549.5152nm
                  f19346(369),  --193.4625THz , 1549.6153nm
                  f19343(370),  --193.4375THz , 1549.8156nm
                  f19342(371),  --193.425THz , 1549.9158nm
                  f19341(372),  --193.4125THz , 1550.0159nm
                  f19338(373),  --193.3875THz , 1550.2163nm
                  f19337(374),  --193.375THz , 1550.3165nm
                  f19336(375),  --193.3625THz , 1550.4167nm
                  f19333(376),  --193.3375THz , 1550.6172nm
                  f19332(377),  --193.325THz , 1550.7175nm
                  f19331(378),  --193.3125THz , 1550.8178nm
                  f19328(379),  --193.2875THz , 1551.0183nm
                  f19327(380),  --193.275THz , 1551.1187nm
                  f19326(381),  --193.2625THz , 1551.219nm
                  f19323(382),  --193.2375THz , 1551.4197nm
                  f19322(383),  --193.225THz , 1551.52nm
                  f19321(384),  --193.2125THz , 1551.6204nm
                  f19318(385),  --193.1875THz , 1551.8212nm
                  f19317(386),  --193.175THz , 1551.9216nm
                  f19316(387),  --193.1625THz , 1552.022nm
                  f19313(388),  --193.1375THz , 1552.2229nm
                  f19312(389),  --193.125THz , 1552.3234nm
                  f19311(390),  --193.1125THz , 1552.4239nm
                  f19308(391),  --193.0875THz , 1552.6249nm
                  f19307(392),  --193.075THz , 1552.7254nm
                  f19306(393),  --193.0625THz , 1552.8259nm
                  f19303(394),  --193.0375THz , 1553.027nm
                  f19302(395),  --193.025THz , 1553.1276nm
                  f19301(396),  --193.0125THz , 1553.2282nm
                  f19298(397),  --192.9875THz , 1553.4294nm
                  f19297(398),  --192.975THz , 1553.53nm
                  f19296(399),  --192.9625THz , 1553.6307nm
                  f19293(400),  --192.9375THz , 1553.832nm
                  f19292(401),  --192.925THz , 1553.9327nm
                  f19291(402),  --192.9125THz , 1554.0333nm
                  f19288(403),  --192.8875THz , 1554.2348nm
                  f19287(404),  --192.875THz , 1554.3355nm
                  f19286(405),  --192.8625THz , 1554.4362nm
                  f19283(406),  --192.8375THz , 1554.6378nm
                  f19282(407),  --192.825THz , 1554.7385nm
                  f19281(408),  --192.8125THz , 1554.8393nm
                  f19278(409),  --192.7875THz , 1555.041nm
                  f19277(410),  --192.775THz , 1555.1418nm
                  f19276(411),  --192.7625THz , 1555.2426nm
                  f19273(412),  --192.7375THz , 1555.4444nm
                  f19272(413),  --192.725THz , 1555.5452nm
                  f19271(414),  --192.7125THz , 1555.6461nm
                  f19268(415),  --192.6875THz , 1555.848nm
                  f19267(416),  --192.675THz , 1555.9489nm
                  f19266(417),  --192.6625THz , 1556.0499nm
                  f19263(418),  --192.6375THz , 1556.2518nm
                  f19262(419),  --192.625THz , 1556.3528nm
                  f19261(420),  --192.6125THz , 1556.4538nm
                  f19258(421),  --192.5875THz , 1556.6558nm
                  f19257(422),  --192.575THz , 1556.7569nm
                  f19256(423),  --192.5625THz , 1556.8579nm
                  f19253(424),  --192.5375THz , 1557.0601nm
                  f19252(425),  --192.525THz , 1557.1612nm
                  f19251(426),  --192.5125THz , 1557.2623nm
                  f19248(427),  --192.4875THz , 1557.4646nm
                  f19247(428),  --192.475THz , 1557.5657nm
                  f19246(429),  --192.4625THz , 1557.6669nm
                  f19243(430),  --192.4375THz , 1557.8692nm
                  f19242(431),  --192.425THz , 1557.9704nm
                  f19241(432),  --192.4125THz , 1558.0716nm
                  f19238(433),  --192.3875THz , 1558.2741nm
                  f19237(434),  --192.375THz , 1558.3754nm
                  f19236(435),  --192.3625THz , 1558.4766nm
                  f19233(436),  --192.3375THz , 1558.6792nm
                  f19232(437),  --192.325THz , 1558.7805nm
                  f19231(438),  --192.3125THz , 1558.8818nm
                  f19228(439),  --192.2875THz , 1559.0845nm
                  f19227(440),  --192.275THz , 1559.1858nm
                  f19226(441),  --192.2625THz , 1559.2872nm
                  f19223(442),  --192.2375THz , 1559.49nm
                  f19222(443),  --192.225THz , 1559.5914nm
                  f19221(444),  --192.2125THz , 1559.6928nm
                  f19218(445),  --192.1875THz , 1559.8957nm
                  f19217(446),  --192.175THz , 1559.9972nm
                  f19216(447),  --192.1625THz , 1560.0987nm
                  f19213(448),  --192.1375THz , 1560.3016nm
                  f19212(449),  --192.125THz , 1560.4032nm
                  f19211(450),  --192.1125THz , 1560.5047nm
                  f19208(451),  --192.0875THz , 1560.7078nm
                  f19207(452),  --192.075THz , 1560.8094nm
                  f19206(453),  --192.0625THz , 1560.9109nm
                  f19203(454),  --192.0375THz , 1561.1141nm
                  f19202(455),  --192.025THz , 1561.2158nm
                  f19201(456),  --192.0125THz , 1561.3174nm
                  f19198(457),  --191.9875THz , 1561.5207nm
                  f19197(458),  --191.975THz , 1561.6224nm
                  f19196(459),  --191.9625THz , 1561.7241nm
                  f19193(460),  --191.9375THz , 1561.9275nm
                  f19192(461),  --191.925THz , 1562.0292nm
                  f19191(462),  --191.9125THz , 1562.131nm
                  f19188(463),  --191.8875THz , 1562.3345nm
                  f19187(464),  --191.875THz , 1562.4363nm
                  f19186(465),  --191.8625THz , 1562.5381nm
                  f19183(466),  --191.8375THz , 1562.7417nm
                  f19182(467),  --191.825THz , 1562.8435nm
                  f19181(468),  --191.8125THz , 1562.9454nm
                  f19178(469),  --191.7875THz , 1563.1491nm
                  f19177(470),  --191.775THz , 1563.251nm
                  f19176(471),  --191.7625THz , 1563.3529nm
                  f19173(472),  --191.7375THz , 1563.5567nm
                  f19172(473),  --191.725THz , 1563.6587nm
                  f19171(474),  --191.7125THz , 1563.7606nm
                  f19168(475),  --191.6875THz , 1563.9646nm
                  f19167(476),  --191.675THz , 1564.0666nm
                  f19166(477),  --191.6625THz , 1564.1686nm
                  f19163(478),  --191.6375THz , 1564.3726nm
                  f19162(479),  --191.625THz , 1564.4747nm
                  f19161(480),  --191.6125THz , 1564.5767nm
                  f19158(481),  --191.5875THz , 1564.7809nm
                  f19157(482),  --191.575THz , 1564.883nm
                  f19156(483),  --191.5625THz , 1564.9851nm
                  f19153(484),  --191.5375THz , 1565.1894nm
                  f19152(485),  --191.525THz , 1565.2915nm
                  f19151(486),  --191.5125THz , 1565.3937nm
                  f19148(487),  --191.4875THz , 1565.5981nm
                  f19147(488),  --191.475THz , 1565.7003nm
                  f19146(489),  --191.4625THz , 1565.8025nm
                  f19143(490),  --191.4375THz , 1566.007nm
                  f19142(491),  --191.425THz , 1566.1092nm
                  f19141(492),  --191.4125THz , 1566.2115nm
                  f19138(493),  --191.3875THz , 1566.4161nm
                  f19137(494),  --191.375THz , 1566.5184nm
                  f19136(495),  --191.3625THz , 1566.6207nm
                  f19133(496),  --191.3375THz , 1566.8254nm
                  f19132(497),  --191.325THz , 1566.9278nm
                  f19131(498),  --191.3125THz , 1567.0302nm
                  f19128(499),  --191.2875THz , 1567.235nm
                  f19127(500),  --191.275THz , 1567.3374nm
                  f19126(501),  --191.2625THz , 1567.4398nm
                  g1490(502),  --1490,00nm
                  f19123(503),  --191.2375THz , 1567.6447nm
                  f19122(504),  --191.225THz , 1567.7472nm
                  f19121(505)  --191.2125THz , 1567.8497nm
                }

FspR7ChannelNumberCaps ::= TEXTUAL-CONVENTION
  STATUS        current
  DESCRIPTION
         "CWDM channels; DWDM frequencies (50 GHz grid according ITU-T" 
  SYNTAX        BITS
                {
                  capUndefined(0),
                  capF19600(1),
                  capF19590(2),
                  capF19580(3),
                  capF19570(4),
                  capF19550(5),
                  capF19540(6),
                  capF19530(7),
                  capF19520(8),
                  capF19500(9),
                  capF19490(10),
                  capF19480(11),
                  capF19470(12),
                  capF19450(13),
                  capF19440(14),
                  capF19430(15),
                  capF19420(16),
                  capF19380(17),
                  capF19370(18),
                  capF19360(19),
                  capF19350(20),
                  capF19330(21),
                  capF19320(22),
                  capF19310(23),
                  capF19300(24),
                  capF19280(25),
                  capF19270(26),
                  capF19260(27),
                  capF19250(28),
                  capF19230(29),
                  capF19220(30),
                  capF19210(31),
                  capF19200(32),
                  capF19100(33),
                  capF19090(34),
                  capF19080(35),
                  capF19070(36),
                  capF19050(37),
                  capF19040(38),
                  capF19030(39),
                  capF19020(40),
                  capF19000(41),
                  capF18990(42),
                  capF18980(43),
                  capF18970(44),
                  capF18950(45),
                  capF18940(46),
                  capF18930(47),
                  capF18920(48),
                  capF18880(49),
                  capF18870(50),
                  capF18860(51),
                  capF18850(52),
                  capF18830(53),
                  capF18820(54),
                  capF18810(55),
                  capF18800(56),
                  capF18780(57),
                  capF18770(58),
                  capF18760(59),
                  capF18750(60),
                  capF18730(61),
                  capF18720(62),
                  capF18710(63),
                  capF18700(64),
                  capF19560(65),
                  capF19510(66),
                  capF19460(67),
                  capF19410(68),
                  capF19390(69),
                  capF19340(70),
                  capF19290(71),
                  capF19240(72),
                  capF19060(73),
                  capF19010(74),
                  capF18960(75),
                  capF18910(76),
                  capF18890(77),
                  capF18840(78),
                  capF18790(79),
                  capF18740(80),
                  capF19400(81),
                  capF18900(82),
                  capF19640(83),
                  capF19635(84),
                  capF19630(85),
                  capF19625(86),
                  capF19620(87),
                  capF19615(88),
                  capF19605(89),
                  capC1470(90),
                  capC1490(91),
                  capC1510(92),
                  capC1530(93),
                  capC1550(94),
                  capC1570(95),
                  capC1590(96),
                  capC1610(97),
                  capS1310(98),
                  capS1630(99),
                  capG850(100),
                  capG1310(101),
                  capG1550(102),
                  capNull(103),
                  capNig(104),
                  capS1510(105),
                  capF19610(106),
                  capF19595(107),
                  capF19585(108),
                  capF19575(109),
                  capF19565(110),
                  capF19555(111),
                  capF19545(112),
                  capF19535(113),
                  capF19525(114),
                  capF19515(115),
                  capF19505(116),
                  capF19495(117),
                  capF19485(118),
                  capF19475(119),
                  capF19465(120),
                  capF19455(121),
                  capF19445(122),
                  capF19435(123),
                  capF19425(124),
                  capF19415(125),
                  capF19405(126),
                  capF19395(127),
                  capF19385(128),
                  capF19375(129),
                  capF19365(130),
                  capF19355(131),
                  capF19345(132),
                  capF19335(133),
                  capF19325(134),
                  capF19315(135),
                  capF19305(136),
                  capF19295(137),
                  capF19285(138),
                  capF19275(139),
                  capF19265(140),
                  capF19255(141),
                  capF19245(142),
                  capF19235(143),
                  capF19225(144),
                  capF19215(145),
                  capF19205(146),
                  capF19195(147),
                  capF19190(148),
                  capF19185(149),
                  capF19180(150),
                  capF19175(151),
                  capF19170(152),
                  capF19165(153),
                  capF19160(154),
                  capF19155(155),
                  capF19150(156),
                  capF19145(157),
                  capF19140(158),
                  capF19135(159),
                  capF19130(160),
                  capF19125(161),
                  capF19120(162),
                  capF19115(163),
                  capF19110(164),
                  capF19105(165),
                  capF19095(166),
                  capF19085(167),
                  capF19075(168),
                  capF19065(169),
                  capF19055(170),
                  capF19045(171),
                  capF19035(172),
                  capF19025(173),
                  capF19015(174),
                  capF19005(175),
                  capF18995(176),
                  capF18985(177),
                  capF18975(178),
                  capF18965(179),
                  capF18955(180),
                  capF18945(181),
                  capF18935(182),
                  capF18925(183),
                  capF18915(184),
                  capF18905(185),
                  capF18895(186),
                  capF18885(187),
                  capF18875(188),
                  capF18865(189),
                  capF18855(190),
                  capF18845(191),
                  capF18835(192),
                  capF18825(193),
                  capF18815(194),
                  capF18805(195),
                  capF18795(196),
                  capF18785(197),
                  capF18775(198),
                  capF18765(199),
                  capF18755(200),
                  capF18745(201),
                  capF18735(202),
                  capF18725(203),
                  capF18715(204),
                  capF18705(205),
                  capC1270(206),
                  capC1290(207),
                  capC1310(208),
                  capC1330(209),
                  capC1350(210),
                  capC1370(211),
                  capC1430(212),
                  capC1450(213),
                  capT1650(214),
                  capS1490(215),
                  capS1610(216),
                  capF19598(217),
                  capF19597(218),
                  capF19596(219),
                  capF19593(220),
                  capF19592(221),
                  capF19591(222),
                  capF19588(223),
                  capF19587(224),
                  capF19586(225),
                  capF19583(226),
                  capF19582(227),
                  capF19581(228),
                  capF19578(229),
                  capF19577(230),
                  capF19576(231),
                  capF19573(232),
                  capF19572(233),
                  capF19571(234),
                  capF19568(235),
                  capF19567(236),
                  capF19566(237),
                  capF19563(238),
                  capF19562(239),
                  capF19561(240),
                  capF19558(241),
                  capF19557(242),
                  capF19556(243),
                  capF19553(244),
                  capF19552(245),
                  capF19551(246),
                  capF19548(247),
                  capF19547(248),
                  capF19546(249),
                  capF19543(250),
                  capF19542(251),
                  capF19541(252),
                  capF19538(253),
                  capF19537(254),
                  capF19536(255),
                  capF19533(256),
                  capF19532(257),
                  capF19531(258),
                  capF19528(259),
                  capF19527(260),
                  capF19526(261),
                  capF19523(262),
                  capF19522(263),
                  capF19521(264),
                  capF19518(265),
                  capF19517(266),
                  capF19516(267),
                  capF19513(268),
                  capF19512(269),
                  capF19511(270),
                  capF19508(271),
                  capF19507(272),
                  capF19506(273),
                  capF19503(274),
                  capF19502(275),
                  capF19501(276),
                  capF19498(277),
                  capF19497(278),
                  capF19496(279),
                  capF19493(280),
                  capF19492(281),
                  capF19491(282),
                  capF19488(283),
                  capF19487(284),
                  capF19486(285),
                  capF19483(286),
                  capF19482(287),
                  capF19481(288),
                  capF19478(289),
                  capF19477(290),
                  capF19476(291),
                  capF19473(292),
                  capF19472(293),
                  capF19471(294),
                  capF19468(295),
                  capF19467(296),
                  capF19466(297),
                  capF19463(298),
                  capF19462(299),
                  capF19461(300),
                  capF19458(301),
                  capF19457(302),
                  capF19456(303),
                  capF19453(304),
                  capF19452(305),
                  capF19451(306),
                  capF19448(307),
                  capF19447(308),
                  capF19446(309),
                  capF19443(310),
                  capF19442(311),
                  capF19441(312),
                  capF19438(313),
                  capF19437(314),
                  capF19436(315),
                  capF19433(316),
                  capF19432(317),
                  capF19431(318),
                  capF19428(319),
                  capF19427(320),
                  capF19426(321),
                  capF19423(322),
                  capF19422(323),
                  capF19421(324),
                  capF19418(325),
                  capF19417(326),
                  capF19416(327),
                  capF19413(328),
                  capF19412(329),
                  capF19411(330),
                  capF19408(331),
                  capF19407(332),
                  capF19406(333),
                  capF19403(334),
                  capF19402(335),
                  capF19401(336),
                  capF19398(337),
                  capF19397(338),
                  capF19396(339),
                  capF19393(340),
                  capF19392(341),
                  capF19391(342),
                  capF19388(343),
                  capF19387(344),
                  capF19386(345),
                  capF19383(346),
                  capF19382(347),
                  capF19381(348),
                  capF19378(349),
                  capF19377(350),
                  capF19376(351),
                  capF19373(352),
                  capF19372(353),
                  capF19371(354),
                  capF19368(355),
                  capF19367(356),
                  capF19366(357),
                  capF19363(358),
                  capF19362(359),
                  capF19361(360),
                  capF19358(361),
                  capF19357(362),
                  capF19356(363),
                  capF19353(364),
                  capF19352(365),
                  capF19351(366),
                  capF19348(367),
                  capF19347(368),
                  capF19346(369),
                  capF19343(370),
                  capF19342(371),
                  capF19341(372),
                  capF19338(373),
                  capF19337(374),
                  capF19336(375),
                  capF19333(376),
                  capF19332(377),
                  capF19331(378),
                  capF19328(379),
                  capF19327(380),
                  capF19326(381),
                  capF19323(382),
                  capF19322(383),
                  capF19321(384),
                  capF19318(385),
                  capF19317(386),
                  capF19316(387),
                  capF19313(388),
                  capF19312(389),
                  capF19311(390),
                  capF19308(391),
                  capF19307(392),
                  capF19306(393),
                  capF19303(394),
                  capF19302(395),
                  capF19301(396),
                  capF19298(397),
                  capF19297(398),
                  capF19296(399),
                  capF19293(400),
                  capF19292(401),
                  capF19291(402),
                  capF19288(403),
                  capF19287(404),
                  capF19286(405),
                  capF19283(406),
                  capF19282(407),
                  capF19281(408),
                  capF19278(409),
                  capF19277(410),
                  capF19276(411),
                  capF19273(412),
                  capF19272(413),
                  capF19271(414),
                  capF19268(415),
                  capF19267(416),
                  capF19266(417),
                  capF19263(418),
                  capF19262(419),
                  capF19261(420),
                  capF19258(421),
                  capF19257(422),
                  capF19256(423),
                  capF19253(424),
                  capF19252(425),
                  capF19251(426),
                  capF19248(427),
                  capF19247(428),
                  capF19246(429),
                  capF19243(430),
                  capF19242(431),
                  capF19241(432),
                  capF19238(433),
                  capF19237(434),
                  capF19236(435),
                  capF19233(436),
                  capF19232(437),
                  capF19231(438),
                  capF19228(439),
                  capF19227(440),
                  capF19226(441),
                  capF19223(442),
                  capF19222(443),
                  capF19221(444),
                  capF19218(445),
                  capF19217(446),
                  capF19216(447),
                  capF19213(448),
                  capF19212(449),
                  capF19211(450),
                  capF19208(451),
                  capF19207(452),
                  capF19206(453),
                  capF19203(454),
                  capF19202(455),
                  capF19201(456),
                  capF19198(457),
                  capF19197(458),
                  capF19196(459),
                  capF19193(460),
                  capF19192(461),
                  capF19191(462),
                  capF19188(463),
                  capF19187(464),
                  capF19186(465),
                  capF19183(466),
                  capF19182(467),
                  capF19181(468),
                  capF19178(469),
                  capF19177(470),
                  capF19176(471),
                  capF19173(472),
                  capF19172(473),
                  capF19171(474),
                  capF19168(475),
                  capF19167(476),
                  capF19166(477),
                  capF19163(478),
                  capF19162(479),
                  capF19161(480),
                  capF19158(481),
                  capF19157(482),
                  capF19156(483),
                  capF19153(484),
                  capF19152(485),
                  capF19151(486),
                  capF19148(487),
                  capF19147(488),
                  capF19146(489),
                  capF19143(490),
                  capF19142(491),
                  capF19141(492),
                  capF19138(493),
                  capF19137(494),
                  capF19136(495),
                  capF19133(496),
                  capF19132(497),
                  capF19131(498),
                  capF19128(499),
                  capF19127(500),
                  capF19126(501),
                  capG1490(502),
                  capF19123(503),
                  capF19122(504),
                  capF19121(505)
                }

FspR7ChannelSpacing ::= TEXTUAL-CONVENTION
  STATUS        current
  DESCRIPTION
         "ITU Grid channel spacing" 
  SYNTAX        INTEGER
                {
                  undefined(0),
                  spacing50Ghz(1),
                  spacing100Ghz(2),
                  spacing200Ghz(3),
                  spacing25GHz(4),
                  spacingFlex(5),
                  spacing37GHz5(6)
                }

FspR7ChannelSpacingCaps ::= TEXTUAL-CONVENTION
  STATUS        current
  DESCRIPTION
         "ITU Grid channel spacing" 
  SYNTAX        BITS
                {
                  capUndefined(0),
                  capSpacing50Ghz(1),
                  capSpacing100Ghz(2),
                  capSpacing200Ghz(3),
                  capSpacing25GHz(4),
                  capSpacingFlex(5),
                  capSpacing37GHz5(6)
                }

FspR7CodeGain ::= TEXTUAL-CONVENTION
  STATUS        current
  DESCRIPTION
         "Forward Error Correction Coding gain" 
  SYNTAX        INTEGER
                {
                  undefined(0),
                  high(1),
                  mean(2),
                  low(3)
                }

FspR7CodeGainCaps ::= TEXTUAL-CONVENTION
  STATUS        current
  DESCRIPTION
         "Forward Error Correction Coding gain" 
  SYNTAX        BITS
                {
                  capUndefined(0),
                  capHigh(1),
                  capMean(2),
                  capLow(3)
                }

FspR7CommandModifier ::= TEXTUAL-CONVENTION
  STATUS        current
  DESCRIPTION
         "Command Execution" 
  SYNTAX        INTEGER
                {
                  undefined(0),
                  generic(1),  --Must be combined with ADMIN in one step.
                              --control plane forces new provisioning of data plane entities if ADMIN = IS or
                              --control plane removes the data plane provisioning if ADMIN = PPS
                  adopt(2),  --Must be combined with ADMIN in one step.
                              --control plane adopts current data plane provisioning if ADMIN = IS
                  release(3)  --Must be combined with ADMIN in one step.
                              --control plane releases the data plane provisioning if ADMIN = PPS
                }

FspR7CommandModifierCaps ::= TEXTUAL-CONVENTION
  STATUS        current
  DESCRIPTION
         "Command Execution" 
  SYNTAX        BITS
                {
                  capUndefined(0),
                  capGeneric(1),
                  capAdopt(2),
                  capRelease(3)
                }

FspR7CommunityCmd ::= TEXTUAL-CONVENTION
  STATUS        current
  DESCRIPTION
         "Used while creating or deleting community strings in the system." 
  SYNTAX        INTEGER
                {
                  undefined(0),
                  idle(1),
                  create(2),
                  destroy(3)
                }

FspR7Conn ::= TEXTUAL-CONVENTION
  STATUS        current
  DESCRIPTION
         "Bidirectional | Unidirectional" 
  SYNTAX        INTEGER
                {
                  undefined(0),
                  bi(1),
                  uni(2)
                }

FspR7ConnCaps ::= TEXTUAL-CONVENTION
  STATUS        current
  DESCRIPTION
         "Bidirectional | Unidirectional" 
  SYNTAX        BITS
                {
                  capUndefined(0),
                  capBi(1),
                  capUni(2)
                }

FspR7ConnCommand ::= TEXTUAL-CONVENTION
  STATUS        current
  DESCRIPTION
         "Connection command" 
  SYNTAX        INTEGER
                {
                  undefined(0),
                  none(1),
                  create(2),
                  destroy(3),
                  forceCreate(4),
                  forceDestroy(5)
                }

FspR7ConnectorType ::= TEXTUAL-CONVENTION
  STATUS        current
  DESCRIPTION
         "Connector Type" 
  SYNTAX        INTEGER
                {
                  undefined(0),
                  lc(1),
                  rj45(2),
                  mupc(3),
                  dsub8(4),
                  usbS(5),
                  dsub44hd(6),
                  fcApc(7),
                  mpo(8),  --MPO is the industry acronym for "Multi-Fiber Push On". A MPO Connector type is a Multi-fiber Connector, which is used for high density fiber interconnections.
                  mbnc(9),  --Micro-BNC
                  hdBnc(10),  --HD-BNC
                  din(11),  --DIN 1.0/2.3
                  sc(12),
                  fc(13),
                  dsub26hd(14)
                }

FspR7ConnectorTypeCaps ::= TEXTUAL-CONVENTION
  STATUS        current
  DESCRIPTION
         "Connector Type" 
  SYNTAX        BITS
                {
                  capUndefined(0),
                  capLc(1),
                  capRj45(2),
                  capMupc(3),
                  capDsub8(4),
                  capUsbS(5),
                  capDsub44hd(6),
                  capFcApc(7),
                  capMpo(8),
                  capMbnc(9),
                  capHdBnc(10),
                  capDin(11),
                  capSc(12),
                  capFc(13),
                  capDsub26hd(14)
                }

FspR7ConnectState ::= TEXTUAL-CONVENTION
  STATUS        current
  DESCRIPTION
         "Connection State" 
  SYNTAX        INTEGER
                {
                  undefined(0),
                  idle(1),
                  idleReceive(2),
                  idleTransmit(3),
                  busy(4)
                }

FspR7CpAbortProcess ::= TEXTUAL-CONVENTION
  STATUS        current
  DESCRIPTION
         "Abort process" 
  SYNTAX        INTEGER
                {
                  undefined(0),
                  abt(1)
                }

FspR7CpAbortProcessCaps ::= TEXTUAL-CONVENTION
  STATUS        current
  DESCRIPTION
         "Abort process" 
  SYNTAX        BITS
                {
                  capUndefined(0),
                  capAbt(1)
                }

FspR7CpActivState ::= TEXTUAL-CONVENTION
  STATUS        current
  DESCRIPTION
         "Activation State" 
  SYNTAX        INTEGER
                {
                  undefined(0),
                  inactive(1),
                  activating(2),
                  active(3),
                  deactivating(4),
                  modifying(5),
                  restoring(6),
                  reverting(7)
                }

FspR7CpActivStateCaps ::= TEXTUAL-CONVENTION
  STATUS        current
  DESCRIPTION
         "Activation State" 
  SYNTAX        BITS
                {
                  capUndefined(0),
                  capInactive(1),
                  capActivating(2),
                  capActive(3),
                  capDeactivating(4),
                  capModifying(5),
                  capRestoring(6),
                  capReverting(7)
                }

FspR7CpAffinityInclusion ::= TEXTUAL-CONVENTION
  STATUS        current
  DESCRIPTION
         "Affinity Inclusion" 
  SYNTAX        INTEGER
                {
                  undefined(0),
                  none(1),  --Exclude TE links advertising at least one of the specified affinities
                  any(2),  --Consider only TE links advertising at least one of the specified affinities
                  all(3)  --Consider only TE links advertising all of the specified affinities
                }

FspR7CpAffinityInclusionCaps ::= TEXTUAL-CONVENTION
  STATUS        current
  DESCRIPTION
         "Affinity Inclusion" 
  SYNTAX        BITS
                {
                  capUndefined(0),
                  capNone(1),
                  capAny(2),
                  capAll(3)
                }

FspR7CpAuthType ::= TEXTUAL-CONVENTION
  STATUS        current
  DESCRIPTION
         "OSPF Authentication Type" 
  SYNTAX        INTEGER
                {
                  undefined(0),
                  none(1),
                  simple(2),
                  md5(3)
                }

FspR7CpAuthTypeCaps ::= TEXTUAL-CONVENTION
  STATUS        current
  DESCRIPTION
         "OSPF Authentication Type" 
  SYNTAX        BITS
                {
                  capUndefined(0),
                  capNone(1),
                  capSimple(2),
                  capMd5(3)
                }

FspR7CpCancConnection ::= TEXTUAL-CONVENTION
  STATUS        current
  DESCRIPTION
         "" 
  SYNTAX        INTEGER
                {
                  undefined(0),
                  rls(1),
                  opr(2)
                }

FspR7CpCancConnectionCaps ::= TEXTUAL-CONVENTION
  STATUS        current
  DESCRIPTION
         "" 
  SYNTAX        BITS
                {
                  capUndefined(0),
                  capRls(1),
                  capOpr(2)
                }

FspR7CpCommand ::= TEXTUAL-CONVENTION
  STATUS        current
  DESCRIPTION
         "Controls Tunnel Behavior" 
  SYNTAX        INTEGER
                {
                  undefined(0),
                  none(1),
                  compute(2),
                  abort(3),
                  computePAF(4)
                }

FspR7CpCommandCaps ::= TEXTUAL-CONVENTION
  STATUS        current
  DESCRIPTION
         "Controls Tunnel Behavior" 
  SYNTAX        BITS
                {
                  capUndefined(0),
                  capNone(1),
                  capCompute(2),
                  capAbort(3),
                  capComputePAF(4)
                }

FspR7CpCompState ::= TEXTUAL-CONVENTION
  STATUS        current
  DESCRIPTION
         "Pre-Computation Enumeration State" 
  SYNTAX        INTEGER
                {
                  undefined(0),
                  idle(1),
                  fail(2),
                  inprogs(3),
                  abt(4),
                  compl(5)
                }

FspR7CpCompStateCaps ::= TEXTUAL-CONVENTION
  STATUS        current
  DESCRIPTION
         "Pre-Computation Enumeration State" 
  SYNTAX        BITS
                {
                  capUndefined(0),
                  capIdle(1),
                  capFail(2),
                  capInprogs(3),
                  capAbt(4),
                  capCompl(5)
                }

FspR7CpEncapsulation ::= TEXTUAL-CONVENTION
  STATUS        current
  DESCRIPTION
         "Encapsulation" 
  SYNTAX        INTEGER
                {
                  undefined(0),
                  none(1),
                  ipip(2),
                  greip(3)
                }

FspR7CpEncapsulationCaps ::= TEXTUAL-CONVENTION
  STATUS        current
  DESCRIPTION
         "Encapsulation" 
  SYNTAX        BITS
                {
                  capUndefined(0),
                  capNone(1),
                  capIpip(2),
                  capGreip(3)
                }

FspR7CpEncode ::= TEXTUAL-CONVENTION
  STATUS        current
  DESCRIPTION
         "Encoding" 
  SYNTAX        INTEGER
                {
                  undefined(0),
                  otn(1),
                  sonet(2),
                  sdh(3),
                  eth(4),
                  fc(5),
                  trans(6),
                  cl(7),
                  ib(8),
                  otnp(9),
                  unspecified(10)
                }

FspR7CpEncodeCaps ::= TEXTUAL-CONVENTION
  STATUS        current
  DESCRIPTION
         "Encoding" 
  SYNTAX        BITS
                {
                  capUndefined(0),
                  capOtn(1),
                  capSonet(2),
                  capSdh(3),
                  capEth(4),
                  capFc(5),
                  capTrans(6),
                  capCl(7),
                  capIb(8),
                  capOtnp(9),
                  capUnspecified(10)
                }

FspR7CpErrorCategory ::= TEXTUAL-CONVENTION
  STATUS        current
  DESCRIPTION
         "CP Provisioning Failure Category" 
  SYNTAX        INTEGER
                {
                  undefined(0),
                  success(1),
                  nonOptimal(2),
                  provision(3),
                  pathComputation(4),
                  communicationConnection(5),
                  networkCommunication(6),
                  resourceUnavailable(7),
                  progress(8),
                  noPath(9)
                }

FspR7CpNePosition ::= TEXTUAL-CONVENTION
  STATUS        current
  DESCRIPTION
         "Position of the NE" 
  SYNTAX        INTEGER
                {
                  undefined(0),
                  local(1),
                  ingress(2),
                  egress(3),
                  transit(4)
                }

FspR7CpNodeId ::= TEXTUAL-CONVENTION
  STATUS        current
  DESCRIPTION
         "Node Name Syntax" 
  SYNTAX        INTEGER
                {
                  undefined(0),
                  tid(1),
                  ip(2)
                }

FspR7CpOperateReversion ::= TEXTUAL-CONVENTION
  STATUS        current
  DESCRIPTION
         "Triggers the manual reversion to the nominal connection" 
  SYNTAX        INTEGER
                {
                  undefined(0),
                  release(1),
                  manual(2)
                }

FspR7CpOspfTeRouting ::= TEXTUAL-CONVENTION
  STATUS        current
  DESCRIPTION
         "OSPF-TE Routing (Dynamic)" 
  SYNTAX        INTEGER
                {
                  undefined(0),
                  enable(1),
                  disable(2)
                }

FspR7CpOspfTeRoutingCaps ::= TEXTUAL-CONVENTION
  STATUS        current
  DESCRIPTION
         "OSPF-TE Routing (Dynamic)" 
  SYNTAX        BITS
                {
                  capUndefined(0),
                  capEnable(1),
                  capDisable(2)
                }

FspR7CpPathType ::= TEXTUAL-CONVENTION
  STATUS        current
  DESCRIPTION
         "Path Type" 
  SYNTAX        INTEGER
                {
                  undefined(0),
                  prov(1),
                  sig(2),
                  comp(3)
                }

FspR7CpPinning ::= TEXTUAL-CONVENTION
  STATUS        current
  DESCRIPTION
         "Pinning" 
  SYNTAX        INTEGER
                {
                  undefined(0),
                  yes(1),  --Do not trigger the restoration rerouting for any of GMPLS tunnel LSPs because of data plane alarm(s) detected in the LSPs data plane
                  no(2)  --Trigger the restoration rerouting for a data plane alarmed GMPLS Tunnel LSP if either of the following conditions holds: a) the LSP is unprotected, b) the LSP is protected and a data plane alarm is also detected on the associated protection LSP
                }

FspR7CpPinningCaps ::= TEXTUAL-CONVENTION
  STATUS        current
  DESCRIPTION
         "Pinning" 
  SYNTAX        BITS
                {
                  capUndefined(0),
                  capYes(1),
                  capNo(2)
                }

FspR7CpPreprovUeqState ::= TEXTUAL-CONVENTION
  STATUS        current
  DESCRIPTION
         "Preprovisioned and Unequipped" 
  SYNTAX        INTEGER
                {
                  undefined(0),
                  yes(1),
                  no(2)
                }

FspR7CpPreprovUeqStateCaps ::= TEXTUAL-CONVENTION
  STATUS        current
  DESCRIPTION
         "Preprovisioned and Unequipped" 
  SYNTAX        BITS
                {
                  capUndefined(0),
                  capYes(1),
                  capNo(2)
                }

FspR7CpProtectionType ::= TEXTUAL-CONVENTION
  STATUS        current
  DESCRIPTION
         "Protection Type" 
  SYNTAX        INTEGER
                {
                  undefined(0),
                  none(1),  --No protection attempt is made during tunnel establishment.
                  desired(2),  --A protection attempt is made but tunnel establishment won't fail without.
                  required(3)  --A protection attempt is made and tunnel establishment will fail without.
                }

FspR7CpProtectionTypeCaps ::= TEXTUAL-CONVENTION
  STATUS        current
  DESCRIPTION
         "Protection Type" 
  SYNTAX        BITS
                {
                  capUndefined(0),
                  capNone(1),
                  capDesired(2),
                  capRequired(3)
                }

FspR7CpProtType ::= TEXTUAL-CONVENTION
  STATUS        current
  DESCRIPTION
         "Protection Type" 
  SYNTAX        INTEGER
                {
                  undefined(0),
                  onePlusOne(1),  --Dedicated 1+1 protection
                  oneToOne(2)  --1:1 protection with sharing resources with one extra traffic link/LSP
                }

FspR7CpRestorationState ::= TEXTUAL-CONVENTION
  STATUS        current
  DESCRIPTION
         "Restoration Enumeration State" 
  SYNTAX        INTEGER
                {
                  undefined(0),
                  idle(1),
                  fail(2),
                  inProgress(3),
                  abort(4),
                  completed(5),
                  completedNotReverted(6)
                }

FspR7CpRestorationType ::= TEXTUAL-CONVENTION
  STATUS        current
  DESCRIPTION
         "Restoration Type" 
  SYNTAX        INTEGER
                {
                  undefined(0),
                  none(1),  --No restoration attempt is made on connection failure.
                  primary(2),  --The primary / working connection is restorable.
                  secondary(3),  --The secondary / protection connection is restorable.
                  all(4)  --All connections are restorable.
                }

FspR7CpRestorationTypeCaps ::= TEXTUAL-CONVENTION
  STATUS        current
  DESCRIPTION
         "Restoration Type" 
  SYNTAX        BITS
                {
                  capUndefined(0),
                  capNone(1),
                  capPrimary(2),
                  capSecondary(3),
                  capAll(4)
                }

FspR7CpRestorationMode ::= TEXTUAL-CONVENTION
  STATUS        current
  DESCRIPTION
         "Restoration Mode (replaces pinning)" 
  SYNTAX        INTEGER
                {
                  undefined(0),
                  none(1),  --No restoration at all, replaces pinning=yes
                  dynamic(2),  --The path along which to restore a failed connection is determined dynamically at the time a failure is detected
                  guaranteed(3)  --Connections associated with a Tunnel will be restored along a given path upon detection of a failure
                }

FspR7CpRestorationModeCaps ::= TEXTUAL-CONVENTION
  STATUS        current
  DESCRIPTION
         "Restoration Mode (replaces pinning)" 
  SYNTAX        BITS
                {
                  capUndefined(0),
                  capNone(1),
                  capDynamic(2),
                  capGuaranteed(3)
                }

FspR7CpReversionState ::= TEXTUAL-CONVENTION
  STATUS        current
  DESCRIPTION
         "Enumeration for Reversion States" 
  SYNTAX        INTEGER
                {
                  undefined(0),
                  idle(1),
                  waitToRevert(2),
                  inProgress(3),
                  failed(4)
                }

FspR7CpReversionType ::= TEXTUAL-CONVENTION
  STATUS        current
  DESCRIPTION
         "Manual Reversion, Automatic Reversion, or no reversion at all for tunnels supporting restoration" 
  SYNTAX        INTEGER
                {
                  undefined(0),
                  none(1),
                  manual(2),
                  auto(3)
                }

FspR7CpReversionTypeCaps ::= TEXTUAL-CONVENTION
  STATUS        current
  DESCRIPTION
         "Manual Reversion, Automatic Reversion, or no reversion at all for tunnels supporting restoration" 
  SYNTAX        BITS
                {
                  capUndefined(0),
                  capNone(1),
                  capManual(2),
                  capAuto(3)
                }

FspR7CpRole ::= TEXTUAL-CONVENTION
  STATUS        current
  DESCRIPTION
         "Role" 
  SYNTAX        INTEGER
                {
                  undefined(0),
                  working(1),
                  protection(2),
                  na(3),
                  workingNominal(4),
                  workingRestored(5),
                  protectionNominal(6),
                  protectionRestored(7),
                  nominal(8),
                  restored(9)
                }

FspR7CpRsvpSignalling ::= TEXTUAL-CONVENTION
  STATUS        current
  DESCRIPTION
         "RSVP Signalling" 
  SYNTAX        INTEGER
                {
                  undefined(0),
                  enable(1),
                  disable(2)
                }

FspR7CpRsvpSignallingCaps ::= TEXTUAL-CONVENTION
  STATUS        current
  DESCRIPTION
         "RSVP Signalling" 
  SYNTAX        BITS
                {
                  capUndefined(0),
                  capEnable(1),
                  capDisable(2)
                }

FspR7CpTEType ::= TEXTUAL-CONVENTION
  STATUS        current
  DESCRIPTION
         "Traffic Engineering Entity Type" 
  SYNTAX        INTEGER
                {
                  undefined(0),
                  node(1),  --Network unique 32 bit number identifying a node on the network
                  linkun(2),  --A combination of the te_node_id and a node unique 32 bit number (local_link_index) that identifies an unnumbered TE link on the network
                  linknr(3)  --Network unique 32 bit number identifying a numbered TE link on the network
                }

FspR7CpTETypeCaps ::= TEXTUAL-CONVENTION
  STATUS        current
  DESCRIPTION
         "Traffic Engineering Entity Type" 
  SYNTAX        BITS
                {
                  capUndefined(0),
                  capNode(1),
                  capLinkun(2),
                  capLinknr(3)
                }

FspR7CpTie ::= TEXTUAL-CONVENTION
  STATUS        current
  DESCRIPTION
         "Follow On" 
  SYNTAX        INTEGER
                {
                  undefined(0),
                  strict(1),
                  loose(2)
                }

FspR7CpTieCaps ::= TEXTUAL-CONVENTION
  STATUS        current
  DESCRIPTION
         "Follow On" 
  SYNTAX        BITS
                {
                  capUndefined(0),
                  capStrict(1),
                  capLoose(2)
                }

FspR7CpTunnelType ::= TEXTUAL-CONVENTION
  STATUS        current
  DESCRIPTION
         "Tunnel Type" 
  SYNTAX        INTEGER
                {
                  undefined(0),
                  p2p(1)
                }

FspR7CpTunnelTypeCaps ::= TEXTUAL-CONVENTION
  STATUS        current
  DESCRIPTION
         "Tunnel Type" 
  SYNTAX        BITS
                {
                  capUndefined(0),
                  capP2p(1)
                }

FspR7CpTunnelScope ::= TEXTUAL-CONVENTION
  STATUS        current
  DESCRIPTION
         "Service Scope extending over either Client or Network Ports of Modules or Links (UN or NR) for Connection Segements" 
  SYNTAX        INTEGER
                {
                  undefined(0),
                  clientPort(1),
                  networkPort(2)
                }

FspR7CpTunnelScopeCaps ::= TEXTUAL-CONVENTION
  STATUS        current
  DESCRIPTION
         "Service Scope extending over either Client or Network Ports of Modules or Links (UN or NR) for Connection Segements" 
  SYNTAX        BITS
                {
                  capUndefined(0),
                  capClientPort(1),
                  capNetworkPort(2)
                }

FspR7CpType ::= TEXTUAL-CONVENTION
  STATUS        current
  DESCRIPTION
         "Control Plane Type" 
  SYNTAX        INTEGER
                {
                  undefined(0),
                  intern(1),
                  gmpls(2),
                  none(3),
                  passive(4),
                  uni(5),
                  oifUni(6),
                  oifNni(7)
                }

FspR7CpTypeCaps ::= TEXTUAL-CONVENTION
  STATUS        current
  DESCRIPTION
         "Control Plane Type" 
  SYNTAX        BITS
                {
                  capUndefined(0),
                  capIntern(1),
                  capGmpls(2),
                  capNone(3),
                  capPassive(4),
                  capUni(5),
                  capOifUni(6),
                  capOifNni(7)
                }

FspR7CpVTeType ::= TEXTUAL-CONVENTION
  STATUS        current
  DESCRIPTION
         "Type of Virtual TE configuration" 
  SYNTAX        INTEGER
                {
                  undefined(0),
                  vTeLink(1),
                  vTeNode(2),
                  vTeNodeRlink(3),
                  vTeNodeVlink(4)
                }

FspR7CpVTeTypeCaps ::= TEXTUAL-CONVENTION
  STATUS        current
  DESCRIPTION
         "Type of Virtual TE configuration" 
  SYNTAX        BITS
                {
                  capUndefined(0),
                  capVTeLink(1),
                  capVTeNode(2),
                  capVTeNodeRlink(3),
                  capVTeNodeVlink(4)
                }

FspR7DatabaseType ::= TEXTUAL-CONVENTION
  STATUS        current
  DESCRIPTION
         "This shows whether the system is running on a temporary auxiliary DBor on the DB in ACT, which is the normal situation" 
  SYNTAX        INTEGER
                {
                  undefined(0),
                  auxiliary(1),
                  normal(2)
                }

FspR7Date ::= TEXTUAL-CONVENTION
  DISPLAY-HINT "2d-1d-1d"
  STATUS        current
  DESCRIPTION
         "A date specification.
         field octets contents range
         ----- ------ -------- -----
         1 1-2 year* 0..65536
         2 3 month 1..12
         3 4 day 1..31
         * Notes: - the value of year is in network-byte order
         For example, Tuesday May 26, 1992 would be
         displayed as:
         1992-5-26" 
  SYNTAX        OCTET STRING (SIZE(4..4))

FspR7DCFiberType ::= TEXTUAL-CONVENTION
  STATUS        current
  DESCRIPTION
         "Dispersion Compensation Fibertype" 
  SYNTAX        INTEGER
                {
                  undefined(0),
                  singleMode(1),
                  trueWaveRs(2)
                }

FspR7DCFiberTypeCaps ::= TEXTUAL-CONVENTION
  STATUS        current
  DESCRIPTION
         "Dispersion Compensation Fibertype" 
  SYNTAX        BITS
                {
                  capUndefined(0),
                  capSingleMode(1),
                  capTrueWaveRs(2)
                }

FspR7DeploymentScenario ::= TEXTUAL-CONVENTION
  STATUS        current
  DESCRIPTION
         "Describes how the card is applied related to a network scenario" 
  SYNTAX        INTEGER
                {
                  undefined(0),
                  generic(1),  --NO additonal deployment information supplied [thus Protected as above OR Protected in a Channel Card Protection (not yet known) OR Unprotected OR possibly (unknown to this card) deployed in a VSM Protection scenario]
                  backToBack(2),  --IF MODE NOT = TRANSHST NOR MUXHST NOR REGEN back to back regenerator on pass-thru
                  clientProt(3),  --IF MODE NOT = TRANSHST OR MUXHST deployed in client layer protection and thus NOT used for HST Channel protection NOR Channel Card protection NOR VSM Protection
                  passThrough(4)  --IF MODE NOT = TRANSHST OR MUXHST deployed in client layer protection and thus NOT used for HST Channel protection NOR Channel Card protection NOR VSM Protection
                }

FspR7DeploymentScenarioCaps ::= TEXTUAL-CONVENTION
  STATUS        current
  DESCRIPTION
         "Describes how the card is applied related to a network scenario" 
  SYNTAX        BITS
                {
                  capUndefined(0),
                  capGeneric(1),
                  capBackToBack(2),
                  capClientProt(3),
                  capPassThrough(4)
                }

FspR7DisableEnable ::= TEXTUAL-CONVENTION
  STATUS        current
  DESCRIPTION
         "Disable/Enable variable." 
  SYNTAX        INTEGER

                {
                  undefined(0),
                  disable(1),
                  enable(2)
                }

FspR7Disjointedness ::= TEXTUAL-CONVENTION
  STATUS        current
  DESCRIPTION
         "Defines how a tunnel must be separated from the reference tunnel." 
  SYNTAX        INTEGER
                {
                  undefined(0),
                  link(1),
                  node(2),
                  srlg(3),
                  best(4),
                  minDisjoint(5),
                  fullCorouted(6)
                }

FspR7DispersionCompensation ::= TEXTUAL-CONVENTION
  STATUS        current
  DESCRIPTION
         "Dispersion Compensation Value in km of SSMF fiber" 
  SYNTAX        INTEGER
                {
                  undefined(0),
                  dispertion10(1),
                  dispertion20(2),
                  dispertion40(3),
                  dispertion60(4),
                  dispertion80(5),
                  dispertion100(6),
                  dispertion30(7),
                  dispertion50(8),
                  dispertion70(9),
                  dispertion90(10),
                  dispertion160(11),
                  dispertion240(12),
                  dispertion320(13)
                }

FspR7DispersionCompensationCaps ::= TEXTUAL-CONVENTION
  STATUS        current
  DESCRIPTION
         "Dispersion Compensation Value in km of SSMF fiber" 
  SYNTAX        BITS
                {
                  capUndefined(0),
                  capDispertion10(1),
                  capDispertion20(2),
                  capDispertion40(3),
                  capDispertion60(4),
                  capDispertion80(5),
                  capDispertion100(6),
                  capDispertion30(7),
                  capDispertion50(8),
                  capDispertion70(9),
                  capDispertion90(10),
                  capDispertion160(11),
                  capDispertion240(12),
                  capDispertion320(13)
                }

FspR7DispersionConfig ::= TEXTUAL-CONVENTION
  STATUS        current
  DESCRIPTION
         "Chromatic Dispersion Compensation" 
  SYNTAX        INTEGER
                {
                  undefined(0),
                  rls(1),
                  oprCdc(2)
                }

FspR7DispersionConfigCaps ::= TEXTUAL-CONVENTION
  STATUS        current
  DESCRIPTION
         "Chromatic Dispersion Compensation" 
  SYNTAX        BITS
                {
                  capUndefined(0),
                  capRls(1),
                  capOprCdc(2)
                }

FspR7DispersionModes ::= TEXTUAL-CONVENTION
  STATUS        current
  DESCRIPTION
         "Chromatic Dispersion Compensation Mode" 
  SYNTAX        INTEGER
                {
                  undefined(0),
                  auto(1),
                  man(2)
                }

FspR7DispersionModesCaps ::= TEXTUAL-CONVENTION
  STATUS        current
  DESCRIPTION
         "Chromatic Dispersion Compensation Mode" 
  SYNTAX        BITS
                {
                  capUndefined(0),
                  capAuto(1),
                  capMan(2)
                }

FspR7DiversifyPath ::= TEXTUAL-CONVENTION
  STATUS        current
  DESCRIPTION
         "Path Types Control Plane avoids in when specifing the diverse tunnels." 
  SYNTAX        INTEGER
                {
                  undefined(0),
                  currentWkg(1),
                  nominalWkg(2),
                  allWkg(3)
                }

FspR7DvScope ::= TEXTUAL-CONVENTION
  STATUS        current
  DESCRIPTION
         "Diversity Scope" 
  SYNTAX        INTEGER
                {
                  undefined(0),
                  local(1),
                  remote(2)
                }

FspR7EdfaOutputPowerRating ::= TEXTUAL-CONVENTION
  STATUS        current
  DESCRIPTION
         "Optical Output Power Rating - Inventory" 
  SYNTAX        INTEGER
                {
                  undefined(0),
                  pwrOut10(1),
                  pwrOut17(2),
                  pwrOut18(3),
                  pwrOut20(4),
                  pwrOut15(5),
                  pwrOut27(6),
                  pwrOut26(7),
                  pwrOut20UN10NU(8)
                }

FspR7EdfaOutputPowerRatingCaps ::= TEXTUAL-CONVENTION
  STATUS        current
  DESCRIPTION
         "Optical Output Power Rating - Inventory" 
  SYNTAX        BITS
                {
                  capUndefined(0),
                  capPwrOut10(1),
                  capPwrOut17(2),
                  capPwrOut18(3),
                  capPwrOut20(4),
                  capPwrOut15(5),
                  capPwrOut27(6),
                  capPwrOut26(7),
                  capPwrOut20UN10NU(8)
                }

FspR7EnableDisable ::= TEXTUAL-CONVENTION
  STATUS        current
  DESCRIPTION
         "Enable/Disable variable." 
  SYNTAX        INTEGER

                {
                  undefined(0),
                  enable(1),
                  disable(2)
                }

FspR7EnableDisableCaps ::= TEXTUAL-CONVENTION
  STATUS        current
  DESCRIPTION
         "Enable/Disable variable." 
  SYNTAX        BITS
                {
                  capUndefined(0),
                  capEnable(1),
                  capDisable(2)
                }

FspR7EntitySecondaryStates ::= TEXTUAL-CONVENTION
  STATUS        current
  DESCRIPTION
         "Variable for representing the secondary states of an entity." 
  SYNTAX        BITS

                {
                  ueq(0),
                  meaState(1),
                  sgeo(2),
                  lpbkState(3),
                  lkdo(4),
                  frcdState(5),
                  faf(6),
                  flt(7),
                  act(8),
                  stbyh(9),
                  psi(10),
                  pri(11),
                  dgn(12),
                  busy(13),
                  idleState(14),
                  receiveIdleState(15),
                  transmitIdleState(16),
                  sgeoSrv(17),
                  farEndPlugOutage(18),
                  aseTableBuildState(19),
                  testState(20),
                  testFailed(21),
                  stby(22),
                  stbyInh(23),
                  noBackup(24),
                  degrade(25),
                  swdl(26)
                }

FspR7EocProtAvailability ::= TEXTUAL-CONVENTION
  STATUS        current
  DESCRIPTION
         "ECC Protection Availability" 
  SYNTAX        INTEGER
                {
                  undefined(0),
                  no(1),  --Unprotected Entity
                  yes(2)  --Protected Entity
                }

FspR7EqlzAdminState ::= TEXTUAL-CONVENTION
  STATUS        current
  DESCRIPTION
         "Scheduled Equalization Administration" 
  SYNTAX        INTEGER
                {
                  undefined(0),
                  enabled(1),
                  disabled(2)
                }

FspR7EqlzAdminStateCaps ::= TEXTUAL-CONVENTION
  STATUS        current
  DESCRIPTION
         "Scheduled Equalization Administration" 
  SYNTAX        BITS
                {
                  capUndefined(0),
                  capEnabled(1),
                  capDisabled(2)
                }

FspR7EqlzInterval ::= TEXTUAL-CONVENTION
  STATUS        current
  DESCRIPTION
         "Scheduled Equalization Interval" 
  SYNTAX        INTEGER
                {
                  undefined(0),
                  interval-2-hr(1),
                  interval-4-hr(2),
                  interval-12-hr(3),
                  interval-1-day(4),
                  interval-7-day(5),
                  interval-5-min(6)
                }

FspR7EqlzIntervalCaps ::= TEXTUAL-CONVENTION
  STATUS        current
  DESCRIPTION
         "Scheduled Equalization Interval" 
  SYNTAX        BITS
                {
                  capUndefined(0),
                  capInterval-2-hr(1),
                  capInterval-4-hr(2),
                  capInterval-12-hr(3),
                  capInterval-1-day(4),
                  capInterval-7-day(5),
                  capInterval-5-min(6)
                }

FspR7ErrorFwdMode ::= TEXTUAL-CONVENTION
  STATUS        current
  DESCRIPTION
         "Determines the reaction in forward direction in response to a LOS on
         the interface on the opposite side of the module: may override
         this behaviour in the interests of laser safety." 
  SYNTAX        INTEGER
                {
                  undefined(0),
                  ais(1),  --Setting of all-ones AIS: Only relevant to a SONET / SDH / OTU interface
                  epc(2),  --Error Propagation Code is set, - if available, - for other applications, - if so desired, - only settable where available
                  idle(3),  --In the absence of any other indication, such as ALS, this implies a typical ADVA network-side facility behavior
                  lsrOff(4),  --Where no Error Propagation Code is available, - or if so desired
                  lsrBrk(5),  --Laser Break. Break of x[ms] length in client signal upon detection of error to propagate the error condition.
                  txOff(6)  --Used for electrical SFP similar than LSROFF
                }

FspR7ErrorFwdModeCaps ::= TEXTUAL-CONVENTION
  STATUS        current
  DESCRIPTION
         "Determines the reaction in forward direction in response to a LOS on
         the interface on the opposite side of the module: may override
         this behaviour in the interests of laser safety." 
  SYNTAX        BITS
                {
                  capUndefined(0),
                  capAis(1),
                  capEpc(2),
                  capIdle(3),
                  capLsrOff(4),
                  capLsrBrk(5),
                  capTxOff(6)
                }

FspR7FalseTrue ::= TEXTUAL-CONVENTION
  STATUS        current
  DESCRIPTION
         "False True variable." 
  SYNTAX        INTEGER

                {
                  undefined(0),
                  false(1),
                  true(2)
                }

FspR7FalseTrueCaps ::= TEXTUAL-CONVENTION
  STATUS        current
  DESCRIPTION
         "False True variable." 
  SYNTAX        BITS
                {
                  capUndefined(0),
                  capFalse(1),
                  capTrue(2)
                }

FspR7FDStatus ::= TEXTUAL-CONVENTION
  STATUS        current
  DESCRIPTION
         "Fiber Detect Status" 
  SYNTAX        INTEGER
                {
                  undefined(0),
                  enabled(1),
                  disabledSystem(2),
                  disabledModule(3),
                  disabledPtp(4),
                  disabledAdmin(5)
                }

FspR7FDStatusCaps ::= TEXTUAL-CONVENTION
  STATUS        current
  DESCRIPTION
         "Fiber Detect Status" 
  SYNTAX        BITS
                {
                  capUndefined(0),
                  capEnabled(1),
                  capDisabledSystem(2),
                  capDisabledModule(3),
                  capDisabledPtp(4),
                  capDisabledAdmin(5)
                }

FspR7FecType ::= TEXTUAL-CONVENTION
  STATUS        current
  DESCRIPTION
         "Forward Error Correction (Only relevant where TYPE = OTU#)" 
  SYNTAX        INTEGER
                {
                  undefined(0),
                  gFec(1),  --G709 Standard FEC
                  eFec(2),  --Enhanced FEC
                  noFec(3),  --No FEC
                  eFec1(4),  --Enhanced FEC (INTEL)
                  eFec2(5),  --Enhanced FEC (AMCC)
                  eFec3(6),  --Enhanced FEC (CORE)
                  eFec4(7),  --Enhanced FEC (Acacia)
                  eFecX(8),  --Variable Coding Gain
                  eFec5(9),  --Cascaded FEC (LDPC+GFEC)
                  eFec6(10),  --EFEC-6 (Turbo)
                  eFec7(11),  --EFEC-7 (15% Overhead)
                  eFec8(12),  --EFEC-8 (25% Overhead)
                  rsFec2(13)  --RSFEC-2(802.3 Clause 91)
                }

FspR7FecTypeCaps ::= TEXTUAL-CONVENTION
  STATUS        current
  DESCRIPTION
         "Forward Error Correction (Only relevant where TYPE = OTU#)" 
  SYNTAX        BITS
                {
                  capUndefined(0),
                  capGFec(1),
                  capEFec(2),
                  capNoFec(3),
                  capEFec1(4),
                  capEFec2(5),
                  capEFec3(6),
                  capEFec4(7),
                  capEFecX(8),
                  capEFec5(9),
                  capEFec6(10),
                  capEFec7(11),
                  capEFec8(12),
                  capRsFec2(13)
                }

FspR7FiberBrand ::= TEXTUAL-CONVENTION
  STATUS        current
  DESCRIPTION
         "Brand of fiber present in the fiber plant" 
  SYNTAX        INTEGER
                {
                  undefined(0),
                  g652(1),
                  g653(2),
                  g655(3),
                  smf28e(4),
                  allWave(5),
                  leaf(6),
                  twRs(7),
                  twPl(8),
                  twCl(9),
                  teraLight(10),
                  smfLs(11),
                  metrocor(12)
                }

FspR7FiberBrandCaps ::= TEXTUAL-CONVENTION
  STATUS        current
  DESCRIPTION
         "Brand of fiber present in the fiber plant" 
  SYNTAX        BITS
                {
                  capUndefined(0),
                  capG652(1),
                  capG653(2),
                  capG655(3),
                  capSmf28e(4),
                  capAllWave(5),
                  capLeaf(6),
                  capTwRs(7),
                  capTwPl(8),
                  capTwCl(9),
                  capTeraLight(10),
                  capSmfLs(11),
                  capMetrocor(12)
                }

FspR7FiberDetect ::= TEXTUAL-CONVENTION
  STATUS        current
  DESCRIPTION
         "Fiber Detect" 
  SYNTAX        INTEGER
                {
                  undefined(0),
                  enabled(1),
                  disabled(2)
                }

FspR7FiberDetectCaps ::= TEXTUAL-CONVENTION
  STATUS        current
  DESCRIPTION
         "Fiber Detect" 
  SYNTAX        BITS
                {
                  capUndefined(0),
                  capEnabled(1),
                  capDisabled(2)
                }

FspR7FlowControlMode ::= TEXTUAL-CONVENTION
  STATUS        current
  DESCRIPTION
         "Flow Control mechanism" 
  SYNTAX        INTEGER
                {
                  undefined(0),
                  none(1),
                  hwControl(2),
                  pause(3)  --Pause frame generation.
                }

FspR7FlowControlModeCaps ::= TEXTUAL-CONVENTION
  STATUS        current
  DESCRIPTION
         "Flow Control mechanism" 
  SYNTAX        BITS
                {
                  capUndefined(0),
                  capNone(1),
                  capHwControl(2),
                  capPause(3)
                }

FspR7ForcedStatus ::= TEXTUAL-CONVENTION
  STATUS        current
  DESCRIPTION
         "Forced Destroy" 
  SYNTAX        INTEGER
                {
                  undefined(0),
                  active(1),
                  forcedDestroy(2)
                }

FspR7ForcedStatusCaps ::= TEXTUAL-CONVENTION
  STATUS        current
  DESCRIPTION
         "Forced Destroy" 
  SYNTAX        BITS
                {
                  capUndefined(0),
                  capActive(1),
                  capForcedDestroy(2)
                }

FspR7FrameFormat ::= TEXTUAL-CONVENTION
  STATUS        current
  DESCRIPTION
         "Frame Format" 
  SYNTAX        INTEGER
                {
                  undefined(0),
                  otn(1),
                  sdh(2),
                  sonet(3),
                  ethernet(4),
                  fiberchannel(5),
                  infiniband(6),
                  couplinglink(7),
                  transparent(8),
                  notDefined(99)
                }

FspR7FrameFormatCaps ::= TEXTUAL-CONVENTION
  STATUS        current
  DESCRIPTION
         "Frame Format" 
  SYNTAX        BITS
                {
                  capUndefined(0),
                  capOtn(1),
                  capSdh(2),
                  capSonet(3),
                  capEthernet(4),
                  capFiberchannel(5),
                  capInfiniband(6),
                  capCouplinglink(7),
                  capTransparent(8),
                  capNotDefined(99)
                }

FspR7FtpServer ::= TEXTUAL-CONVENTION
  STATUS        current
  DESCRIPTION
         "FTP server enable/disable configuration" 
  SYNTAX        INTEGER
                {
                  undefined(0),
                  enable(1),
                  disable(2)
                }

FspR7FtpServerCaps ::= TEXTUAL-CONVENTION
  STATUS        current
  DESCRIPTION
         "FTP server enable/disable configuration" 
  SYNTAX        BITS
                {
                  capUndefined(0),
                  capEnable(1),
                  capDisable(2)
                }

FspR7FtpClient ::= TEXTUAL-CONVENTION
  STATUS        current
  DESCRIPTION
         "FTP client enable/disable configuration" 
  SYNTAX        INTEGER
                {
                  undefined(0),
                  enable(1),
                  disable(2)
                }

FspR7FunctionCrs ::= TEXTUAL-CONVENTION
  STATUS        current
  DESCRIPTION
         "Describes the Cross Connect Functionality" 
  SYNTAX        INTEGER
                {
                  undefined(0),
                  add(1),
                  drop(2),
                  pass(3),
                  hairpin(4),
                  select(5),
                  addDrop(6),
                  dropCont(7)
                }

FspR7Gain ::= TEXTUAL-CONVENTION
  STATUS        current
  DESCRIPTION
         "Gain" 
  SYNTAX        INTEGER
                {
                  undefined(0),
                  gain24(1),
                  gain25(2)
                }

FspR7GainCaps ::= TEXTUAL-CONVENTION
  STATUS        current
  DESCRIPTION
         "Gain" 
  SYNTAX        BITS
                {
                  capUndefined(0),
                  capGain24(1),
                  capGain25(2)
                }

FspR7GainRange ::= TEXTUAL-CONVENTION
  STATUS        current
  DESCRIPTION
         "EDFA gain range to provision" 
  SYNTAX        INTEGER
                {
                  undefined(0),
                  high(1),
                  low(2),
                  lowUNlowNU(3)
                }

FspR7GainRangeCaps ::= TEXTUAL-CONVENTION
  STATUS        current
  DESCRIPTION
         "EDFA gain range to provision" 
  SYNTAX        BITS
                {
                  capUndefined(0),
                  capHigh(1),
                  capLow(2),
                  capLowUNlowNU(3)
                }

FspR7InitEqualization ::= TEXTUAL-CONVENTION
  STATUS        current
  DESCRIPTION
         "Initiate Equalization" 
  SYNTAX        INTEGER
                {
                  undefined(0),
                  rls(1),
                  opr(2)
                }

FspR7InitEqualizationCaps ::= TEXTUAL-CONVENTION
  STATUS        current
  DESCRIPTION
         "Initiate Equalization" 
  SYNTAX        BITS
                {
                  capUndefined(0),
                  capRls(1),
                  capOpr(2)
                }

FspR7InterfaceFunction ::= TEXTUAL-CONVENTION
  STATUS        current
  DESCRIPTION
         "Interface Function" 
  SYNTAX        INTEGER
                {
                  undefined(0),
                  transport(1),
                  switch(2),
                  edfa(3),
                  super(4),
                  passive(5),
                  active(6),
                  raman(7),
                  physicalTerm(8)
                }

FspR7InterfaceFunctionCaps ::= TEXTUAL-CONVENTION
  STATUS        current
  DESCRIPTION
         "Interface Function" 
  SYNTAX        BITS
                {
                  capUndefined(0),
                  capTransport(1),
                  capSwitch(2),
                  capEdfa(3),
                  capSuper(4),
                  capPassive(5),
                  capActive(6),
                  capRaman(7),
                  capPhysicalTerm(8)
                }

FspR7InterfaceType ::= TEXTUAL-CONVENTION
  STATUS        current
  DESCRIPTION
         "The TYPE defines the transport service type as wrapper with wrapper layer termination OR else as payload" 
  SYNTAX        INTEGER
                {
                  undefined(0),
                  ifTypeOtu1(1),  --OTU1: Line Rate 2.66 Gbps; supports full protocol
                  ifTypeOtu2(2),  --OTU2: Line Rate 10.70 Gbps; supports full protocol
                  ifType10GbE(3),  --Ethernet 10G LAN: Line Rate 10.3125 Gbps; supports full protocol
                  ifTypeOc192(4),  --SONET OC-192: Line Rate 9.953 Gbps; supports full protocol
                  ifTypeOc48(5),  --SONET OC-48: Line Rate 2.488 Gbps; supports full protocol
                  ifTypeStm16(6),  --SDH STM-16: Line Rate 2.488 Gbps; supports full protocol
                  ifTypeStm64(7),  --SDH STM-16: Line Rate 9.953 Gbps; supports full protocol
                  ifType10GFC(8),  --Fibre Channel 10G: Line Rate 10.518 Gbps; supports full protocol
                  ifTypeF1062(10),  --Fixed Rate 1.062 Gbps; supports transport of Fibre Channel 1G
                  ifTypeF1250(11),  --Fixed Rate 1.250 Gbps; supports transport of Ethernet 1G 
                  ifTypeFC(12),  --Fibre Channel 1G: Line Rate 1.0625 Gbps; supports full protocol
                  ifTypeF125(13),  --Fixed Rate 125 Mbps; supports transport of Fast Ethernet or MADI 
                  ifTypeF200(14),  --Fixed Rate 200 Mbps; supports transport of ESCON
                  ifTypeF9953(15),  --Fixed Rate 9.953 Gbps; supports transport of STM-64, OC-192 or 10G Ethernet WAN
                  ifTypeF10312(16),  --Fixed Rate 10.312 Gbps; supports transport of Ethernet 10G LAN
                  ifTypeF10518(17),  --Fixed Rate 10.518 Gbps; supports transport of Fibre Channel 10G
                  ifTypeF2488(18),  --Fixed Rate 2.488 Gbps; supports transport of STM-16 or OC-48
                  ifTypeGfpF(19),  --GFP-F: Generic Framing Protocol Frame (payload has a defined frame)
                  ifTypeGfpT(20),  --GFP-T: Generic Framing Protocol Transparent (payload is transparent)
                  ifTypeDccL(21),  --SONET Line DCC: Digital Communication Channel in overhead bytes
                  ifTypeDccS(22),  --SONET Section DCC: Digital Communication Channel in overhead bytes
                  ifTypeDccP(23),  --SONET Path DCC: Digital Communication Channel in overhead bytes
                  ifTypeOdu1(24),  --ODU1: carries client service
                  ifTypeGcc0(25),  --GCC0: General Communication Channel 0 in overhead bytes
                  ifTypeGcc1(26),  --GCC1: General Communication Channel 1 in overhead bytes
                  ifTypeGcc2(27),  --GCC2: General Communication Channel 2 in overhead bytes
                  ifTypeoch(28),  --Single optical channel on physical layer
                  ifTypeOm(29),  --Multiplex of optical channels on physical layer
                  ifTypeOt(34),  --Multiplex of optical channels on physical layer with OSC support
                  ifTypeE10or100bt(36),  --Ethernet 10/100Base-T: Ethernet 10 or 100 Mbps on electrical physical layer
                  ifTypeE100fx(37),  --Ethernet 100FX: Ethernet 100 Mbps optical physical layer
                  ifTypeCl(38),  --Coupling Link 1G: Inter System Channel 
                  ifType2GFC(39),  --Fibre Channel 2G: Line Rate 2.125 Gbps; supports full protocol
                  ifType2GCL(40),  --Coupling Link 2G: Inter System Channel 
                  ifType1GbE(41),  --Ethernet 1G: Line Rate 1.03125 Gbps; supports full protocol
                  ifTypeEoc(42),  --Embedded Operations Channel; supports management communication 
                  ifTypeSwitch(43),  --Switch; supports path switching
                  ifTypePassive(44),  --Passive; fixed equipment path
                  ifTypeF2500(45),  --Fixed Rate 2.500 Mbps; supports transport of 2.5G Infiniband
                  ifTypeSc(46),  --Supervisiory Channel (OSC); supports management communication
                  ifTypeUch(47),  --Unidirectional Channel: Service support limited to one direction
                  ifTypeF155(48),  --Fixed Rate 155.52 Mbps; supports transport of SDH STM-1, SONET OC-3 or ATM 155 
                  ifTypeF622(49),  --Fixed Rate 622.08 Mbps; supports transport of SDH STM-4, SONET OC-12 or ATM 622 
                  ifTypeF2125(50),  --Fixed Rate 2.125 Gbps; supports transport for Fibre Channel 2G
                  ifTypeF2666(51),  --Fixed Rate 2.666 Gbps; supports transport of OTU1
                  ifTypeF4250(52),  --Fixed Rate 4.250 Gbps; supports transport of Fibre Channel 4G
                  ifTypeF10709(54),  --Fixed Rate 10.709 Gbps; supports transport of OTU2
                  ifTypeF11095(55),  --Fixed Rate 11.095 Gbps; supports transport of OTU2e (OTU2 carrying Ethernet 10G LAN with stuffing)
                  ifTypeF11318(56),  --Fixed Rate 11.318 Gbps; supports transport of OTU2f (OTU2 carrying Fibre Channel 10G with stuffing)
                  ifTypeLs(57),  --Not supported
                  ifType4Gfc(58),  --Fibre Channel 4G: Line Rate 4.250 Gbps; supports full protocol
                  ifTypeGcc0S(59),  --GCC0 Special: General Communication Channel 0 Special
                  ifType2R(60),  --Regeneration-2R: Signal shaped and re-clocked
                  ifTypePppIp(61),  --Point-to-Point Protocol; connects communication channel to Management Network
                  ifTypeLanIp(62),  --Internet Protocol LAN; connects Management Network
                  ifTypeSerial(64),  --Serial Interface; supports RS-232 data format
                  ifTypeModem(65),  --Modem
                  ifTypeAdapt(66),  --Adaptive Clock: Equipment adjusts clock to any rate (within limits) to match signal
                  ifTypeAdaptd(67),  --Adaptive Clock Discrete: Equipment adjusts clock to a predefined rate to match signal
                  ifTypeGBEFR(69),  --Not supported
                  ifTypeVc4(70),  --SDH VC-4: carries client service 
                  ifTypeVc3(71),  --SDH VC-3: carries client service 
                  ifTypeSts1(72),  --SONET STS-1: carries client service
                  ifTypeEdfa(73),  --Amplified multiplex of optical channels
                  ifTypeEdfaMid(74),  --Amplified multiplex of optical channels access between amplifier stages
                  ifType10Gdw(75),  --Not supported
                  ifTypeOtu2Lan(76),  --OTU2 (10G Ethernet): OTU2 carrying Ethernet 10G with stuffing control)
                  ifTypeOtu1Lan(77),  --OTU1 (Ethernet): OTU1 carrying Ethernet 1G)
                  ifTypeOtu1Fc(78),  --OTU1 (Fibre Channel 1G): OTU1 carrying Fibre Channel 1G)
                  ifTypeOtu1Fc2G(79),  --OTU1 (Fibre Channel 2G): OTU1 carrying Fibre Channel 2G)
                  ifTypeF197(80),  --Fixed Rate 196.6 Mbps; supports transport of GLink
                  ifTypeTif(81),  --Telemetry Interface
                  ifTypeSts3c(82),  --SONET STS-3c: carries client service
                  ifTypeVs1(83),  --Virtual Container; carries client service
                  ifType1GbETH(84),  --Ethernet 1G-Rate Limit: Rate limited Ethernet at 1Gbps or lower
                  ifTypeStm1(85),  --SDH STM-1: Line Rate 155.52 Mbps; supports full protocol
                  ifTypeStm4(86),  --SDH STM-4: Line Rate 622.08 Mbps; supports full protocol
                  ifTypeOc3(87),  --SONET OC-3: Line Rate 155.52 Mbps; supports full protocol
                  ifTypeOc12(88),  --SONET OC-12: Line Rate 622.08 Mbps; supports full protocol
                  ifTypeOtu1Stm1(89),  --OTU1 (STM1): OTU1 carrying STM-1
                  ifTypeOtu1Stm4(90),  --OTU1 (STM4): OTU1 carrying STM-4
                  ifTypeF166(91),  --Fixed Rate 166 Mbps; supports transport of Video
                  ifTypeF666(92),  --Fixed Rate 666 Mbps; supports transport of Video
                  ifTypeI2C(93),  --I2C: Inter-Integrated Circuit 
                  ifTypeLifIP(94),  --LIF IP: Logiical Interface to support Internet Protocol (IP)
                  ifTypeSts24c(95),  --SONET STS-24c: carries client service
                  ifTypeSts48c(96),  --SONET STS-48c: carries client service
                  ifTypeLifte(97),  --Traffic Engineering: Logical Interface to support network traffic engineering
                  ifTypeRaman(98),  --Amplified multiplex of optical channels using recieve network fiber
                  ifTypeIpWhiteList(99),  --IP (White List): Internet Protocol (IP) allowed packets
                  ifTypeOspfIp(100),  --IP (OSPF): Internet Protocol (IP) supports Open Shortest Path First (OSPF) path determination
                  ifTypeEncapIp(101),  --IP (Encapsulation): Internet Protocol (IP) allows IP packets to be encapsulated within an IP packet 
                  ifTypeOtu3(102),  --OTU3: Line Rate 43.01 Gbps; supports full protocol
                  ifTypeStm256(103),  --SDH STM-256: Line Rate 39.81312 Gbps; supports full protocol
                  ifTypeOc768(104),  --SONET OC-768: Line Rate 39.81312 Gbps; supports full protocol
                  ifTypeF10664(105),  --Fixed Rate 10.664 Gbps; supports transport of proprietary OTU2 carrying STM-64 or OC-192 without stuffing
                  ifTypeOdu2(106),  --ODU2: carries client service
                  ifTypeF39813(107),  --Fixed Rate 39.813 Gbps; supports transport of OC-768 or STM-256 
                  ifTypeVc4c8(108),  --SDH VC4-8c; carries client service
                  ifTypeVc4c16(109),  --SDH VC4-16c; carries client service
                  ifTypeF8500(110),  --Fixed datarate 8500 Mbps; supports transport of 8G Fibre Channel
                  ifTypePb(111),  --Port Binding: support port specification for TCP and UDP
                  ifTypePolicer(112),  --Police: support Ethernet packet monitoring and control
                  ifTypeQueue(113),  --Queue: support Ethernet packet queueing
                  ifTypeFlowPoint(114),  --Flow: carreis client service
                  ifTypeLag(115),  --Link Aggregation Group: Multiple ports support traffic sharing
                  ifTypeElinePPP(116),  --Ethernet path restricted to another point
                  ifTypeEtree(117),  --Ethernet Tree
                  ifTypeEline(118),  --Ethernet path restricted to another point
                  ifTypeElan(119),  --Ethernet path forms a LAN
                  ifTypeCtrans(120),
                  ifTypeVs0(121),  --Virtual Sub Container (VS0): carries client service
                  ifTypeTug(122),  --Triburary Unit Group: carries client service
                  ifTypeMd(123),  --Maintenance Domain
                  ifTypeMa(124),  --Maintenance Association
                  ifTypeDownMep(125),  --Downstream Maintenance End Point
                  ifTypeFMep(126),  --Far End Maintenance End Point
                  ifType8Gfc(127),  --Fibre Channel 8G: Line Rate 8.5 Gbps; supports full protocol
                  ifType10Gib(128),  --InfiniBand 10G: Line Rate 10.000 Gbps; supports full protocol
                  ifTypeF10000(129),  --Fixed Rate 10000 Mbps; supports transport of InifinBand 10G
                  ifTypeOtu2pFC8(130),  --Proprietary OTU2 carrying Fibre Channel 8G
                  ifTypeOtu2pIB(131),  --Proprietary OTU2 carrying Infiniband 10G
                  ifTypeOtu2pFC(132),  --Proprietary OTU2 carrying Fibre Channel 10G 
                  ifTypeOtu2pLAN(133),  --Proprietary OTU2 carrying Ethernet 10G
                  ifTypeOtu2p(134),  --Proprietary OTU2 carrying Multiplexed Signals
                  ifTypeUpMep(135),  --Upstream Maintenance End Point
                  ifTypeOtdrCh(136),  --Optical channel supporting fiber validation
                  ifTypeMaNet(137),  --Maintenance Association Network
                  ifTypeMaComp(138),  --Maintenance Association Component
                  ifTypeBridge(139),  --Ethernet Bridge
                  ifType1000BaseT(140),  --Ethernet 1000Base-T: Ethernet 1 Gbps on electrical physical layer
                  ifTypeOtu2E(141),  --OTU2E: OTU2 overclocked to carry Ethernet 10G with stuffing; supports full protocol
                  ifTypeOtu1E(142),  --OTU1E: OTU2 overclocked to carry Ethernet 10G without stuffing; supports full protocol
                  ifTypeOtu2F(143),  --OTU2 carrying Fibre Channel 10G; supports full protocol
                  ifTypeF11049(144),  --Fixed Rate 11.049 Gbps; supports transport of OTU1E (OTU2 carrying 10G Ethernet without stuffing)
                  ifTypeLifteNum(145),  --Logical Interface to support Traffic Engineering across numbered IP interfaces
                  ifTypeLifteUnn(146),  --Logical Interface to support Traffic Engineering across unnumbered IP interfaces
                  ifTypeLifPbNum(147),  --Logical Interface to support Port Binding across numbered IP interfaces
                  ifTypeLifSubUnn(148),  --Logical Interface to support Traffic Engineering on a sublayer across unnumbered IP interfaces
                  ifType5Gib(149),  --InfiniBand 5G: Line Rate 5.000 Gbps; supports full protocol
                  ifTypeF5000(150),  --Fixed Rate 5.000 Gbps; supports transport of InfiniBand 5G
                  ifTypeOtu2eEth(151),  --OTU2E: OTU2 overclocked to carry Ethernet with stuffing; supports full protocol
                  ifTypeOdu0(152),  --ODU0: carries client service
                  ifTypeFcu(153),  --Fan Control
                  ifTypeOtu4(154),  --OTU4: Line Rate 112 Gbps; supports full protocol
                  ifType100GbE(160),  --Ethernet 100G: Line Rate 103.125 Gbps; supports full protocol
                  ifTypeOptical(161),  --Optical Channel 
                  ifType10GbEWan(162),  --Ethernet 10G WAN: Line Rate 9.9533 Gbps; 
                  ifType10GbELan(163),  --Ethernet 10G LAN: Line Rate 10.3125 Gbps; supports full protocol
                  ifTypeOduFlx(164),  --ODUflex: carries client service 
                  ifTypeOtlc(165),  --Optical Transport Lane (G.709)
                  ifTypeOtu2ps(167),  --Proprietary OTU2 carrying 9.953 G signal (OC-192 or STM-64)
                  ifTypeOdu2E(168),  --ODU2E: carries client service 
                  ifTypeOdu1E(169),  --ODU1E: carries client service 
                  ifTypeOdu2Lan(170),  --ODU2LAN: carries client service 
                  ifTypeOdu4(171),  --ODU4: carries client service 
                  ifTypeLifVTeNum(173),  --Logical Interface for Virtural Traffic Engineering links with numbered IP interfaces 
                  ifTypeLifVTeUnn(174),  --Logical Interface for Virtural Traffic Engineering links with unnumbered IP interfaces 
                  ifTypeF14025(178),  --Fixed Rate 14.025 Gbps; supports transport of Fibre Channel 16G 
                  ifTypeF270(181),  --Fixed Rate 270 Mbps; support transport of SD-SDI Video per SMPTE 259M-C 
                  ifTypeF1485(184),  --Fixed Rate 1.485 Gbps; support transport of HD-SDI Video
                  ifTypeF2970(185),  --Fixed Rate 2.970 Gbps; support transport of 3G-SDI Video
                  ifTypeF1483(188),  --Fixed Rate 1.483 Gbps; supports transport of HD-SDI Video (1)
                  ifTypeF2967(189),  --Fixed Rate 2.967 Gbps; supports transport of 3G-SDI Video (1)
                  ifType40GbE(192),  --Ethernet 40G: Line Rate 41.250; supports full protocol
                  ifTypeOdu3(193),  --ODU3: carries client service 
                  ifTypeF41250(194),  --Fixed Rate 41.250 Gbps; supports transport of Ethernet 40G (40 GbE)
                  ifTypeF103125(195),  --Fixed Rate 103.125 Gbps; supports transport of Ethernet 100G (100 GbE)
                  ifTypeF1228(199),  --Fixed Rate 1.228 Gbps; supports transport of 2xCPRI
                  ifTypeF2457(200),  --Fixed Rate 2.457 Gbps; supports transport of 4xCPRI
                  ifTypeF3072(201),  --Fixed Rate 3.072 Gbps; support transport of 5xCPRI or 4xOBSAI
                  ifTypeF4915(202),  --Fixed Rate 4.915 Gbps; supports transport of 8xCPRI
                  ifTypeF6144(203),  --Fixed Rate 6.144 Gbps; supports transport of 10xCPRI or 8xOBSAI
                  ifTypeF9830(204),  --Fixed Rate 9.830 Gbps; supports transport of 16xCPRI
                  ifTypeF10137(205),  --Fixed Rate 10.137 Gbps; supports transport of 20xCPRI
                  ifTypeAdapt1485(207),  --Adaptive Clock; rates around 1.485 Gbps
                  ifTypeAdapt2970(208),  --Adaptive Clock; rates around 2.970 Gbps
                  ifTypeOtuC2PA(209),  --Proprietary OTU for 200 Gbps transports two ODU4
                  ifTypeE10to1000t(212),  --Ethernet 10/100/1000Base-T:10/100/1000 Mbps on electrical physical layer
                  ifTypeLldp(213)  --Link Layer Discovery Protocol
                }

FspR7InterfaceTypeCaps ::= TEXTUAL-CONVENTION
  STATUS        current
  DESCRIPTION
         "The TYPE defines the transport service type as wrapper with wrapper layer termination OR else as payload" 
  SYNTAX        BITS
                {
                  capUndefined(0),
                  capIfTypeOtu1(1),
                  capIfTypeOtu2(2),
                  capIfType10GbE(3),
                  capIfTypeOc192(4),
                  capIfTypeOc48(5),
                  capIfTypeStm16(6),
                  capIfTypeStm64(7),
                  capIfType10GFC(8),
                  capIfTypeF1062(10),
                  capIfTypeF1250(11),
                  capIfTypeFC(12),
                  capIfTypeF125(13),
                  capIfTypeF200(14),
                  capIfTypeF9953(15),
                  capIfTypeF10312(16),
                  capIfTypeF10518(17),
                  capIfTypeF2488(18),
                  capIfTypeGfpF(19),
                  capIfTypeGfpT(20),
                  capIfTypeDccL(21),
                  capIfTypeDccS(22),
                  capIfTypeDccP(23),
                  capIfTypeOdu1(24),
                  capIfTypeGcc0(25),
                  capIfTypeGcc1(26),
                  capIfTypeGcc2(27),
                  capIfTypeoch(28),
                  capIfTypeOm(29),
                  capIfTypeOt(34),
                  capIfTypeE10or100bt(36),
                  capIfTypeE100fx(37),
                  capIfTypeCl(38),
                  capIfType2GFC(39),
                  capIfType2GCL(40),
                  capIfType1GbE(41),
                  capIfTypeEoc(42),
                  capIfTypeSwitch(43),
                  capIfTypePassive(44),
                  capIfTypeF2500(45),
                  capIfTypeSc(46),
                  capIfTypeUch(47),
                  capIfTypeF155(48),
                  capIfTypeF622(49),
                  capIfTypeF2125(50),
                  capIfTypeF2666(51),
                  capIfTypeF4250(52),
                  capIfTypeF10709(54),
                  capIfTypeF11095(55),
                  capIfTypeF11318(56),
                  capIfTypeLs(57),
                  capIfType4Gfc(58),
                  capIfTypeGcc0S(59),
                  capIfType2R(60),
                  capIfTypePppIp(61),
                  capIfTypeLanIp(62),
                  capIfTypeSerial(64),
                  capIfTypeModem(65),
                  capIfTypeAdapt(66),
                  capIfTypeAdaptd(67),
                  capIfTypeGBEFR(69),
                  capIfTypeVc4(70),
                  capIfTypeVc3(71),
                  capIfTypeSts1(72),
                  capIfTypeEdfa(73),
                  capIfTypeEdfaMid(74),
                  capIfType10Gdw(75),
                  capIfTypeOtu2Lan(76),
                  capIfTypeOtu1Lan(77),
                  capIfTypeOtu1Fc(78),
                  capIfTypeOtu1Fc2G(79),
                  capIfTypeF197(80),
                  capIfTypeTif(81),
                  capIfTypeSts3c(82),
                  capIfTypeVs1(83),
                  capIfType1GbETH(84),
                  capIfTypeStm1(85),
                  capIfTypeStm4(86),
                  capIfTypeOc3(87),
                  capIfTypeOc12(88),
                  capIfTypeOtu1Stm1(89),
                  capIfTypeOtu1Stm4(90),
                  capIfTypeF166(91),
                  capIfTypeF666(92),
                  capIfTypeI2C(93),
                  capIfTypeLifIP(94),
                  capIfTypeSts24c(95),
                  capIfTypeSts48c(96),
                  capIfTypeLifte(97),
                  capIfTypeRaman(98),
                  capIfTypeIpWhiteList(99),
                  capIfTypeOspfIp(100),
                  capIfTypeEncapIp(101),
                  capIfTypeOtu3(102),
                  capIfTypeStm256(103),
                  capIfTypeOc768(104),
                  capIfTypeF10664(105),
                  capIfTypeOdu2(106),
                  capIfTypeF39813(107),
                  capIfTypeVc4c8(108),
                  capIfTypeVc4c16(109),
                  capIfTypeF8500(110),
                  capIfTypePb(111),
                  capIfTypePolicer(112),
                  capIfTypeQueue(113),
                  capIfTypeFlowPoint(114),
                  capIfTypeLag(115),
                  capIfTypeElinePPP(116),
                  capIfTypeEtree(117),
                  capIfTypeEline(118),
                  capIfTypeElan(119),
                  capIfTypeCtrans(120),
                  capIfTypeVs0(121),
                  capIfTypeTug(122),
                  capIfTypeMd(123),
                  capIfTypeMa(124),
                  capIfTypeDownMep(125),
                  capIfTypeFMep(126),
                  capIfType8Gfc(127),
                  capIfType10Gib(128),
                  capIfTypeF10000(129),
                  capIfTypeOtu2pFC8(130),
                  capIfTypeOtu2pIB(131),
                  capIfTypeOtu2pFC(132),
                  capIfTypeOtu2pLAN(133),
                  capIfTypeOtu2p(134),
                  capIfTypeUpMep(135),
                  capIfTypeOtdrCh(136),
                  capIfTypeMaNet(137),
                  capIfTypeMaComp(138),
                  capIfTypeBridge(139),
                  capIfType1000BaseT(140),
                  capIfTypeOtu2E(141),
                  capIfTypeOtu1E(142),
                  capIfTypeOtu2F(143),
                  capIfTypeF11049(144),
                  capIfTypeLifteNum(145),
                  capIfTypeLifteUnn(146),
                  capIfTypeLifPbNum(147),
                  capIfTypeLifSubUnn(148),
                  capIfType5Gib(149),
                  capIfTypeF5000(150),
                  capIfTypeOtu2eEth(151),
                  capIfTypeOdu0(152),
                  capIfTypeFcu(153),
                  capIfTypeOtu4(154),
                  capIfType100GbE(160),
                  capIfTypeOptical(161),
                  capIfType10GbEWan(162),
                  capIfType10GbELan(163),
                  capIfTypeOduFlx(164),
                  capIfTypeOtlc(165),
                  capIfTypeOtu2ps(167),
                  capIfTypeOdu2E(168),
                  capIfTypeOdu1E(169),
                  capIfTypeOdu2Lan(170),
                  capIfTypeOdu4(171),
                  capIfTypeLifVTeNum(173),
                  capIfTypeLifVTeUnn(174),
                  capIfTypeF14025(178),
                  capIfTypeF270(181),
                  capIfTypeF1485(184),
                  capIfTypeF2970(185),
                  capIfTypeF1483(188),
                  capIfTypeF2967(189),
                  capIfType40GbE(192),
                  capIfTypeOdu3(193),
                  capIfTypeF41250(194),
                  capIfTypeF103125(195),
                  capIfTypeF1228(199),
                  capIfTypeF2457(200),
                  capIfTypeF3072(201),
                  capIfTypeF4915(202),
                  capIfTypeF6144(203),
                  capIfTypeF9830(204),
                  capIfTypeF10137(205),
                  capIfTypeAdapt1485(207),
                  capIfTypeAdapt2970(208),
                  capIfTypeOtuC2PA(209),
                  capIfTypeE10to1000t(212),
                  capIfTypeLldp(213)
                }

FspR7Integer32Caps ::= TEXTUAL-CONVENTION
  DISPLAY-HINT "4d:4d"
  STATUS        current
  DESCRIPTION
         "A FspR7Integer32Caps specification.
         1..4 bytes - minValue(Integer32),
         5..8 bytes - maxValue(Integer32)." 
  SYNTAX        OCTET STRING (SIZE(0..8))

FspR7InvertTelemetryInputLogic ::= TEXTUAL-CONVENTION
  STATUS        current
  DESCRIPTION
         "Change telemetry interface input logic" 
  SYNTAX        INTEGER
                {
                  undefined(0),
                  almClosed(1),  --TIF Alarm when the switch is closed
                  almOpen(2)  --TIF Alarm when the switch is open
                }

FspR7InvertTelemetryInputLogicCaps ::= TEXTUAL-CONVENTION
  STATUS        current
  DESCRIPTION
         "Change telemetry interface input logic" 
  SYNTAX        BITS
                {
                  capUndefined(0),
                  capAlmClosed(1),
                  capAlmOpen(2)
                }

FspR7IpMode ::= TEXTUAL-CONVENTION
  STATUS        current
  DESCRIPTION
         "IP Mode of Operation either IPv4 only or IPv4 and IPv6. When operation supports IPv6, it is used for addresses external to the network." 
  SYNTAX        INTEGER
                {
                  undefined(0),
                  none(1),
                  ipv4(2),
                  ipv4ipv6(3),
                  ipv6(4)
                }

FspR7IpModeCaps ::= TEXTUAL-CONVENTION
  STATUS        current
  DESCRIPTION
         "IP Mode of Operation either IPv4 only or IPv4 and IPv6. When operation supports IPv6, it is used for addresses external to the network." 
  SYNTAX        BITS
                {
                  capUndefined(0),
                  capNone(1),
                  capIpv4(2),
                  capIpv4ipv6(3),
                  capIpv6(4)
                }

FspR7IpType ::= TEXTUAL-CONVENTION
  STATUS        current
  DESCRIPTION
         "Type of IP configuration" 
  SYNTAX        INTEGER
                {
                  undefined(0),
                  unnumbered(1),  --No additional IP parameter is needed for ECC Interface; System IP address is used
                  numbered(2)  --Additional IP parameter is needed for ECC Interface; Has to be setted by the user
                }

FspR7IpTypeCaps ::= TEXTUAL-CONVENTION
  STATUS        current
  DESCRIPTION
         "Type of IP configuration" 
  SYNTAX        BITS
                {
                  capUndefined(0),
                  capUnnumbered(1),
                  capNumbered(2)
                }

FspR7L2CacEnable ::= TEXTUAL-CONVENTION
  STATUS        current
  DESCRIPTION
         "Enable of CAC" 
  SYNTAX        INTEGER
                {
                  undefined(0),
                  enable(1),
                  disable(2)
                }

FspR7L2CacEnableCaps ::= TEXTUAL-CONVENTION
  STATUS        current
  DESCRIPTION
         "Enable of CAC" 
  SYNTAX        BITS
                {
                  capUndefined(0),
                  capEnable(1),
                  capDisable(2)
                }

FspR7LacpMode ::= TEXTUAL-CONVENTION
  STATUS        current
  DESCRIPTION
         "Enable of LACP state machine" 
  SYNTAX        INTEGER
                {
                  undefined(0),
                  active(1),
                  passive(2),
                  disable(3)
                }

FspR7LacpModeCaps ::= TEXTUAL-CONVENTION
  STATUS        current
  DESCRIPTION
         "Enable of LACP state machine" 
  SYNTAX        BITS
                {
                  capUndefined(0),
                  capActive(1),
                  capPassive(2),
                  capDisable(3)
                }

FspR7LacpTimeout ::= TEXTUAL-CONVENTION
  STATUS        current
  DESCRIPTION
         "Timeout of the LACP" 
  SYNTAX        INTEGER
                {
                  undefined(0),
                  advaExtraShort(1),
                  short(2),
                  long(3)
                }

FspR7LacpTimeoutCaps ::= TEXTUAL-CONVENTION
  STATUS        current
  DESCRIPTION
         "Timeout of the LACP" 
  SYNTAX        BITS
                {
                  capUndefined(0),
                  capAdvaExtraShort(1),
                  capShort(2),
                  capLong(3)
                }

FspR7LagFendState ::= TEXTUAL-CONVENTION
  STATUS        current
  DESCRIPTION
         "The Partner's state variables for the port, encoded as individual bits,
         as follows:
         Bits ordering:
         - LACP_Activity(0),
         - LACP_Timeout(1),
         - Aggregation(2),
         - Synchronization(3),
         - Collecting(4),
         - Distributing(5),
         - Defaulted(6),
         - Expired(7)" 
  SYNTAX        OCTET STRING (SIZE(0..2))

FspR7LagIdFend ::= TEXTUAL-CONVENTION
  STATUS        current
  DESCRIPTION
         "LAG ID of the Partner LAG PORT parameters. Concatination of
         Operational Key, Priority and port number. Uses 4+2+4 bytes. Each byte is represented
         with 2 octets string.
         
         Port LAG ID Parameters
         field octets contents
         ----- ------ --------
         1_______1-4_____Key___________(ASCII e.g. '0x00AA')
         2_______5-6_____Port Priority_(ASCII e.g. '0x80')
         3_______7-10____Port Number___(ASCII e.g. '0x0002')
         
         Parameters of the LAG ID are separated by commas, e.g. '00AA,80,0002'" 
  SYNTAX        OCTET STRING (SIZE(0..10))

FspR7LagLoadBallanceSource ::= TEXTUAL-CONVENTION
  STATUS        current
  DESCRIPTION
         "What source is used in the load balance calculation" 
  SYNTAX        INTEGER
                {
                  undefined(0),
                  srcMac(1),
                  destMac(2),
                  srcDestMac(3),
                  srcIp(4),
                  destIp(5),
                  srcDestIp(6),
                  vlanId(7)
                }

FspR7LagLoadBallanceSourceCaps ::= TEXTUAL-CONVENTION
  STATUS        current
  DESCRIPTION
         "What source is used in the load balance calculation" 
  SYNTAX        BITS
                {
                  capUndefined(0),
                  capSrcMac(1),
                  capDestMac(2),
                  capSrcDestMac(3),
                  capSrcIp(4),
                  capDestIp(5),
                  capSrcDestIp(6),
                  capVlanId(7)
                }

FspR7LagPorts ::= TEXTUAL-CONVENTION
  STATUS        current
  DESCRIPTION
         "Eeach 4 bytes contain the information about the ETH Client or Network entity.
         Bytes ordering:
         - AidName(0)
         - ShelfNumber(1)
         - SlotNumber(2)
         - PortNumber(3)" 
  SYNTAX        OCTET STRING (SIZE(0..200))

FspR7LagPortType ::= TEXTUAL-CONVENTION
  STATUS        current
  DESCRIPTION
         "Type/Speed of connected ports in the Link Aggregation Group" 
  SYNTAX        INTEGER
                {
                  undefined(0),
                  type1gb(1),
                  type10gb(2)
                }

FspR7LagPortTypeCaps ::= TEXTUAL-CONVENTION
  STATUS        current
  DESCRIPTION
         "Type/Speed of connected ports in the Link Aggregation Group" 
  SYNTAX        BITS
                {
                  capUndefined(0),
                  capType1gb(1),
                  capType10gb(2)
                }

FspR7LagStandby ::= TEXTUAL-CONVENTION
  STATUS        current
  DESCRIPTION
         "Eeach 4 bytes contain the information about the ETH Client or Network entity.
         Bytes ordering:
         - AidName(0)
         - ShelfNumber(1)
         - SlotNumber(2)
         - PortNumber(3)" 
  SYNTAX        OCTET STRING (SIZE(0..200))

FspR7LagState ::= TEXTUAL-CONVENTION
  STATUS        current
  DESCRIPTION
         "The Actors state variables for the port, encoded as individual bits,
         as follows:
         Bits ordering:
         - LACP_Activity(0),
         - LACP_Timeout(1),
         - Aggregation(2),
         - Synchronization(3),
         - Collecting(4),
         - Distributing(5),
         - Defaulted(6),
         - Expired(7)" 
  SYNTAX        OCTET STRING (SIZE(0..2))

FspR7LagSysIdFend ::= TEXTUAL-CONVENTION
  STATUS        current
  DESCRIPTION
         "Partner system part of LAG ID. Concatinated from priority and MAC.
         
         System LAG ID Parameters
         field octets contents
         ----- ------ --------
         1_______1-4_____System Priority__(ASCII e.g. '0x8000')
         2_______5-16____MAC Address______(ASCII e.g. 'AC-DE-48-03-67-80')
         
         Parameters of the LAG ID are separated by commas, e.g. '8000,AC-DE-48-03-67-80'" 
  SYNTAX        OCTET STRING (SIZE(0..16))

FspR7LaneGroupInventory ::= TEXTUAL-CONVENTION
  STATUS        current
  DESCRIPTION
         "Lanel Group read from the hardware" 
  SYNTAX        INTEGER
                {
                  undefined(0),
                  f19595f19520(1),  --tunable CFP part of C-band
                  f19515f19440(2),  --tunable CFP part of C-band
                  f19435f19360(3),  --tunable CFP part of C-band
                  f19355f19280(4),  --tunable CFP part of C-band
                  f19275f19200(5),  --tunable CFP part of C-band
                  f19600f19200(6),  --tunable CFP part of C-band
                  f19600f19125(7),  --tunable CFP C-band
                  f19597f19122(8),  --tunable CFP C-band
                  f19600f19570(9),  --fix CFP
                  f19560f19530(10),  --fix CFP
                  f19520f19490(11),  --fix CFP
                  f19480f19450(12),  --fix CFP
                  f19440f19410(13),  --fix CFP
                  f19400f19370(14),  --fix CFP
                  f19360f19330(15),  --fix CFP
                  f19320f19290(16),  --fix CFP
                  f19280f19250(17),  --fix CFP
                  f19240f19210(18),  --fix CFP
                  f19200f19170(19),  --fix CFP
                  f19160f19130(20),  --fix CFP
                  f19595f19565(21),  --fix CFP
                  f19555f19525(22),  --fix CFP
                  f19515f19485(23),  --fix CFP
                  f19475f19445(24),  --fix CFP
                  f19435f19405(25),  --fix CFP
                  f19395f19365(26),  --fix CFP
                  f19355f19325(27),  --fix CFP
                  f19315f19285(28),  --fix CFP
                  f19275f19245(29),  --fix CFP
                  f19235f19205(30),  --fix CFP
                  f19195f19165(31),  --fix CFP
                  f19155f19125(32)  --fix CFP
                }

FspR7LaneGroupInventoryCaps ::= TEXTUAL-CONVENTION
  STATUS        current
  DESCRIPTION
         "Lanel Group read from the hardware" 
  SYNTAX        BITS
                {
                  capUndefined(0),
                  capF19595f19520(1),
                  capF19515f19440(2),
                  capF19435f19360(3),
                  capF19355f19280(4),
                  capF19275f19200(5),
                  capF19600f19200(6),
                  capF19600f19125(7),
                  capF19597f19122(8),
                  capF19600f19570(9),
                  capF19560f19530(10),
                  capF19520f19490(11),
                  capF19480f19450(12),
                  capF19440f19410(13),
                  capF19400f19370(14),
                  capF19360f19330(15),
                  capF19320f19290(16),
                  capF19280f19250(17),
                  capF19240f19210(18),
                  capF19200f19170(19),
                  capF19160f19130(20),
                  capF19595f19565(21),
                  capF19555f19525(22),
                  capF19515f19485(23),
                  capF19475f19445(24),
                  capF19435f19405(25),
                  capF19395f19365(26),
                  capF19355f19325(27),
                  capF19315f19285(28),
                  capF19275f19245(29),
                  capF19235f19205(30),
                  capF19195f19165(31),
                  capF19155f19125(32)
                }

FspR7LaserDelayTimer ::= TEXTUAL-CONVENTION
  STATUS        current
  DESCRIPTION
         "Relevant only when ERRFWD=LSROFF. Enables/disables the
         possibility to delay turning off and on the laser.
         This applies to the case when turning off the laser
         is done as an error forwarding mechanism." 
  SYNTAX        INTEGER
                {
                  undefined(0),
                  disable(1),
                  enableLsrOffTm(2),
                  enableLsrOnTm(3)
                }

FspR7LaserDelayTimerCaps ::= TEXTUAL-CONVENTION
  STATUS        current
  DESCRIPTION
         "Relevant only when ERRFWD=LSROFF. Enables/disables the
         possibility to delay turning off and on the laser.
         This applies to the case when turning off the laser
         is done as an error forwarding mechanism." 
  SYNTAX        BITS
                {
                  capUndefined(0),
                  capDisable(1),
                  capEnableLsrOffTm(2),
                  capEnableLsrOnTm(3)
                }

FspR7LaserForcedOperation ::= TEXTUAL-CONVENTION
  STATUS        current
  DESCRIPTION
         "FspR7LaserForcedOperation variable." 
  SYNTAX        INTEGER
                {
                  undefined(0),
                  rls(1),
                  opr(2)
                }

FspR7LaserForcedOperationCaps ::= TEXTUAL-CONVENTION
  STATUS        current
  DESCRIPTION
         "FspR7LaserForcedOperation variable." 
  SYNTAX        BITS
                {
                  capUndefined(0),
                  capRls(1),
                  capOpr(2)
                }

FspR7LaserOffDelayTime ::= TEXTUAL-CONVENTION
  STATUS        current
  DESCRIPTION
         "Hold-Off Period for Error Forwarding LKDO-OFF Consequent Action." 
  SYNTAX        INTEGER
                {
                  undefined(0),
                  del0ms(1),  --DEPLOY=CLIENTP or special services like Fiber Channel which needs immediate resynchronisation or LSROFFDLY=DISABLE.
                  del10ms(2),  --Channel and Channel Card (if fast enough) Protection.
                  del250ms(3)  --Unprotected or Versatile Switched Protection (at the moment)
                }

FspR7LaserOffDelayTimeCaps ::= TEXTUAL-CONVENTION
  STATUS        current
  DESCRIPTION
         "Hold-Off Period for Error Forwarding LKDO-OFF Consequent Action." 
  SYNTAX        BITS
                {
                  capUndefined(0),
                  capDel0ms(1),
                  capDel10ms(2),
                  capDel250ms(3)
                }

FspR7LifeCycle ::= TEXTUAL-CONVENTION
  STATUS        current
  DESCRIPTION
         "Defines time period where tunnels must be kept separate from the reference tunnel." 
  SYNTAX        INTEGER
                {
                  undefined(0),
                  setup(1),
                  life(2)
                }

FspR7LineCoding ::= TEXTUAL-CONVENTION
  STATUS        current
  DESCRIPTION
         "Line Coding" 
  SYNTAX        INTEGER
                {
                  undefined(0),
                  ookNrz(1),
                  dpsk(2),
                  qpsk(3),
                  dpQpsk(4),
                  odbPsbt(5),
                  mQam(6),
                  ofdm(7),
                  notDefined(99)
                }

FspR7LineCodingCaps ::= TEXTUAL-CONVENTION
  STATUS        current
  DESCRIPTION
         "Line Coding" 
  SYNTAX        BITS
                {
                  capUndefined(0),
                  capOokNrz(1),
                  capDpsk(2),
                  capQpsk(3),
                  capDpQpsk(4),
                  capOdbPsbt(5),
                  capMQam(6),
                  capOfdm(7),
                  capNotDefined(99)
                }

FspR7LossAttenuation ::= TEXTUAL-CONVENTION
  STATUS        current
  DESCRIPTION
         "LOS Attenuation Finding in progress" 
  SYNTAX        INTEGER
                {
                  undefined(0),
                  rls(1),
                  opr(2)
                }

FspR7LossAttenuationCaps ::= TEXTUAL-CONVENTION
  STATUS        current
  DESCRIPTION
         "LOS Attenuation Finding in progress" 
  SYNTAX        BITS
                {
                  capUndefined(0),
                  capRls(1),
                  capOpr(2)
                }

FspR7ManualAuto ::= TEXTUAL-CONVENTION
  STATUS        current
  DESCRIPTION
         "Manual/Automatic variable." 
  SYNTAX        INTEGER

                {
                  undefined(0),
                  manual(1),
                  automatic(2)
                }

FspR7ManualAutoCaps ::= TEXTUAL-CONVENTION
  STATUS        current
  DESCRIPTION
         "Manual/Automatic variable." 
  SYNTAX        BITS
                {
                  capUndefined(0),
                  capManual(1),
                  capAutomatic(2)
                }

FspR7Mapping ::= TEXTUAL-CONVENTION
  STATUS        current
  DESCRIPTION
         "Type of mapping; transparent or framing" 
  SYNTAX        INTEGER
                {
                  undefined(0),
                  frame(1),
                  trans(2)
                }

FspR7MappingCaps ::= TEXTUAL-CONVENTION
  STATUS        current
  DESCRIPTION
         "Type of mapping; transparent or framing" 
  SYNTAX        BITS
                {
                  capUndefined(0),
                  capFrame(1),
                  capTrans(2)
                }

FspR7MaxBitErrorRate ::= TEXTUAL-CONVENTION
  STATUS        current
  DESCRIPTION
         "Maximum Bit Error Rate" 
  SYNTAX        INTEGER
                {
                  undefined(0),
                  ber1e2(1),
                  ber1e3(2),
                  ber1e4(3),
                  ber1e5(4),
                  ber1e6(5),
                  ber1e7(6),
                  ber1e8(7),
                  ber1e9(8),
                  ber1e10(9),
                  ber1e11(10),
                  ber1e12(11),
                  ber1e13(12),
                  ber1e14(13),
                  ber1e15(14)
                }

FspR7MaxBitErrorRateCaps ::= TEXTUAL-CONVENTION
  STATUS        current
  DESCRIPTION
         "Maximum Bit Error Rate" 
  SYNTAX        BITS
                {
                  capUndefined(0),
                  capBer1e2(1),
                  capBer1e3(2),
                  capBer1e4(3),
                  capBer1e5(4),
                  capBer1e6(5),
                  capBer1e7(6),
                  capBer1e8(7),
                  capBer1e9(8),
                  capBer1e10(9),
                  capBer1e11(10),
                  capBer1e12(11),
                  capBer1e13(12),
                  capBer1e14(13),
                  capBer1e15(14)
                }

FspR7ModeDbInit ::= TEXTUAL-CONVENTION
  STATUS        current
  DESCRIPTION
         "Mode of Database Initialisation at Time of Last Start / Restart" 
  SYNTAX        INTEGER
                {
                  undefined(0),
                  none(1),
                  restore(2),
                  startUpDefault(3),
                  startUpEqpt(4)
                }

FspR7Model ::= TEXTUAL-CONVENTION
  STATUS        current
  DESCRIPTION
         "Marketing model name of System" 
  SYNTAX        INTEGER
                {
                  undefined(0),
                  fsp3000R7(1),
                  flashwave74200(2),
                  ots1000(3)
                }

FspR7ModusLastRestart ::= TEXTUAL-CONVENTION
  STATUS        current
  DESCRIPTION
         "Information over the modus of the last restart" 
  SYNTAX        INTEGER
                {
                  undefined(0),
                  reload(1),
                  cold(2),
                  warm(3)
                }

FspR7MonLevel ::= TEXTUAL-CONVENTION
  STATUS        current
  DESCRIPTION
         "Highest signal level of intrusive or non-intrusive monitoring. Hardware may monitor the signal one layer higher than Termination Level (TERM)." 
  SYNTAX        INTEGER
                {
                  undefined(0),
                  phys(1),
                  otnOtu(2),
                  otnOdu(3),
                  otnOpu(4),
                  sonetSection(5),
                  sonetLine(6),
                  sonetPath(7),
                  pcs(8),
                  hoOdu(9)
                }

FspR7NCTraceId ::= TEXTUAL-CONVENTION
  STATUS        current
  DESCRIPTION
         "Node Channel Trace ID - It associates each direction of a channel trace through a node." 
  SYNTAX        INTEGER
                {
                  undefined(0),
                  id1(1),
                  id2(2),
                  id3(3),
                  id4(4),
                  id5(5),
                  id6(6),
                  id7(7),
                  id8(8)
                }

FspR7NCTRouteType ::= TEXTUAL-CONVENTION
  STATUS        current
  DESCRIPTION
         "ROUTE-TYPE = NONE | FIBER | CABLE | BKPLANE | EQPT | PROVND. ROUTE-TYPE 
          parameter indicates the connection type between two ports. If a connection 
          between the two ports is within a module (i.e. Client to Network port), 
          the Route-Type is either provisioned (PROVND) of fixed (EQPT). If the 
          connection is between two ports, then the Route-Type is FIBER, or CABLE,
          or BKPLANE." 
  SYNTAX        INTEGER                {
                  undefined(0),
                  none(1),  --No connection between ports
                  fiber(2),  --Connection between ports is a fiber optic cable
                  cable(3),  --Connection between ports is an electrical cable
                  backPlane(4),  --Connection between ports or modules is through Backplane
                  equipment(5),  --Connection between ports on the same module cannot be changed (not affected by provisioning).
                  provisioned(6)  --Connection between ports on the same module is determined by provisional parameter(s) (mode, channel, cross-connect, etc.)
                }

FspR7NeType ::= TEXTUAL-CONVENTION
  STATUS        current
  DESCRIPTION
         "Type of Network Element" 
  SYNTAX        INTEGER
                {
                  undefined(0),
                  wdm(1)
                }

FspR7NodeId ::= TEXTUAL-CONVENTION
  STATUS        current
  DESCRIPTION
         "Node Name Syntax" 
  SYNTAX        INTEGER
                {
                  undefined(0),
                  tid(1),
                  ip(2)
                }

FspR7NodeIdCaps ::= TEXTUAL-CONVENTION
  STATUS        current
  DESCRIPTION
         "Node Name Syntax" 
  SYNTAX        BITS
                {
                  capUndefined(0),
                  capTid(1),
                  capIp(2)
                }

FspR7NoYes ::= TEXTUAL-CONVENTION
  STATUS        current
  DESCRIPTION
         "NoYes variable." 
  SYNTAX        INTEGER

                {
                  undefined(0),
                  no(1),
                  yes(2)
                }

FspR7NoYesCaps ::= TEXTUAL-CONVENTION
  STATUS        current
  DESCRIPTION
         "NoYes variable." 
  SYNTAX        BITS
                {
                  capUndefined(0),
                  capNo(1),
                  capYes(2)
                }

FspR7NtpAdminState ::= TEXTUAL-CONVENTION
  STATUS        current
  DESCRIPTION
         "The Administrative State of the NTP server" 
  SYNTAX        INTEGER
                {
                  undefined(0),
                  is(2),
                  dsbld(6)
                }

FspR7NtpMode ::= TEXTUAL-CONVENTION
  STATUS        current
  DESCRIPTION
         "NTP Service Mode" 
  SYNTAX        INTEGER
                {
                  undefined(0),
                  ntpOff(1),  --NTP is switched off
                  ntpClientOnly(2),  --Doesn't provide service, clock source one or more NTP servers
                  ntpServerOnly(3),  --Provides service, clock source local
                  ntpRelay(4)  --Provides service, clock source one or more NTP servers
                }

FspR7NtpServerStatus ::= TEXTUAL-CONVENTION
  STATUS        current
  DESCRIPTION
         "NTP server status" 
  SYNTAX        INTEGER
                {
                  undefined(0),
                  unreachable(1),
                  reachable(2)
                }

FspR7NtpSyncStatus ::= TEXTUAL-CONVENTION
  STATUS        current
  DESCRIPTION
         "NTP Synchronization Status" 
  SYNTAX        INTEGER
                {
                  undefined(0),
                  noData(1),
                  systemPeer(2),
                  falseTicker(3),
                  candidate(4),
                  discarded(5),
                  inProgress(6),
                  notApplicable(7)
                }

FspR7NtpTest ::= TEXTUAL-CONVENTION
  STATUS        current
  DESCRIPTION
         "Check NTP; e.g. listen on NTP Port" 
  SYNTAX        INTEGER
                {
                  undefined(0),
                  rls(1),
                  ntpTest(2)
                }

FspR7NtpTestStatus ::= TEXTUAL-CONVENTION
  STATUS        current
  DESCRIPTION
         "NTP Server Test Status" 
  SYNTAX        INTEGER
                {
                  undefined(0),
                  success(1),
                  fail(2),
                  idle(3),
                  inProgress(4)
                }

FspR7NumberOfChannels ::= TEXTUAL-CONVENTION
  STATUS        current
  DESCRIPTION
         "Number of channels supported by an entity" 
  SYNTAX        INTEGER
                {
                  undefined(0),
                  channels20(1),
                  channels40(2),
                  channels80(3),
                  channels96(4),
                  channels8(5),
                  channels192(7)
                }

FspR7NumberOfChannelsCaps ::= TEXTUAL-CONVENTION
  STATUS        current
  DESCRIPTION
         "Number of channels supported by an entity" 
  SYNTAX        BITS
                {
                  capUndefined(0),
                  capChannels20(1),
                  capChannels40(2),
                  capChannels80(3),
                  capChannels96(4),
                  capChannels8(5),
                  capChannels192(7)
                }

FspR7OdtuType ::= TEXTUAL-CONVENTION
  STATUS        current
  DESCRIPTION
         "ODTU Transport Unit" 
  SYNTAX        INTEGER
                {
                  undefined(0),
                  odtu01(1),
                  odtu12(2),
                  odtu2dsh1(3),
                  odtu2dshTS(4),
                  odtu13(5),
                  odtu23(6),
                  odtu3dsh1(7),
                  odtu3dsh9(8),
                  odtu3dshTS(9),
                  odtu4dsh1(10),
                  odtu4dsh2(11),
                  odtu4dsh8(12),
                  odtu4dsh31(13),
                  odtu4dshTS(14)
                }

FspR7OdtuTypeCaps ::= TEXTUAL-CONVENTION
  STATUS        current
  DESCRIPTION
         "ODTU Transport Unit" 
  SYNTAX        BITS
                {
                  capUndefined(0),
                  capOdtu01(1),
                  capOdtu12(2),
                  capOdtu2dsh1(3),
                  capOdtu2dshTS(4),
                  capOdtu13(5),
                  capOdtu23(6),
                  capOdtu3dsh1(7),
                  capOdtu3dsh9(8),
                  capOdtu3dshTS(9),
                  capOdtu4dsh1(10),
                  capOdtu4dsh2(11),
                  capOdtu4dsh8(12),
                  capOdtu4dsh31(13),
                  capOdtu4dshTS(14)
                }

FspR7OperState ::= TEXTUAL-CONVENTION
  STATUS        current
  DESCRIPTION
         "The Operational State will be displayed on the
         GUI with full name values; it will be differently
         displayed in TL1 syntax according to TL1 display rules." 
  SYNTAX        INTEGER
                {
                  undefined(0),
                  nr(1),
                  anr(2),
                  out(3),
                  un(4)
                }

FspR7OpticalBand ::= TEXTUAL-CONVENTION
  STATUS        current
  DESCRIPTION
         "OM Band - Inventory. BAND__PROVISION references to this." 
  SYNTAX        INTEGER
                {
                  undefined(0),
                  bandC(1),
                  bandL(2),
                  bandA(3),
                  bandB(4),
                  -- bandAny(5),
                  bandCi(5),
                  bandCandCi(6)
                }

FspR7OpticalBandCaps ::= TEXTUAL-CONVENTION
  STATUS        current
  DESCRIPTION
         "OM Band - Inventory. BAND__PROVISION references to this." 
  SYNTAX        BITS
                {
                  capUndefined(0),
                  capBandC(1),
                  capBandL(2),
                  capBandA(3),
                  capBandB(4),
                  -- capBandAny(5),
                  capBandCi(5),
                  capBandCandCi(6)
                }

FspR7OpticalFiberType ::= TEXTUAL-CONVENTION
  STATUS        current
  DESCRIPTION
         "Fiber of Optical Interface - Inventory. FIBER references to this." 
  SYNTAX        INTEGER
                {
                  undefined(0),
                  singleMode(1),
                  multiMode(2),
                  any(3)
                }

FspR7OpticalFiberTypeCaps ::= TEXTUAL-CONVENTION
  STATUS        current
  DESCRIPTION
         "Fiber of Optical Interface - Inventory. FIBER references to this." 
  SYNTAX        BITS
                {
                  capUndefined(0),
                  capSingleMode(1),
                  capMultiMode(2),
                  capAny(3)
                }

FspR7OpticalGroup ::= TEXTUAL-CONVENTION
  STATUS        current
  DESCRIPTION
         "Channel Group read from the hardware" 
  SYNTAX        INTEGER
                {
                  undefined(0),
                  d01d04(1),
                  d05d08(2),
                  d09d12(3),
                  d13d16(4),
                  d17d20(5),
                  d21d24(6),
                  d25d28(7),
                  d29d32(8),
                  d33d36(9),
                  d37d40(10),
                  d41d44(11),
                  d45d48(12),
                  d49d52(13),
                  d53d56(14),
                  d57d60(15),
                  d61d64(16),
                  -- any(17),
                  f19590f19560(17),
                  f19550f19520(18),
                  f19510f19480(19),
                  f19470f19440(20),
                  f19430f19400(21),
                  f19390f19360(22),
                  f19350f19320(23),
                  f19310f19280(24),
                  f19270f19240(25),
                  f19230f19200(26),
                  f19590f19520(27),  --D02-D04, DC1, D05-D08
                  f19510f19440(28),  --DC2, D09-D12, DC3, D13-D14
                  f19430f19360(29),  --D15-D16, DC4, DC9, D17-D19
                  f19350f19280(30),  --D2, DC6, D21-D24, DC7, D25
                  f19270f19200(31),  --D26-D28, DC8, D29-D32
                  f19590f19500(32),
                  f19350f19260(34)
                }

FspR7OpticalGroupCaps ::= TEXTUAL-CONVENTION
  STATUS        current
  DESCRIPTION
         "Channel Group read from the hardware" 
  SYNTAX        BITS
                {
                  capUndefined(0),
                  capD01d04(1),
                  capD05d08(2),
                  capD09d12(3),
                  capD13d16(4),
                  capD17d20(5),
                  capD21d24(6),
                  capD25d28(7),
                  capD29d32(8),
                  capD33d36(9),
                  capD37d40(10),
                  capD41d44(11),
                  capD45d48(12),
                  capD49d52(13),
                  capD53d56(14),
                  capD57d60(15),
                  capD61d64(16),
                  -- capAny(17),
                  capF19590f19560(17),
                  capF19550f19520(18),
                  capF19510f19480(19),
                  capF19470f19440(20),
                  capF19430f19400(21),
                  capF19390f19360(22),
                  capF19350f19320(23),
                  capF19310f19280(24),
                  capF19270f19240(25),
                  capF19230f19200(26),
                  capF19590f19520(27),
                  capF19510f19440(28),
                  capF19430f19360(29),
                  capF19350f19280(30),
                  capF19270f19200(31),
                  capF19590f19500(32),
                  capF19350f19260(34)
                }

FspR7OpticalInterfaceReach ::= TEXTUAL-CONVENTION
  STATUS        current
  DESCRIPTION
         "Reach" 
  SYNTAX        INTEGER
                {
                  undefined(0),
                  intra(1),  --0.5 - <5 km;  850nm;  MM fiber
                  short(2),  --5 - <30 km;  1310nm;  SM fiber
                  long(4),  --30 - <70 km;  1550nm;  SM fiber
                  vlong(5),  --70 - <110 km;  15xx;  SM fiber
                  ulong(6),  --110 - <165 km;  SM fiber
                  reg(7),  --290 - <360 km;  SM fiber
                  xlong(8),  --360 - <600 km;  SM fiber
                  -- any(9),
                  longn(10),  --30 - <70 km;  15xx;  SM fiber
                  extended(11),  --165 - <220 km;  SM fiber
                  hyperlong(12),  --220 - <290 km;  SM fiber
                  longNR(13),  --30 - <70 km; 15xx;  SM fiber
                  ulongHaul(14),  --500 - <2500 km 
                  shortIntra(15),  --0 - <500 m;  850nm;  MM fiber
                  ulongHaulC(16),  --500 - <2500 km 
                  longR(17),  --20-40 km; 1550nm; SM fiber
                  vlongX(18),  --85 - <125 km;  1550nm;  SM fiber
                  vshort(19)  --0 - <5 km; 1310nm; SM fiber
                }

FspR7OpticalInterfaceReachCaps ::= TEXTUAL-CONVENTION
  STATUS        current
  DESCRIPTION
         "Reach" 
  SYNTAX        BITS
                {
                  capUndefined(0),
                  capIntra(1),
                  capShort(2),
                  capLong(4),
                  capVlong(5),
                  capUlong(6),
                  capReg(7),
                  capXlong(8),
                  -- capAny(9),
                  capLongn(10),
                  capExtended(11),
                  capHyperlong(12),
                  capLongNR(13),
                  capUlongHaul(14),
                  capShortIntra(15),
                  capUlongHaulC(16),
                  capLongR(17),
                  capVlongX(18),
                  capVshort(19)
                }

FspR7OpticalLanes ::= TEXTUAL-CONVENTION
  STATUS        current
  DESCRIPTION
         "Number of Optical Transport Lanes in OTLG" 
  SYNTAX        INTEGER
                {
                  undefined(0),
                  lanesNumber4(1)
                }

FspR7OpticalMultiplexLevel ::= TEXTUAL-CONVENTION
  STATUS        current
  DESCRIPTION
         "Optical Multiplex Level" 
  SYNTAX        INTEGER
                {
                  undefined(0),
                  levelOm1D(1),
                  levelOm1C(2),
                  levelOm4D(3),
                  levelOm4C(4),
                  levelOm16D(5),
                  levelOm32D(6),
                  levelOm40D(7),
                  levelOmC(9),
                  levelOmD(10),
                  levelOtD(11),
                  levelOtC(12),
                  levelOt(13)
                }

FspR7OpticalSubBand ::= TEXTUAL-CONVENTION
  STATUS        current
  DESCRIPTION
         "Subband - Inventory" 
  SYNTAX        INTEGER
                {
                  undefined(0),
                  d01d16(1),
                  d17d32(2),
                  d33d48(3),
                  d49d64(4)
                  -- subBandAny(5)
                }

FspR7OpticalSubBandCaps ::= TEXTUAL-CONVENTION
  STATUS        current
  DESCRIPTION
         "Subband - Inventory" 
  SYNTAX        BITS
                {
                  capUndefined(0),
                  capD01d16(1),
                  capD17d32(2),
                  capD33d48(3),
                  capD49d64(4)
                  -- capSubBandAny(5)
                }

FspR7OpuPayloadType ::= TEXTUAL-CONVENTION
  STATUS        current
  DESCRIPTION
         "OPU Payload Type Indicator" 
  SYNTAX        INTEGER
                {
                  undefined(0),
                  pt01(1),  --Experimental mapping
                  pt02(2),  --Asynchronous CBR mapping
                  pt03(3),  --Bit synchronous CBR mapping
                  pt04(4),  --ATM mapping
                  pt05(5),  --GFP mapping
                  pt06(6),  --Virtual Concatenated signal
                  pt07(7),  --1000Base-X into ODU0 mapping
                  pt08(8),  --FC-1200 into ODU2e mapping
                  pt09(9),  --GFP mapping into Extended OPU2 payload
                  pt0A(10),  --STM-1 mapping into ODU0
                  pt0B(11),  --STM-4 mapping into ODU0
                  pt0C(12),  --FC-100 mapping into ODU0
                  pt0D(13),  --FC-200 mapping into ODU1
                  pt0E(14),  --FC-400 mapping into ODUflex
                  pt0F(15),  --FC-800 mapping into ODUflex
                  pt10(16),  --Bit stream with octet timing mapping
                  pt11(17),  --Bit stream without octet timing mapping
                  pt20(18),  --ODU multiplex structure supporting ODTUjk only, (AMP only)
                  pt21(19),  --ODU multiplex structure supporting ODTUk.ts or ODTUk.ts and ODTUjk, (GMP capable)
                  pt80(20),  --Reserved codes for proprietary use
                  pt81(21),  --Reserved codes for proprietary use
                  pt82(22),  --Reserved codes for proprietary use
                  pt83(23),  --Reserved codes for proprietary use
                  pt84(24),  --Reserved codes for proprietary use
                  pt85(25),  --Reserved codes for proprietary use
                  pt86(26),  --Reserved codes for proprietary use
                  pt87(27),  --Reserved codes for proprietary use
                  pt88(28),  --Reserved codes for proprietary use
                  pt89(29),  --Reserved codes for proprietary use
                  pt8A(30),  --Reserved codes for proprietary use
                  pt8B(31),  --Reserved codes for proprietary use
                  pt8C(32),  --Reserved codes for proprietary use
                  pt8D(33),  --Reserved codes for proprietary use
                  pt8E(34),  --Reserved codes for proprietary use
                  pt8F(35),  --Reserved codes for proprietary use
                  ptFD(36),  --NULL test signal mapping
                  ptFE(37),  --PRBS test signal mapping
                  pt8X(38)
                }

FspR7OpuPayloadTypeCaps ::= TEXTUAL-CONVENTION
  STATUS        current
  DESCRIPTION
         "OPU Payload Type Indicator" 
  SYNTAX        BITS
                {
                  capUndefined(0),
                  capPt01(1),
                  capPt02(2),
                  capPt03(3),
                  capPt04(4),
                  capPt05(5),
                  capPt06(6),
                  capPt07(7),
                  capPt08(8),
                  capPt09(9),
                  capPt0A(10),
                  capPt0B(11),
                  capPt0C(12),
                  capPt0D(13),
                  capPt0E(14),
                  capPt0F(15),
                  capPt10(16),
                  capPt11(17),
                  capPt20(18),
                  capPt21(19),
                  capPt80(20),
                  capPt81(21),
                  capPt82(22),
                  capPt83(23),
                  capPt84(24),
                  capPt85(25),
                  capPt86(26),
                  capPt87(27),
                  capPt88(28),
                  capPt89(29),
                  capPt8A(30),
                  capPt8B(31),
                  capPt8C(32),
                  capPt8D(33),
                  capPt8E(34),
                  capPt8F(35),
                  capPtFD(36),
                  capPtFE(37),
                  capPt8X(38)
                }

FspR7OspfAreaType ::= TEXTUAL-CONVENTION
  STATUS        current
  DESCRIPTION
         "Area Type" 
  SYNTAX        INTEGER
                {
                  undefined(0),
                  stub(1),
                  normal(2)
                }

FspR7OspfAreaTypeCaps ::= TEXTUAL-CONVENTION
  STATUS        current
  DESCRIPTION
         "Area Type" 
  SYNTAX        BITS
                {
                  capUndefined(0),
                  capStub(1),
                  capNormal(2)
                }

FspR7OspfMode ::= TEXTUAL-CONVENTION
  STATUS        current
  DESCRIPTION
         "OSPF Routing (Dynamic)" 
  SYNTAX        INTEGER
                {
                  undefined(0),
                  enable(1),
                  disable(2),
                  passive(3)
                }

FspR7OspfModeCaps ::= TEXTUAL-CONVENTION
  STATUS        current
  DESCRIPTION
         "OSPF Routing (Dynamic)" 
  SYNTAX        BITS
                {
                  capUndefined(0),
                  capEnable(1),
                  capDisable(2),
                  capPassive(3)
                }

FspR7OscChannel ::= TEXTUAL-CONVENTION
  STATUS        current
  DESCRIPTION
         "OSC Channel" 
  SYNTAX        INTEGER
                {
                  undefined(0),
                  s1310(99),
                  s1630(100),
                  s1510(106),
                  s1610(197)
                }

FspR7OscChannelCaps ::= TEXTUAL-CONVENTION
  STATUS        current
  DESCRIPTION
         "OSC Channel" 
  SYNTAX        BITS
                {
                  capUndefined(0),
                  capS1310(99),
                  capS1630(100),
                  capS1510(106),
                  capS1610(197)
                }

FspR7OscUsage ::= TEXTUAL-CONVENTION
  STATUS        current
  DESCRIPTION
         "Select if and how the OSC is to be used on an amplifier" 
  SYNTAX        INTEGER
                {
                  undefined(0),
                  none(1),  --No OSC usage
                  osctxctrl(2),  --Use the OSC Tx Control
                  oscrx(3),  --Use the OSC Rx
                  osctxandrx(4)  --Use OSC Tx and Rx
                }

FspR7OscUsageCaps ::= TEXTUAL-CONVENTION
  STATUS        current
  DESCRIPTION
         "Select if and how the OSC is to be used on an amplifier" 
  SYNTAX        BITS
                {
                  capUndefined(0),
                  capNone(1),
                  capOsctxctrl(2),
                  capOscrx(3),
                  capOsctxandrx(4)
                }

FspR7OtdrPeriod ::= TEXTUAL-CONVENTION
  STATUS        current
  DESCRIPTION
         "NONE - OTDR measurement disabled otherwise the OTDR duration in minutes." 
  SYNTAX        INTEGER
                {
                  undefined(0),
                  periodNone(1),
                  period5ms(2),
                  period20ms(3),
                  period40ms(4),
                  period60ms(5)
                }

FspR7Overwrite ::= TEXTUAL-CONVENTION
  STATUS        current
  DESCRIPTION
         "Maximum allowed file access attribute." 
  SYNTAX        INTEGER
                {
                  undefined(0),
                  no(1),
                  yes(2)
                }

FspR7PacketsLayer ::= TEXTUAL-CONVENTION
  STATUS        current
  DESCRIPTION
         "Notional Layer of Advertisement on Packets on the LIF" 
  SYNTAX        INTEGER
                {
                  undefined(0),
                  lambda(1),  --Lambda Switching Capable
                  fiber(2),  --Fiber Switching Capable
                  tdm(3),  --TDM Switching Capable
                  psc1(4),  --Packet Switching Capable 1
                  psc2(5),  --Packet Switching Capable 2
                  psc3(6),  --Packet Switching Capable 3
                  psc4(7),  --Packet Switching Capable 4
                  l2sc(8),  --Layer-2 Switching Capable
                  ethSvlan(9),  --ETH S-tagged VLAN Switching Capable
                  unspecified(10),  --No Switching Capability specified for this Tunnel
                  subLsc(11),  --Sub-Lambda Switching Capable
                  dcsc(12),  --Data Channel Switching Capable
                  otn(13)  --OTN Switching Capable
                }

FspR7PacketsLayerCaps ::= TEXTUAL-CONVENTION
  STATUS        current
  DESCRIPTION
         "Notional Layer of Advertisement on Packets on the LIF" 
  SYNTAX        BITS
                {
                  capUndefined(0),
                  capLambda(1),
                  capFiber(2),
                  capTdm(3),
                  capPsc1(4),
                  capPsc2(5),
                  capPsc3(6),
                  capPsc4(7),
                  capL2sc(8),
                  capEthSvlan(9),
                  capUnspecified(10),
                  capSubLsc(11),
                  capDcsc(12),
                  capOtn(13)
                }

FspR7ParityBit ::= TEXTUAL-CONVENTION
  STATUS        current
  DESCRIPTION
         "Parity Bit Settings" 
  SYNTAX        INTEGER
                {
                  undefined(0),
                  no(1)
                }

FspR7PathNode ::= TEXTUAL-CONVENTION
  STATUS        current
  DESCRIPTION
         "Node count along a signal path on a unidirectional basis from the client signal ingress to egress" 
  SYNTAX        INTEGER
                {
                  undefined(0),
                  node1(1),
                  node2(2),
                  node3(3),
                  node4(4),
                  node5(5),
                  node6(6),
                  node7(7),
                  node8(8),
                  node9(9),
                  node10(10),
                  node11(11),
                  node12(12),
                  node13(13),
                  node14(14),
                  node15(15),
                  node16(16),
                  node17(17),
                  node18(18),
                  node19(19),
                  node20(20),
                  node21(21),
                  node22(22),
                  node23(23),
                  node24(24),
                  node25(25),
                  node26(26),
                  node27(27),
                  node28(28),
                  node29(29),
                  node30(30),
                  node31(31),
                  node32(32),
                  node33(33),
                  node34(34),
                  node35(35),
                  node36(36),
                  node37(37),
                  node38(38),
                  node39(39),
                  node40(40),
                  node41(41),
                  node42(42),
                  node43(43),
                  node44(44),
                  node45(45),
                  node46(46),
                  node47(47),
                  node48(48),
                  node49(49),
                  node50(50),
                  node51(51),
                  node52(52),
                  node53(53),
                  node54(54),
                  node55(55),
                  node56(56),
                  node57(57),
                  node58(58),
                  node59(59),
                  node60(60),
                  node61(61),
                  node62(62),
                  node63(63),
                  node64(64),
                  node65(65),
                  node66(66),
                  node67(67),
                  node68(68),
                  node69(69),
                  node70(70),
                  node71(71),
                  node72(72),
                  node73(73),
                  node74(74),
                  node75(75),
                  node76(76),
                  node77(77),
                  node78(78),
                  node79(79),
                  node80(80),
                  node81(81),
                  node82(82),
                  node83(83),
                  node84(84),
                  node85(85),
                  node86(86),
                  node87(87),
                  node88(88),
                  node89(89),
                  node90(90),
                  node91(91),
                  node92(92),
                  node93(93),
                  node94(94),
                  node95(95),
                  node96(96),
                  node97(97),
                  node98(98),
                  node99(99),
                  node100(100),
                  node101(101),
                  node102(102),
                  node103(103),
                  node104(104),
                  node105(105),
                  node106(106),
                  node107(107),
                  node108(108),
                  node109(109),
                  node110(110),
                  node111(111),
                  node112(112),
                  node113(113),
                  node114(114),
                  node115(115),
                  node116(116),
                  node117(117),
                  node118(118)
                }

FspR7PathNodeCaps ::= TEXTUAL-CONVENTION
  STATUS        current
  DESCRIPTION
         "Node count along a signal path on a unidirectional basis from the client signal ingress to egress" 
  SYNTAX        BITS
                {
                  capUndefined(0),
                  capNode1(1),
                  capNode2(2),
                  capNode3(3),
                  capNode4(4),
                  capNode5(5),
                  capNode6(6),
                  capNode7(7),
                  capNode8(8),
                  capNode9(9),
                  capNode10(10),
                  capNode11(11),
                  capNode12(12),
                  capNode13(13),
                  capNode14(14),
                  capNode15(15),
                  capNode16(16),
                  capNode17(17),
                  capNode18(18),
                  capNode19(19),
                  capNode20(20),
                  capNode21(21),
                  capNode22(22),
                  capNode23(23),
                  capNode24(24),
                  capNode25(25),
                  capNode26(26),
                  capNode27(27),
                  capNode28(28),
                  capNode29(29),
                  capNode30(30),
                  capNode31(31),
                  capNode32(32),
                  capNode33(33),
                  capNode34(34),
                  capNode35(35),
                  capNode36(36),
                  capNode37(37),
                  capNode38(38),
                  capNode39(39),
                  capNode40(40),
                  capNode41(41),
                  capNode42(42),
                  capNode43(43),
                  capNode44(44),
                  capNode45(45),
                  capNode46(46),
                  capNode47(47),
                  capNode48(48),
                  capNode49(49),
                  capNode50(50),
                  capNode51(51),
                  capNode52(52),
                  capNode53(53),
                  capNode54(54),
                  capNode55(55),
                  capNode56(56),
                  capNode57(57),
                  capNode58(58),
                  capNode59(59),
                  capNode60(60),
                  capNode61(61),
                  capNode62(62),
                  capNode63(63),
                  capNode64(64),
                  capNode65(65),
                  capNode66(66),
                  capNode67(67),
                  capNode68(68),
                  capNode69(69),
                  capNode70(70),
                  capNode71(71),
                  capNode72(72),
                  capNode73(73),
                  capNode74(74),
                  capNode75(75),
                  capNode76(76),
                  capNode77(77),
                  capNode78(78),
                  capNode79(79),
                  capNode80(80),
                  capNode81(81),
                  capNode82(82),
                  capNode83(83),
                  capNode84(84),
                  capNode85(85),
                  capNode86(86),
                  capNode87(87),
                  capNode88(88),
                  capNode89(89),
                  capNode90(90),
                  capNode91(91),
                  capNode92(92),
                  capNode93(93),
                  capNode94(94),
                  capNode95(95),
                  capNode96(96),
                  capNode97(97),
                  capNode98(98),
                  capNode99(99),
                  capNode100(100),
                  capNode101(101),
                  capNode102(102),
                  capNode103(103),
                  capNode104(104),
                  capNode105(105),
                  capNode106(106),
                  capNode107(107),
                  capNode108(108),
                  capNode109(109),
                  capNode110(110),
                  capNode111(111),
                  capNode112(112),
                  capNode113(113),
                  capNode114(114),
                  capNode115(115),
                  capNode116(116),
                  capNode117(117),
                  capNode118(118)
                }

FspR7PceMode ::= TEXTUAL-CONVENTION
  STATUS        current
  DESCRIPTION
         "Path Computation Policy to be followed when computing paths for a given Tunnel" 
  SYNTAX        INTEGER
                {
                  undefined(0),
                  optimalTe(1),
                  osnrConstr(2),
                  optimalOsnr(3)
                }

FspR7PceModeCaps ::= TEXTUAL-CONVENTION
  STATUS        current
  DESCRIPTION
         "Path Computation Policy to be followed when computing paths for a given Tunnel" 
  SYNTAX        BITS
                {
                  capUndefined(0),
                  capOptimalTe(1),
                  capOsnrConstr(2),
                  capOptimalOsnr(3)
                }

FspR7PlugDataRate ::= TEXTUAL-CONVENTION
  STATUS        current
  DESCRIPTION
         "Rate" 
  SYNTAX        INTEGER
                {
                  undefined(0),
                  rateCouplingLink(1),
                  rateHighSpeed(2),
                  rateGBe(3),
                  rate2G1(4),
                  rate2G5(5),
                  rate4G(6),
                  rate10G(7),
                  any(8),
                  rate11G(9),
                  rateFE(10),
                  rate10G2R(11),
                  rate8G(12),
                  rate103G(13),
                  rate112G(14),
                  rate16G(15),
                  rate3gSdi(16),
                  rate3G(17),
                  rateMadi(18),
                  rate6G(19)
                }

FspR7PlugDataRateCaps ::= TEXTUAL-CONVENTION
  STATUS        current
  DESCRIPTION
         "Rate" 
  SYNTAX        BITS
                {
                  capUndefined(0),
                  capRateCouplingLink(1),
                  capRateHighSpeed(2),
                  capRateGBe(3),
                  capRate2G1(4),
                  capRate2G5(5),
                  capRate4G(6),
                  capRate10G(7),
                  capAny(8),
                  capRate11G(9),
                  capRateFE(10),
                  capRate10G2R(11),
                  capRate8G(12),
                  capRate103G(13),
                  capRate112G(14),
                  capRate16G(15),
                  capRate3gSdi(16),
                  capRate3G(17),
                  capRateMadi(18),
                  capRate6G(19)
                }

FspR7PmSnapshotParameterTypes ::= TEXTUAL-CONVENTION
  STATUS        current
  DESCRIPTION
         "List of PM Snapshot parameters" 
  SYNTAX        INTEGER
                {
                  undefined(0),
                  outputPower(1),
                  inputPower(2),
                  attenuation(3),
                  attenuationOfVoa(4),
                  oscGain(5),
                  backreflectionPowerReceived(6),
                  ramanPumpPower(7),
                  oscPowerReceived(8),
                  variableGain(9),
                  txLineAttenuation(10),
                  rxLineAttenuation(11)
                }

FspR7PmReset ::= TEXTUAL-CONVENTION
  STATUS        current
  DESCRIPTION
         "Reset data-layer Performance registers" 
  SYNTAX        INTEGER
                {
                  undefined(0),
                  none(1),
                  all(2),
                  curr(3)
                }

FspR7PmResetCaps ::= TEXTUAL-CONVENTION
  STATUS        current
  DESCRIPTION
         "Reset data-layer Performance registers" 
  SYNTAX        BITS
                {
                  capUndefined(0),
                  capNone(1),
                  capAll(2),
                  capCurr(3)
                }

FspR7PmSnapshotStatus ::= TEXTUAL-CONVENTION
  STATUS        current
  DESCRIPTION
         "Reference value Status" 
  SYNTAX        INTEGER
                {
                  undefined(0),
                  none(1),
                  inProgress(2),
                  success(3),
                  error(4)
                }

FspR7PortBehaviour ::= TEXTUAL-CONVENTION
  STATUS        current
  DESCRIPTION
         "Behavior or Port usage based on configuration/usage in the system regardless of faceplate designation" 
  SYNTAX        INTEGER
                {
                  undefined(0),
                  client(1),  --Client Interface Side Behavior
                  network(2)  --Network Interface Side Behavior
                }

FspR7PortBehaviourCaps ::= TEXTUAL-CONVENTION
  STATUS        current
  DESCRIPTION
         "Behavior or Port usage based on configuration/usage in the system regardless of faceplate designation" 
  SYNTAX        BITS
                {
                  capUndefined(0),
                  capClient(1),
                  capNetwork(2)
                }

FspR7PortMode ::= TEXTUAL-CONVENTION
  STATUS        current
  DESCRIPTION
         "Port Mode" 
  SYNTAX        INTEGER
                {
                  undefined(0),
                  port(1),
                  cTag(2),
                  sTag(3)
                }

FspR7PortModeCaps ::= TEXTUAL-CONVENTION
  STATUS        current
  DESCRIPTION
         "Port Mode" 
  SYNTAX        BITS
                {
                  capUndefined(0),
                  capPort(1),
                  capCTag(2),
                  capSTag(3)
                }

FspR7PortRole ::= TEXTUAL-CONVENTION
  STATUS        current
  DESCRIPTION
         "ADVA cloud Port Roles" 
  SYNTAX        INTEGER
                {
                  undefined(0),
                  uni(1),  --User Network Interface
                  iNni(2),  --ADVA Interconnect Network Network Interface
                  nni(3)  --Network Network Interface
                }

FspR7PortRoleCaps ::= TEXTUAL-CONVENTION
  STATUS        current
  DESCRIPTION
         "ADVA cloud Port Roles" 
  SYNTAX        BITS
                {
                  capUndefined(0),
                  capUni(1),
                  capINni(2),
                  capNni(3)
                }

FspR7PrbsPmReset ::= TEXTUAL-CONVENTION
  STATUS        current
  DESCRIPTION
         "Reset PRBS PM counters" 
  SYNTAX        INTEGER
                {
                  undefined(0),
                  none(1),  --Not initialize PRBS PM Counters
                  all(2)  --Initialize all PRBS PM Counters
                }

FspR7PrbsPmResetCaps ::= TEXTUAL-CONVENTION
  STATUS        current
  DESCRIPTION
         "Reset PRBS PM counters" 
  SYNTAX        BITS
                {
                  capUndefined(0),
                  capNone(1),
                  capAll(2)
                }

FspR7PreferredFacilityType ::= TEXTUAL-CONVENTION
  STATUS        current
  DESCRIPTION
         ">Default type of facility model to use for automatically created, an entity in the OOS-AU,AINS
         facilities. SDH will cause STM64, STM16, VC4, VC3 type
         state will immediately transition to an in-service state.AINS Default Signal Timer. The length of time in hours and minutes
         facilities to be auto-created. SONET will cause OC192,
         for which an entity must be free of service affecting conditions in
         OC48, STS1 and STS3c type facilities to be auto-created." 
  SYNTAX        INTEGER
                {
                  undefined(0),
                  sdh(1),
                  sonet(2)
                }

FspR7PreferredFacilityTypeCaps ::= TEXTUAL-CONVENTION
  STATUS        current
  DESCRIPTION
         ">Default type of facility model to use for automatically created, an entity in the OOS-AU,AINS
         facilities. SDH will cause STM64, STM16, VC4, VC3 type
         state will immediately transition to an in-service state.AINS Default Signal Timer. The length of time in hours and minutes
         facilities to be auto-created. SONET will cause OC192,
         for which an entity must be free of service affecting conditions in
         OC48, STS1 and STS3c type facilities to be auto-created." 
  SYNTAX        BITS
                {
                  capUndefined(0),
                  capSdh(1),
                  capSonet(2)
                }

FspR7ProfileCmd ::= TEXTUAL-CONVENTION
  STATUS        current
  DESCRIPTION
         "Profile manipulation command." 
  SYNTAX        INTEGER
                {
                  undefined(0),
                  idle(1),
                  copyToRdisk(2),
                  copyToPdisk(3)
                }

FspR7ProfileType ::= TEXTUAL-CONVENTION
  STATUS        current
  DESCRIPTION
         "Type of the profile." 
  SYNTAX        INTEGER
                {
                  undefined(0),
                  ech(1),
                  mod(2)
                }

FspR7ProtectionRole ::= TEXTUAL-CONVENTION
  STATUS        current
  DESCRIPTION
         "Path label Working or Protect" 
  SYNTAX        INTEGER
                {
                  undefined(0),
                  wkg(1),
                  protn(2),
                  na(3)
                }

FspR7ProtectionType ::= TEXTUAL-CONVENTION
  STATUS        current
  DESCRIPTION
         "" 
  SYNTAX        INTEGER
                {
                  undefined(0),
                  dpring(1),
                  line(2)
                }

FspR7ProtectionTypeCaps ::= TEXTUAL-CONVENTION
  STATUS        current
  DESCRIPTION
         "" 
  SYNTAX        BITS
                {
                  capUndefined(0),
                  capDpring(1),
                  capLine(2)
                }

FspR7Protocol ::= TEXTUAL-CONVENTION
  STATUS        current
  DESCRIPTION
         "The Type of the IP Route." 
  SYNTAX        INTEGER
                {
                  undefined(0),
                  local(1),  --OS controlled Route
                  static(2),  --Static Route, Part of database.
                  ospf(3)  --OSFP controlled Route
                }

FspR7PsuOutputPower ::= TEXTUAL-CONVENTION
  STATUS        current
  DESCRIPTION
         "Maximum PSU Output Power" 
  SYNTAX        INTEGER
                {
                  undefined(0),
                  pwrOut120w(1),
                  pwrOut130w(2),
                  pwrOut400w(3),
                  pwrOut600w(4),
                  pwrOut170w(5),
                  pwrOut200w(6),
                  pwrOut1000w(7),
                  pwrOut0w(8),
                  pwrOut800w(9),
                  pwrOut150w(10),
                  pwrOut1200w(11),
                  pwrOut1450w(13)
                }

FspR7PsuOutputPowerCaps ::= TEXTUAL-CONVENTION
  STATUS        current
  DESCRIPTION
         "Maximum PSU Output Power" 
  SYNTAX        BITS
                {
                  capUndefined(0),
                  capPwrOut120w(1),
                  capPwrOut130w(2),
                  capPwrOut400w(3),
                  capPwrOut600w(4),
                  capPwrOut170w(5),
                  capPwrOut200w(6),
                  capPwrOut1000w(7),
                  capPwrOut0w(8),
                  capPwrOut800w(9),
                  capPwrOut150w(10),
                  capPwrOut1200w(11),
                  capPwrOut1450w(13)
                }

FspR7RedLinedState ::= TEXTUAL-CONVENTION
  STATUS        current
  DESCRIPTION
         "will be set by higher level software to act as a barrier to deletion" 
  SYNTAX        INTEGER
                {
                  undefined(0),
                  yes(1),
                  no(2)
                }

FspR7RedLinedStateCaps ::= TEXTUAL-CONVENTION
  STATUS        current
  DESCRIPTION
         "will be set by higher level software to act as a barrier to deletion" 
  SYNTAX        BITS
                {
                  capUndefined(0),
                  capYes(1),
                  capNo(2)
                }

FspR7RemoteAlarmPath ::= TEXTUAL-CONVENTION
  STATUS        current
  DESCRIPTION
         "Remote Alarm Path Type (current or non-current)" 
  SYNTAX        INTEGER
                {
                  undefined(0),
                  curr(1),
                  nonCurr(2)
                }

FspR7RemoteAlarmType ::= TEXTUAL-CONVENTION
  STATUS        current
  DESCRIPTION
         "Remote Alarm Type" 
  SYNTAX        INTEGER
                {
                  undefined(0),
                  out(1),
                  outAndOscDown(2)
                }

FspR7RemoteAuth ::= TEXTUAL-CONVENTION
  STATUS        current
  DESCRIPTION
         "Type of Remote authentication" 
  SYNTAX        INTEGER
                {
                  undefined(0),
                  none(1),
                  radius(2),
                  tacacs(3)
                }

FspR7RemoteAuthCaps ::= TEXTUAL-CONVENTION
  STATUS        current
  DESCRIPTION
         "Type of Remote authentication" 
  SYNTAX        BITS
                {
                  capUndefined(0),
                  capNone(1),
                  capRadius(2),
                  capTacacs(3)
                }

FspR7ResetRfi ::= TEXTUAL-CONVENTION
  STATUS        current
  DESCRIPTION
         "Resets Retained Failure Indications for restored Tunnels" 
  SYNTAX        INTEGER
                {
                  undefined(0),
                  rls(1),
                  resetRfi(2)
                }

FspR7ResetRfiCaps ::= TEXTUAL-CONVENTION
  STATUS        current
  DESCRIPTION
         "Resets Retained Failure Indications for restored Tunnels" 
  SYNTAX        BITS
                {
                  capUndefined(0),
                  capRls(1),
                  capResetRfi(2)
                }

FspR7RoadmNumber ::= TEXTUAL-CONVENTION
  STATUS        current
  DESCRIPTION
         "Number for ROADM module typically associated with a Network Fiber or Degree" 
  SYNTAX        INTEGER
                {
                  undefined(0),
                  rNo1(1),
                  rNo2(2),
                  rNo3(3),
                  rNo4(4),
                  rNo5(5),
                  rNo6(6),
                  rNo7(7),
                  rNo8(8),
                  rNo9(9),
                  rNo10(10),
                  rNoNone(11),
                  rNo1AND2(12)
                }

FspR7RoadmNumberCaps ::= TEXTUAL-CONVENTION
  STATUS        current
  DESCRIPTION
         "Number for ROADM module typically associated with a Network Fiber or Degree" 
  SYNTAX        BITS
                {
                  capUndefined(0),
                  capRNo1(1),
                  capRNo2(2),
                  capRNo3(3),
                  capRNo4(4),
                  capRNo5(5),
                  capRNo6(6),
                  capRNo7(7),
                  capRNo8(8),
                  capRNo9(9),
                  capRNo10(10),
                  capRNoNone(11),
                  capRNo1AND2(12)
                }

FspR7RouteRedist ::= TEXTUAL-CONVENTION
  STATUS        current
  DESCRIPTION
         "Redistribution of routes in OSPF" 
  SYNTAX        INTEGER
                {
                  undefined(0),
                  none(1),  --No routes will be redistributed
                  static(2)  --Static routes will be redistirbuted
                }

FspR7RowStatusCaps ::= TEXTUAL-CONVENTION
  STATUS        current
  DESCRIPTION
         "RowStatus" 
  SYNTAX        BITS
                {
                  capUndefined(0),
                  capActive(1),
                  capNotInService(2),
                  capNotReady(3),
                  capCreateAndGo(4),
                  capCreateAndWait(5),
                  capDestroy(6)
                }

FspR7Scrambling ::= TEXTUAL-CONVENTION
  STATUS        current
  DESCRIPTION
         "Configuration of scrambling functionality for Virtual Facilities" 
  SYNTAX        INTEGER
                {
                  undefined(0),
                  enable(1),
                  disable(2)
                }

FspR7ScramblingCaps ::= TEXTUAL-CONVENTION
  STATUS        current
  DESCRIPTION
         "Configuration of scrambling functionality for Virtual Facilities" 
  SYNTAX        BITS
                {
                  capUndefined(0),
                  capEnable(1),
                  capDisable(2)
                }

FspR7ScuDbBackup ::= TEXTUAL-CONVENTION
  STATUS        current
  DESCRIPTION
         "DB Backup on SCU available" 
  SYNTAX        INTEGER
                {
                  undefined(0),
                  yes(1),
                  no(2)
                }

FspR7ScuRing ::= TEXTUAL-CONVENTION
  STATUS        current
  DESCRIPTION
         "SCU Interconnection" 
  SYNTAX        INTEGER
                {
                  undefined(0),
                  enable(1),  --Enables SCU ringinterconnect
                  disable(2)  --Disables SCU ring interconnect
                }

FspR7ScuRingCaps ::= TEXTUAL-CONVENTION
  STATUS        current
  DESCRIPTION
         "SCU Interconnection" 
  SYNTAX        BITS
                {
                  capUndefined(0),
                  capEnable(1),
                  capDisable(2)
                }

FspR7SecurityMode ::= TEXTUAL-CONVENTION
  STATUS        current
  DESCRIPTION
         "Security Mode" 
  SYNTAX        INTEGER
                {
                  undefined(0),
                  basic(1),
                  enhanced(2)
                }

FspR7SecurityModeCaps ::= TEXTUAL-CONVENTION
  STATUS        current
  DESCRIPTION
         "Security Mode" 
  SYNTAX        BITS
                {
                  capUndefined(0),
                  capBasic(1),
                  capEnhanced(2)
                }

FspR7SecurityName ::= TEXTUAL-CONVENTION
  STATUS        current
  DESCRIPTION
         "SNMP V1 Security Name" 
  SYNTAX        INTEGER
                {
                  undefined(0),
                  readOnly(1),
                  readWrite(2)
                }

FspR7SessionStatus ::= TEXTUAL-CONVENTION
  STATUS        current
  DESCRIPTION
         "Disable/Enable variable." 
  SYNTAX        INTEGER

                {
                  undefined(0),
                  active(1),
                  inactive(2)
                }

FspR7SessionStatusCaps ::= TEXTUAL-CONVENTION
  STATUS        current
  DESCRIPTION
         "Disable/Enable variable." 
  SYNTAX        BITS
                {
                  capUndefined(0),
                  capActive(1),
                  capInactive(2)
                }

FspR7SignalDirection ::= TEXTUAL-CONVENTION
  STATUS        current
  DESCRIPTION
         "Signal Direction" 
  SYNTAX        INTEGER
                {
                  undefined(0),
                  networkToClient(1),
                  cientToNetwork(2),
                  upgradeToNetwork(3),
                  networkToUpgrade(4)
                }

FspR7SignalMapping ::= TEXTUAL-CONVENTION
  STATUS        current
  DESCRIPTION
         "Mapping of Client Signal into some other format" 
  SYNTAX        INTEGER
                {
                  undefined(0),
                  gfp(1), --Standard GFP mapping of 10GBE into OTU2 without flow control and to standard OTU2 bitrate
                  proprietary(2) --AMFCC's proprietary mapping of 10GBE into OTU2 without flow control and to standard OTU2 bitrate
                }

FspR7SignalMappingCaps ::= TEXTUAL-CONVENTION
  STATUS        current
  DESCRIPTION
         "Mapping of Client Signal into some other format" 
  SYNTAX        BITS
                {
                  capUndefined(0),
                  capGfp(1),
                  capProprietary(2)
                }

FspR7SingleFiberLocation ::= TEXTUAL-CONVENTION
  STATUS        current
  DESCRIPTION
         "determines the location (A or B) for Single Fiber applications" 
  SYNTAX        INTEGER
                {
                  undefined(0),
                  locationA(1),  --location A for SF applications
                  locationB(2)  --location B for SF applications
                }

FspR7SingleFiberLocationCaps ::= TEXTUAL-CONVENTION
  STATUS        current
  DESCRIPTION
         "determines the location (A or B) for Single Fiber applications" 
  SYNTAX        BITS
                {
                  capUndefined(0),
                  capLocationA(1),
                  capLocationB(2)
                }

FspR7SnmpHexString ::= TEXTUAL-CONVENTION
  STATUS        current
  DESCRIPTION
         "An octet string containing Hex values and presenting them in Hex format.
         This textual convention should be used when SnmpAdminString or DisplayString cannot be used,
         because of DISPLAY-HINT limitations." 
  SYNTAX        OCTET STRING (SIZE(0..255))

FspR7SnmpLongString ::= TEXTUAL-CONVENTION
  STATUS        current
  DESCRIPTION
         "This textual convention should be used when SnmpAdminString or DisplayString
         cannot be used because of the length limitations." 
  SYNTAX        OCTET STRING (SIZE(0..65535))

FspR7SnmpPrivLevel ::= TEXTUAL-CONVENTION
  STATUS        current
  DESCRIPTION
         "" 
  SYNTAX        INTEGER
                {
                  undefined(0),
                  admin(1),
                  provision(2),
                  operator(3),
                  monitor(4),
                  crypto(5),
                  snmponly(6)
                }

FspR7SnmpPrivLevelCaps ::= TEXTUAL-CONVENTION
  STATUS        current
  DESCRIPTION
         "" 
  SYNTAX        BITS
                {
                  capUndefined(0),
                  capAdmin(1),
                  capProvision(2),
                  capOperator(3),
                  capMonitor(4),
                  capCrypto(5),
                  capSnmponly(6)
                }

FspR7SnmpSecuLevel ::= TEXTUAL-CONVENTION
  STATUS        current
  DESCRIPTION
         "" 
  SYNTAX        INTEGER
                {
                  undefined(0),
                  noAuthNoPriv(1),
                  authNoPriv(2),
                  authPriv(3)
                }

FspR7SnmpSecuLevelCaps ::= TEXTUAL-CONVENTION
  STATUS        current
  DESCRIPTION
         "" 
  SYNTAX        BITS
                {
                  capUndefined(0),
                  capNoAuthNoPriv(1),
                  capAuthNoPriv(2),
                  capAuthPriv(3)
                }

FspR7SshDeamon ::= TEXTUAL-CONVENTION
  STATUS        current
  DESCRIPTION
         "Secure Shell Interface Control" 
  SYNTAX        INTEGER
                {
                  undefined(0),
                  enable(1),
                  disable(2)
                }

FspR7SshHostKeyEncryptAlgorithm ::= TEXTUAL-CONVENTION
  STATUS        current
  DESCRIPTION
         "ssh host key encryption alogrithm" 
  SYNTAX        INTEGER
                {
                  undefined(0),
                  rsa(1),
                  dsa(2),
                  rsa1(3)
                }

FspR7SshHostKeyEncryptAlgorithmCaps ::= TEXTUAL-CONVENTION
  STATUS        current
  DESCRIPTION
         "ssh host key encryption alogrithm" 
  SYNTAX        BITS
                {
                  capUndefined(0),
                  capRsa(1),
                  capDsa(2),
                  capRsa1(3)
                }

FspR7Stages ::= TEXTUAL-CONVENTION
  STATUS        current
  DESCRIPTION
         "Number of Stages" 
  SYNTAX        INTEGER
                {
                  undefined(0),
                  st1(1),
                  st2(2)
                }

FspR7StandingConditionTypes ::= TEXTUAL-CONVENTION
  STATUS        current
  DESCRIPTION
         "List of all alarms" 
  SYNTAX        INTEGER
                {
                  undefined(0),
                  thirdPartyPlug(1001),
                  facilityLoopback(1002),
                  terminalLoopback(1003),
                  facilityForcedOn(1004),
                  oosDisabled(1005),
                  receiverDisabled(1006),
                  transmitterDisabledOff(1007),
                  transmittedDisabledIdle(1008),
                  transmitterDisabledAis(1009),
                  transmitterDisabledEpc(1010),
                  oosManagement(1011),
                  oosMaintenance(1012),
                  oosAins(1013),
                  dcnCommunicationFail(1014),
                  removed(1015),
                  mismatch(1016),
                  equipmentNotAccepted(1017),
                  facilityDataRateNotSupported(1018),
                  equipmentNotSupportedByPhysicalLayer(1019),
                  equipmentNotApproved(1020),
                  equipmentMismatch(1021),
                  -- fuseAlarm1(1022),
                  -- fuseAlarm2(1023),
                  -- fanAlarm(1024),
                  -- fanUnitAlarm(1025),
                  powerMissing(1026),
                  -- powerFailure(1027),
                  -- voltageTooLow(1028),
                  -- voltageTooHigh(1029),
                  temperatureTooLow(1030),
                  temperatureTooHigh(1031),
                  -- receiverFailure(1032),
                  -- opticalInputPowerReceiverFailure(1033),
                  lossOfSignal(1034),
                  -- idleSignalReceived(1035),
                  -- lossOfLinkPulse(1036),
                  lossOfReceiverClockRecovery(1037),
                  -- elasticStoreOverflowReceiver(1038),
                  -- lossOfTransmitterClockRecovery(1039),
                  laserFailure(1040),
                  switchFailed(1041),
                  -- elasticStoreOverflowTransmitter(1042),
                  autoShutdownLaserOffDueToErrFwd(1043),
                  -- autoShutdown(1044),
                  autoShutdownAls(1045),
                  -- autoShutdownSendingIdle(1046),
                  thermoElectricCoolerEndOfLife(1047),
                  opticalInputPwrReceivedTooLow(1048),
                  opticalInputPwrReceivedTooHigh(1049),
                  laserTemperatureTooHigh(1050),
                  laserTemperatureTooLow(1051),
                  opticalOutputPowerTransmittedTooLow(1052),
                  opticalOutputPowerTransmittedTooHigh(1053),
                  laserBiasCurrentNormalizedtooHigh(1054),
                  lossOfSignalTransmitter(1055),
                  attOnReceiverFiberLowerThanMonitor(1056),
                  attOnReceiverFiberHigherThanMonitor(1057),
                  attOnTransmitterFiberLowerThanMonitor(1058),
                  attOnTransmitterFiberHigherThanMonitor(1059),
                  autoShutdownSendingAisOtu(1060),
                  lossOfFrameOtu(1061),
                  lossOfMultiFrameOtu(1062),
                  alarmIndicationSignalOtu(1063),
                  signalDegradeOtu(1064),
                  backwardDefectIndicationOtu(1065),
                  autoShutdownSendingAisOdu(1066),
                  lossOfFrameLossOfMultiFrameOdu(1067),
                  alarmIndicationSignalOdu(1068),
                  openConnectionIndicationOdu(1069),
                  lockedDefectOdu(1070),
                  signalDegradeOdu(1071),
                  backwardDefectIndicationOdu(1072),
                  alarmIndicationSignalOduTcmA(1073),
                  openConnectionIndicationOduTcmA(1074),
                  lockedDefectOduTcmA(1075),
                  lossofTandemConnectionOduTcmA(1076),
                  signalDegradeOduTcmA(1077),
                  backwardDefectIndicationOduTcmA(1078),
                  payloadMismatchOPU(1079),
                  multiplexStructureIdentifierMismatchOPU(1080),
                  lossOfFrame(1081),
                  -- sectionSignalFailure(1082),
                  autoShutdownSendingAisLine(1083),
                  alarmIndicationSignalLine(1084),
                  remoteDefectIndicationLine(1085),
                  signalDegradeLine(1086),
                  alarmIndicationSignalHigherOrderPath(1087),
                  lossOfPointerHigherOrderPath(1088),
                  lossofMultiframeHigherOrderPath(1089),
                  lossofSequenceHigherOrderPath(1090),
                  unequippedHigherOrderPath(1091),
                  payloadMismatchHigherOrderPath(1092),
                  remoteDefectIndicationHigherOrderPath(1093),
                  -- signalDegradeHigherOrderPath(1094),
                  alarmIndicationSignalLowerOrderPath(1095),
                  lossOfPointerLowerOrderPath(1096),
                  lossofMultiframeLowerOrderPath(1097),
                  lossofSequenceLowerOrderPath(1098),
                  unequippedLowerOrderPath(1099),
                  payloadMismatchLowerOrderPath(1100),
                  remoteDefectIndicationLowerOrderPath(1101),
                  -- lossOfMultiframeVCG(1102),
                  -- lossOfSequenceVCG(1103),
                  -- lossofAlignmentVCG(1104),
                  autoShutdownSendingEPC(1105),
                  thres15MinExceededPhysConvES(1106),
                  thres15MinExceededPhysConvCV(1107),
                  thres15MinExceededPhysConvDE(1108),
                  thres15MinExceededPhysConvCVDE(1109),
                  lossOfGfpFrame(1110),
                  payloadMismatchGfp(1111),
                  gfpLossOfClientSig(1112),
                  lossOfCharSyncFromFarEnd(1113),
                  switchtoProtectionInhibited(1114),
                  switchtoWorkingInhibited(1115),
                  oTDRMeasuringinProgress(1116),
                  protectionNotAvailable(1117),
                  apsConfigMismatch(1118),
                  embeddedOperationsChannelFailure(1119),
                  -- signalDegradeSection(1120),
                  signalDegradationonLinkVector(1121),
                  signalFailureonLinkVector(1122),
                  inputVoltageFailure(1123),
                  powerSupplyUnitFailure(1124),
                  currentTooLow(1125),
                  currentTooHigh(1126),
                  multipleFanFailure(1127),
                  singleFanFailure(1128),
                  linkDown(1129),
                  voltageOutOfRange(1130),
                  peerLink(1131),
                  hwFailure(1132),
                  alarmIndicationSignalOduTcmB(1133),
                  openConnectionIndicationOduTcmB(1134),
                  lockedDefectOduTcmB(1135),
                  lossofTandemConnectionOduTcmB(1136),
                  signalDegradeOduTcmB(1137),
                  backwardDefectIndicationOduTcmB(1138),
                  apsProtocolFailure(1139),
                  -- apdLowVoltage(1140),
                  -- apdHighVoltage(1141),
                  linkControlProtocolFailure(1142),
                  -- receiverLowTemp(1143),
                  -- receiverHighTemp(1144),
                  -- thermoElectricCoolerCurrentTooLow(1145),
                  -- thermoElectricCoolerCurrentTooHigh(1146),
                  subModuleTempTooHigh(1147),
                  signalDegradeOlm(1148),
                  receiverOverloadProtection(1149),
                  lossOfFrameMux(1150),
                  lossOfFrameMuxFarEnd(1151),
                  lossOfCharSync(1152),
                  thres15MinExceededFecCE(1153),
                  thres15MinExceededFecUBE(1154),
                  thres15MinExceededFecES(1155),
                  thres15MinExceededFecSES(1156),
                  thres15MinExceededMuxES(1157),
                  thres15MinExceededMuxSES(1158),
                  thres15MinExceededGfpCHEC(1159),
                  thres15MinExceededGfpTHEC(1160),
                  thres15MinExceededGfpTHecDisc(1161),
                  thres15MinExceededGfpTsuperblockDisc(1162),
                  -- intrusionRx(1163),
                  -- intrusionTx(1164),
                  autoShutdownLaserOffDueToHighTemp(1165),
                  autoShutdownLaserOffDueToHighTxPwr(1166),
                  laserEndOfLife(1167),
                  laserBiasCurrAbnormal(1168),
                  opticalPowerTxLOS(1169),
                  midstageFault(1170),
                  farEndIpAddressUnknown(1171),
                  topologyDataCalculationInProgress(1172),
                  ntpServer1Unreachable(1173),
                  ntpServer2Unreachable(1174),
                  ntpServer3Unreachable(1175),
                  autoShutdownSendingAisOpu(1176),
                  alarmIndicationSignalOpu(1177),
                  alarmIndicationSignalOduTcmC(1178),
                  backwardDefectIndicationOduTcmC(1179),
                  lockedDefectOduTcmC(1180),
                  lossofTandemConnectionOduTcmC(1181),
                  openConnectionIndicationOduTcmC(1182),
                  signalDegradeOduTcmC(1183),
                  loopbackError(1184),
                  sectionTraceMismatch(1185),
                  traceIdentifierMismatchOtu(1186),
                  traceIdentifierMismatchOdu(1187),
                  traceIdentifierMismatchOduTcmA(1188),
                  traceIdentifierMismatchOduTcmC(1189),
                  traceIdentifierMismatchOduTcmB(1190),
                  databaseMismatch(1191),
                  databaseNcuMismatch(1192),
                  serverSignalFailureSectionRS(1193),
                  fwpMismatchDownloadServiceAffecting(1194),
                  fwpMismatchDownloadNotServiceAffecting(1195),
                  databaseVersionMismatch(1196),
                  clientFailForwarding(1197),
                  virtualChannelAis(1198),
                  serverSignalFailureVf(1199),
                  signalFailureOnLink(1200),
                  serverSignalFailureGfp(1201),
                  serverSignalFailurePath(1202),
                  gainTiltNotSettable(1203),
                  txPowerLimited(1204),
                  equalizationProgress(1205),
                  uPortFailure(1206),
                  autoShutdownBlock(1207),
                  serverSignalFailTx(1208),
                  payloadMismatch(1209),
                  voaControlFail(1210),
                  provisioningLocked(1211),
                  mansw(1212),
                  wtrTimerRunning(1213),
                  pcsSignalDegrade(1214),
                  alarmInputTIF(1215),
                  thres15MinExceededSonetSectES(1216),
                  thres15MinExceededSonetSectSES(1217),
                  thres15MinExceededSonetSectSEFS(1218),
                  thres15MinExceededSonetSectCV(1219),
                  thres15MinExceededSonetLineES(1220),
                  thres15MinExceededSonetLineSES(1221),
                  thres15MinExceededSonetLineCV(1222),
                  thres15MinExceededSonetLineUAS(1223),
                  thres15MinExceededOduTcmAES(1224),
                  thres15MinExceededOduTcmASES(1225),
                  thres15MinExceededOduTcmAUAS(1226),
                  thres15MinExceededOduTcmABbe(1227),
                  thres15MinExceededOduTcmBES(1228),
                  thres15MinExceededOduTcmBSES(1229),
                  thres15MinExceededOduTcmBUAS(1230),
                  thres15MinExceededOduTcmBBbe(1231),
                  thres15MinExceededOduTcmCES(1232),
                  thres15MinExceededOduTcmCSES(1233),
                  thres15MinExceededOduTcmCUAS(1234),
                  thres15MinExceededOduTcmCBbe(1235),
                  thres15MinExceededOtuES(1236),
                  thres15MinExceededOtuSES(1237),
                  thres15MinExceededOtuUAS(1238),
                  thres15MinExceededOtuBbe(1239),
                  thres15MinExceededOduES(1240),
                  thres15MinExceededOduSES(1241),
                  thres15MinExceededOduUAS(1242),
                  thres15MinExceededOduBbe(1243),
                  thresOptPowerCtrlFailureLow(1244),
                  thresOptPowerCtrlFailureHigh(1245),
                  dcnServerSignalFailure(1246),
                  maxPowerConsEquipModulesToHigh(1247),
                  maxPowerConsProvModulesToHigh(1248),
                  equipmentMismatchAllow(1249),
                  oosPrePostSig(1250),
                  oosPrePostSigInSetUpProcess(1251),
                  oosPrePostSigInTearDownProcess(1252),
                  cpTunnelModificationInProgess(1253),
                  capabilityLevelMismatch(1254),
                  oosPrePostSigEstablishFailed(1255),
                  oosPrePostSigAfterPrecompFailed(1256),
                  cpTunnelEstablishFailed(1257),
                  cpTunnelPrecompFailed(1258),
                  localFault(1259),
                  oscPwrTooHigh(1260),
                  oscPwrTooLow(1261),
                  aseTableBuild(1262),
                  aseTableNotAvailable(1263),
                  automaticPowerReduction(1264),
                  highBer(1266),
                  pumpLaser1TempTooHigh(1267),
                  pumpLaser1TempTooLow(1268),
                  pumpLaser2TempTooHigh(1269),
                  pumpLaser2TempTooLow(1270),
                  ospfIpServerNotAvailable(1271),
                  lossOsc(1272),
                  brPwrRxTooHigh(1273),
                  aseTableGenFailSignalinput(1274),
                  aseTableGenFailOscMissing(1275),
                  aseTableGenFailHighBackreflection(1276),
                  ramanPumpPwrTooHigh(1277),
                  ramanPumpPwrTooLow(1278),
                  autoPowerShutdown(1279),
                  aseTableGenFailLow(1280),
                  aseLow(1281),
                  configurableOpticalOutputPowerTransmittedTooHigh(1282),
                  configurableOpticalOutputPowerTransmittedTooLow(1283),
                  losAttProgress(1284),
                  aseTableGenProgress(1285),
                  signalDegradeScn(1286),
                  dispertionTunningCondition(1287),
                  turnupCondition(1288),
                  turnupFailed(1289),
                  faultOnOpm(1301),
                  optSignalFailure(1302),
                  opmAbnormalCondition(1303),
                  hwOprReachedHT(1304),
                  disabledChannelPowerTooHigh(1305),
                  lossOfSignalCPort(1306),
                  lossOfSignalNPort(1307),
                  serverSignalFailureODU(1308),
                  signalFailureOPU(1309),
                  serverSignalFail(1310),
                  serverSignalReduced(1311),
                  dispersionCompensationTooLow(1312),
                  dispersionCompensationTooHigh(1313),
                  farEndCommFailure(1315),
                  linkAttenuationTooLow(1316),
                  linkAttenuationTooHigh(1317),
                  entityOutageIndication(1320),
                  fiberConnectionMissing(1321),
                  farEndInformationMismatch(1322),
                  automaticPowerReductionForEyeSafety(1325),
                  lossOfPilotSignal(1326),
                  pumpLaser3TempTooHigh(1327),
                  pumpLaser3TempTooLow(1328),
                  pilotReceiveLevelHigh(1329),
                  autoShutdownStbyProtection(1330),
                  databaseFailure(1331),
                  latencyTooHigh(1335),
                  latencyTooLow(1336),
                  thres15MinExceededFecBERCE(1337),
                  autoShutdownSendingLckOdu(1338),
                  ntpNotInSync(1339),
                  encryptionModuleTamperDetected(1340),
                  encryptionModuleCryPasswdMissing(1341),
                  encryptionModuleCryPasswdError(1342),
                  encryptionModuleFwpUpdateEnabled(1343),
                  encryptionModuleSelfTestStarted(1344),
                  encryptionModuleSelfTestFail(1345),
                  encryptionModuleSelfTestFailCritical(1346),
                  encryptionPortAuthPasswdMissing(1350),
                  encryptionPortMaxKeyExchgFailuresReachedIs(1351),
                  encryptionPortMaxKeyExchgFailuresReachedOos(1352),
                  encryptionPortEncryptionSwitchedOff(1353),
                  encryptionPortKeyExchangedForced(1354),
                  encryptionPortEncryptionSwitchOffEnabled(1355),
                  encryptionPortKeyInitExchgMissed(1356),
                  roundTripDelayTooHigh(1380),
                  roundTripDelayTooLow(1381),
                  ntpForSchedEqlzRequired(1386),
                  airDustFilterClogged(1385),
                  oscOpticalPowerControlFailHigh(1387),
                  oscOpticalPowerControlFailLow(1388),
                  amplifierAbnormal(1389),
                  aseTableGenFailPilot(1390),
                  pumpLaser4TempTooHigh(1391),
                  pumpLaser4TempTooLow(1392),
                  fwdAseTableFailPilot(1393),
                  fwdAseTableOnPilot(1394),
                  inputVoltageFailurePort1(1395),
                  inputVoltageFailurePort2(1396),
                  xfpDecisionThresSetFailed(1397),
                  ntpSrvOosDsbld(1398),
                  thres15MinExceededPhysConvSE(1399),
                  thres15MinExceededPhysConvESTX(1400),
                  thres15MinExceededPhysConvCVTX(1401),
                  thres15MinExceededPhysConvSETX(1402),
                  prbsRcvActivated(1403),
                  prbsTrmtActivated(1404),
                  prbsLossOfSeqSynch(1405),
                  opuClientSignalFail(1406),
                  lossOfTestSeqSynchOpu(1407),
                  autoShutdownOpuClientSignalFail(1408),
                  localOscTemperatureTooLow(1409),
                  localOscTemperatureTooHigh(1410),
                  differentialGroupDelayTooHigh(1412),
                  chromaticDispersionTooLow(1413),
                  chromaticDispersionTooHigh(1414),
                  signalToNoiseRatioTooLow(1415),
                  localOscLevelAbnormal(1416),
                  carrierFreqOffsetTooLow(1417),
                  carrierFreqOffsetTooHigh(1418),
                  lossOfLane(1419),
                  serverSignalFailureODUcrs(1420),
                  autoShutdownSendingOciOdu(1421),
                  oduTribMsiMismatch(1422),
                  channelMismatch(1423),
                  eqlzAdjust(1424),
                  hwDegrade(1425),
                  hwInitializing(1426),
                  ampFailure(1427),
                  autoAmpShutdown(1428),
                  fiberConnLos(1429),
                  fiberConnOptFault(1430),
                  fiberConnInvalid(1431),
                  fiberConnMismatch(1432),
                  fiberConnCommError(1433),
                  fiberConnProtocolFailure(1434),
                  fiberConnDataFailure(1435),
                  fiberAttenuationHigh(1436),
                  fiberConnInvalidTx(1437),
                  fiberConnMismatchTx(1438),
                  fiberAttenuationHighTx(1439),
                  switchToDuplexInhibited(1440),
                  meaSwRevision(1441),
                  dbReplicationIncompleted(1442),
                  backupNotResponding(1443),
                  backupForcedToHalt(1444),
                  duplexLinkFailure(1445),
                  provPayloadMismatch(1446),
                  autoShutdownOpuFlxCSF(1447),
                  logicalLanesSkewTooHigh(1448),
                  fiberAttenuationCond(1449),
                  laserOnDelay(1450),
                  autoShutdownTxRxLasersDueToHighTemp(1451),
                  autoShutdownAmpAps(1459),
                  tunnelAbnormal(1460)
                }

FspR7StartPmSnapshot ::= TEXTUAL-CONVENTION
  STATUS        current
  DESCRIPTION
         "Apply reference values" 
  SYNTAX        INTEGER
                {
                  undefined(0),
                  none(1),
                  apply(2)
                }

FspR7StartOpticalPmSnapshotExport ::= TEXTUAL-CONVENTION
  STATUS        current
  DESCRIPTION
         "Export Reference Levels." 
  SYNTAX        INTEGER

                {
                  undefined(0),
                  none(1),
                  apply(19)   --Export Reference Levels to csv file
                }

FspR7StateConnection ::= TEXTUAL-CONVENTION
  STATUS        current
  DESCRIPTION
         "State of the Physical Connection" 
  SYNTAX        INTEGER
                {
                  undefined(0),
                  standard(1),
                  mismatchEquipment(2),
                  mismatchConnection(3),
                  mismatchChannel(4),
                  mismatchPhysical(5),
                  invalidConfig(6),
                  nonStandard(7),
                  standardSpeq(8)
                }

FspR7Stuff ::= TEXTUAL-CONVENTION
  STATUS        current
  DESCRIPTION
         "Indicates if bit/byte stuffing is used in the transport signal." 
  SYNTAX        INTEGER
                {
                  undefined(0),
                  yes(1),
                  no(2)
                }

FspR7StuffCaps ::= TEXTUAL-CONVENTION
  STATUS        current
  DESCRIPTION
         "Indicates if bit/byte stuffing is used in the transport signal." 
  SYNTAX        BITS
                {
                  capUndefined(0),
                  capYes(1),
                  capNo(2)
                }

FspR7SubLayer ::= TEXTUAL-CONVENTION
  STATUS        current
  DESCRIPTION
         "Layer of Traffic Engineering Links attached to the tunnel created in the supporting layer" 
  SYNTAX        INTEGER
                {
                  undefined(0),
                  lambda(1),  --Lambda Switching Capable
                  fiber(2),  --Fiber Switching Capable
                  tdm(3),  --TDM Switching Capable
                  psc1(4),  --Packet Switching Capable 1
                  psc2(5),  --Packet Switching Capable 2
                  psc3(6),  --Packet Switching Capable 3
                  psc4(7),  --Packet Switching Capable 4
                  l2sc(8),  --Layer-2 Switching Capable
                  ethSvlan(9),  --ETH S-tagged VLAN Switching Capable
                  none(10),  --No Sub-Layer attached to this Tunnel
                  subLsc(11),  --Sub-Lambda Switching Capable
                  dcsc(12),  --Data Channel Switching Capable
                  otn(13)  --OTNl Switching Capable
                }

FspR7SubLayerCaps ::= TEXTUAL-CONVENTION
  STATUS        current
  DESCRIPTION
         "Layer of Traffic Engineering Links attached to the tunnel created in the supporting layer" 
  SYNTAX        BITS
                {
                  capUndefined(0),
                  capLambda(1),
                  capFiber(2),
                  capTdm(3),
                  capPsc1(4),
                  capPsc2(5),
                  capPsc3(6),
                  capPsc4(7),
                  capL2sc(8),
                  capEthSvlan(9),
                  capNone(10),
                  capSubLsc(11),
                  capDcsc(12),
                  capOtn(13)
                }

FspR7SubLayerEncoding ::= TEXTUAL-CONVENTION
  STATUS        current
  DESCRIPTION
         "Sub-Layer Encoding" 
  SYNTAX        INTEGER
                {
                  undefined(0),
                  otn(1),
                  sonet(2),
                  sdh(3),
                  eth(4),
                  fc(5),
                  trans(6),
                  cl(7),
                  ib(8),
                  otnp(9),
                  unspecified(10)
                }

FspR7SubLayerEncodingCaps ::= TEXTUAL-CONVENTION
  STATUS        current
  DESCRIPTION
         "Sub-Layer Encoding" 
  SYNTAX        BITS
                {
                  capUndefined(0),
                  capOtn(1),
                  capSonet(2),
                  capSdh(3),
                  capEth(4),
                  capFc(5),
                  capTrans(6),
                  capCl(7),
                  capIb(8),
                  capOtnp(9),
                  capUnspecified(10)
                }

FspR7SupplyType ::= TEXTUAL-CONVENTION
  STATUS        current
  DESCRIPTION
         "The kind of power supply - provisioned value" 
  SYNTAX        INTEGER
                {
                  undefined(0),
                  front(1),
                  rear(2)
                }

FspR7SupplyTypeCaps ::= TEXTUAL-CONVENTION
  STATUS        current
  DESCRIPTION
         "The kind of power supply - provisioned value" 
  SYNTAX        BITS
                {
                  capUndefined(0),
                  capFront(1),
                  capRear(2)
                }

FspR7SwitchOverCause ::= TEXTUAL-CONVENTION
  STATUS        current
  DESCRIPTION
         "Cause of Fail-Over or Switch-Over to Partner Controller" 
  SYNTAX        INTEGER
                {
                  undefined(0),
                  notApplicable(1),
                  removed(2),
                  softwareException(3),
                  noResponse(4),
                  gracefulShutdown(9),
                  switchToDuplex(10),
                  buttonPushed(11)
                }

FspR7SystemBusy ::= TEXTUAL-CONVENTION
  STATUS        current
  DESCRIPTION
         "System Busy state." 
  SYNTAX        INTEGER
                {
                  undefined(0),
                  idle(1),
                  busyFileTransfer(2),
                  busySystemUpdate(3),
                  busyEqptUpdate(4)
                }

FspR7SysType ::= TEXTUAL-CONVENTION
  STATUS        current
  DESCRIPTION
         "Type of Network Element" 
  SYNTAX        INTEGER
                {
                  undefined(0),
                  otm(1),  --Node configuration that provides a single degree with channel add-drop.
                  oadm(2),  --Node configuration that provides multiple degrees with channel add-drop.
                  converter(3),  --Node configuration that provides channel power equalization and optical amplification without add-drop. Channel powers are converted to the same level to increase reach.
                  ila(4),  --Node configuration that provides optical amplification without channel add-drop.
                  hub(5)  --Node configuration that supports a multiple degrees with channel add-drop to all other nodes in the network.
                }

FspR7TelemetryOutput ::= TEXTUAL-CONVENTION
  STATUS        current
  DESCRIPTION
         "Telemetry interface output provision" 
  SYNTAX        INTEGER
                {
                  undefined(0),
                  neAlmCr(1),  --Network Element alarm with critical severity
                  neAlmMj(2),  --Network Element alarm with major severity
                  neAlmMn(3),  --Network Element alarm with minor severity
                  neAlmMjGe(4),  --Network Element alarm with major or greater severity
                  neAlmMnGe(5),  --Network Element alarm with minor or greater severity
                  fcuAlmCr(6),  --FCU alarm with critical severity
                  fcuAlmMj(7),  --FCU alarm with major severity
                  fcuAlmMn(8),  --FCU alarm with minor severity
                  fcuAlmMjGe(9),  --FCU alarm with major or greater severity
                  fcuAlmMnGe(10),  --FCU alarm with minor or greater severity
                  psuAlmCr(11),  --PSU alarm with critical severity
                  psuAlmMj(12),  --PSU alarm with major severity
                  psuAlmMn(13),  --PSU alarm with minor severity
                  psuAlmMjGe(14),  --PSU alarm with major or greater severity
                  psuAlmMnGe(15),  --PSU alarm with minor or greater severity
                  none(16)  --No alarm group assigned
                }

FspR7TelemetryOutputCaps ::= TEXTUAL-CONVENTION
  STATUS        current
  DESCRIPTION
         "Telemetry interface output provision" 
  SYNTAX        BITS
                {
                  capUndefined(0),
                  capNeAlmCr(1),
                  capNeAlmMj(2),
                  capNeAlmMn(3),
                  capNeAlmMjGe(4),
                  capNeAlmMnGe(5),
                  capFcuAlmCr(6),
                  capFcuAlmMj(7),
                  capFcuAlmMn(8),
                  capFcuAlmMjGe(9),
                  capFcuAlmMnGe(10),
                  capPsuAlmCr(11),
                  capPsuAlmMj(12),
                  capPsuAlmMn(13),
                  capPsuAlmMjGe(14),
                  capPsuAlmMnGe(15),
                  capNone(16)
                }

FspR7TerminateSessions ::= TEXTUAL-CONVENTION
  STATUS        current
  DESCRIPTION
         "Shows forced logout availability for selected user and allows to take such an action." 
  SYNTAX        INTEGER
                {
                  undefined(0),
                  allowed(1),
                  forbidden(2),
                  apply(3)
                }

FspR7TestMode ::= TEXTUAL-CONVENTION
  STATUS        current
  DESCRIPTION
         "Sets the operation mode for reveiver PRBS testing" 
  SYNTAX        INTEGER
                {
                  undefined(0),
                  testModeRls(1),
                  testModePRBS23(2),  --Pseudo Random Bit Sequence with 23 bit
                  testModePRBS23Inv(3),  --Pseudo Random Bit Sequence with 23 bit inverted
                  testModePRBS31(4),  --Pseudo Random Bit Sequence with 31 bit
                  testModePRBS31Inv(5)  --Pseudo Random Bit Sequence with 31 bit inverted
                }

FspR7TestModeCaps ::= TEXTUAL-CONVENTION
  STATUS        current
  DESCRIPTION
         "Sets the operation mode for reveiver PRBS testing" 
  SYNTAX        BITS
                {
                  capUndefined(0),
                  capTestModeRls(1),
                  capTestModePRBS23(2),
                  capTestModePRBS23Inv(3),
                  capTestModePRBS31(4),
                  capTestModePRBS31Inv(5)
                }

FspR7TifOutputReset ::= TEXTUAL-CONVENTION
  STATUS        current
  DESCRIPTION
         "Has the same function as the HW switch at the UTM board" 
  SYNTAX        INTEGER
                {
                  undefined(0),
                  rls(1),  --Telemetry Interface Output is not changed
                  opr(2)  --Reset Telemetry Interface Output
                }

FspR7TifOutputResetCaps ::= TEXTUAL-CONVENTION
  STATUS        current
  DESCRIPTION
         "Has the same function as the HW switch at the UTM board" 
  SYNTAX        BITS
                {
                  capUndefined(0),
                  capRls(1),
                  capOpr(2)
                }

FspR7Time ::= TEXTUAL-CONVENTION
  DISPLAY-HINT "1d-1d-1d"
  STATUS        current
  DESCRIPTION
         "A time specification.
         field octets contents range
         ----- ------ -------- -----
         1 1 hour 0..23
         2 2 minutes 0..59
         3 3 seconds 0..60
         (use 60 for leap-second)
         For example: 13-10-26" 
  SYNTAX        OCTET STRING (SIZE(3..3))

FspR7TimeShort ::= TEXTUAL-CONVENTION
  DISPLAY-HINT "1d-1d"
  STATUS        current
  DESCRIPTION
         "A time specification.
         field octets contents range
         ----- ------ -------- -----
         1 1 hour 0..23
         2 1 minutes 0..59
         For example: 13-10" 
  SYNTAX        OCTET STRING (SIZE(2..2))

FspR7TimeChangeReason ::= TEXTUAL-CONVENTION
  STATUS        current
  DESCRIPTION
         "Time Change Reason" 
  SYNTAX        INTEGER
                {
                  undefined(0),
                  none(1),
                  manual(2),
                  correction(3),
                  dst(4)
                }

FspR7TiltSet ::= TEXTUAL-CONVENTION
  STATUS        current
  DESCRIPTION
         "Tilt setting as discrete values versus a range" 
  SYNTAX        INTEGER
                {
                  undefined(0),
                  minus1dB0(1),
                  minus1dB5(2),
                  minus2dB0(3)
                }

FspR7TiltSetCaps ::= TEXTUAL-CONVENTION
  STATUS        current
  DESCRIPTION
         "Tilt setting as discrete values versus a range" 
  SYNTAX        BITS
                {
                  capUndefined(0),
                  capMinus1dB0(1),
                  capMinus1dB5(2),
                  capMinus2dB0(3)
                }

FspR7TL1InternalState ::= TEXTUAL-CONVENTION
  STATUS        current
  DESCRIPTION
         "" 
  SYNTAX        INTEGER
                {
                  undefined(0),
                  alw(1),
                  inh(2)
                }

FspR7TL1InternalStateCaps ::= TEXTUAL-CONVENTION
  STATUS        current
  DESCRIPTION
         "" 
  SYNTAX        BITS
                {
                  capUndefined(0),
                  capAlw(1),
                  capInh(2)
                }

FspR7TL1TimoutAvailable ::= TEXTUAL-CONVENTION
  STATUS        current
  DESCRIPTION
         "" 
  SYNTAX        INTEGER
                {
                  undefined(0),
                  yes(1),
                  no(2)
                }

FspR7TL1TimoutAvailableCaps ::= TEXTUAL-CONVENTION
  STATUS        current
  DESCRIPTION
         "" 
  SYNTAX        BITS
                {
                  capUndefined(0),
                  capYes(1),
                  capNo(2)
                }

FspR7TopologyType ::= TEXTUAL-CONVENTION
  STATUS        current
  DESCRIPTION
         "Monitored Topology Type" 
  SYNTAX        INTEGER
                {
                  undefined(0),
                  lad(1),
                  ring(2),
                  p2p(3),
                  unknown(4)
                }

FspR7TopologyTypeCaps ::= TEXTUAL-CONVENTION
  STATUS        current
  DESCRIPTION
         "Monitored Topology Type" 
  SYNTAX        BITS
                {
                  capUndefined(0),
                  capLad(1),
                  capRing(2),
                  capP2p(3),
                  capUnknown(4)
                }

FspR7TrafficDirection ::= TEXTUAL-CONVENTION
  STATUS        current
  DESCRIPTION
         "Traffic Direction" 
  SYNTAX        INTEGER
                {
                  undefined(0),
                  bidi(1),  --Bidirectional Traffic (standard application)
                  uniCton(2),
                  uniNtoc(3),
                  uniWtoe(4),
                  uniEtow(5),
                  txcrs(6),  --Unidirectional traffic; Naming convention: CRS transmitts data to CH, UCH,VCH or others entities
                  rxcrs(7)  --Unidirectional traffic; Naming convention:CRS receives data from CH, UCH, VCH or other entities
                }

FspR7TrafficDirectionCaps ::= TEXTUAL-CONVENTION
  STATUS        current
  DESCRIPTION
         "Traffic Direction" 
  SYNTAX        BITS
                {
                  capUndefined(0),
                  capBidi(1),
                  capUniCton(2),
                  capUniNtoc(3),
                  capUniWtoe(4),
                  capUniEtow(5),
                  capTxcrs(6),
                  capRxcrs(7)
                }

FspR7TransmissionMode ::= TEXTUAL-CONVENTION
  STATUS        current
  DESCRIPTION
         "Mode of the module, determine operation or functionality" 
  SYNTAX        INTEGER
                {
                  undefined(0),
                  trans(1),  --Simple transport of signal without protection on a TRANSponder card with only one network port for which it is default.
                  transE(2),  --Simple transport of signal without protection using the port CH-NE.
                  transW(3),  --Simple transport of signal without protection using the port CH-NW.
                  transHst(4),  --Transport of signal with network port protection (only on TRANSponder cards with two network ports, for which it is default).
                  mux(5),  --Simple aggregation of signals without protection on a MUXponder card with only one network port - for which it is default.
                  muxE(6),  --Simple aggregation of signals without protection using the port CH-NE.
                  muxW(7),  --Simple aggregation of signals without protection using the port CH-NW.
                  muxHst(8),  --Aggregation of signals with network port protection (only on MUXponder cards with two network ports - for which it is default).
                  regen1Way(9),  --Regeneration of signal using network port(s).
                  regen2Way(10),  --Regeneration of signal using network port(s).
                  obsolete(11),  --To remove.
                  adm(12),  --Add, Drop, Passthrough, Drop and Continue Fuctionality
                  transDual(13),  --Dual Transport of signal without protection on a Transponder card with two network ports
                  muxDual(14),  --Dual Transport of signal without protection on a Muxponder card with two network ports
                  nFixed(15),  --Add/Drop channels connected to the associated Network Fiber. Channel filter must be connected to C port associated with the ROADM number 
                  cSelect(16),  --Add/Drop channels can be connected to any Network Fiber. Channel filter must be connected to N port. C port associated with ROADM number is not connected.
                  dualClient(17),  --Two (2) client ports are allocated for add/drop.  Add/Drop channels for C-Even wavelengths (1-40) are allocated to C port associated with the ROADM number. Add/Dropchannels for C-Odd wavelengths (41-80) are allocated to C8 port.
                  xc(20),  --(X)cross Connect mode. Used on cards that cross connects traffic between generic ports.
                  transQuad(21),  -- Quad Transport of signal without protection on a Transponder card
                  transQuintuple(22),  --Quintuple Transport of signal without protection on a Transponder card
                  std(23),  --Traffic Path is between C port and this N Port only
                  pair(24),  --Traffic Path is between C port and this N Port and N Port designated as the protection partner. Channel protection requries FFP to be added.
                  mux10GEnterprise(25)  --10G Multiplexer with Enterprise feature set
                }

FspR7TransmissionModeCaps ::= TEXTUAL-CONVENTION
  STATUS        current
  DESCRIPTION
         "Mode of the module, determine operation or functionality" 
  SYNTAX        BITS
                {
                  capUndefined(0),
                  capTrans(1),
                  capTransE(2),
                  capTransW(3),
                  capTransHst(4),
                  capMux(5),
                  capMuxE(6),
                  capMuxW(7),
                  capMuxHst(8),
                  capRegen1Way(9),
                  capRegen2Way(10),
                  capObsolete(11),
                  capAdm(12),
                  capTransDual(13),
                  capMuxDual(14),
                  capNFixed(15),
                  capCSelect(16),
                  capDualClient(17),
                  capXc(20),
                  capTransQuad(21),
                  capTransQuintuple(22),
                  capStd(23),
                  capPair(24),
                  capMux10GEnterprise(25)
                }

FspR7TurnupConfig ::= TEXTUAL-CONVENTION
  STATUS        current
  DESCRIPTION
         "Turnup Operation" 
  SYNTAX        INTEGER
                {
                  undefined(0),
                  rls(1),
                  oprTurnup(2)
                }

FspR7TurnupConfigCaps ::= TEXTUAL-CONVENTION
  STATUS        current
  DESCRIPTION
         "Turnup Operation" 
  SYNTAX        BITS
                {
                  capUndefined(0),
                  capRls(1),
                  capOprTurnup(2)
                }

FspR7TypeConnection ::= TEXTUAL-CONVENTION
  STATUS        current
  DESCRIPTION
         "Type of equipment connection" 
  SYNTAX        INTEGER
                {
                  undefined(0),
                  connection1Way(1),
                  connection2Way(2)
                }

FspR7TypeConnectionCaps ::= TEXTUAL-CONVENTION
  STATUS        current
  DESCRIPTION
         "Type of equipment connection" 
  SYNTAX        BITS
                {
                  capUndefined(0),
                  capConnection1Way(1),
                  capConnection2Way(2)
                }

FspR7TypeCrs ::= TEXTUAL-CONVENTION
  STATUS        current
  DESCRIPTION
         "Type of Cross-Connect" 
  SYNTAX        INTEGER
                {
                  undefined(0),
                  connection1Way(1),  --Unidirectional CRS
                  connection2Way(2),  --Bidirectional CRS
                  connection1WayProt(3),  --Unidirectional CRS with protection
                  connection2WayProt(4),  --Bidirectional CRS with protection
                  connection1WayMc(5),  --Unidirectional multicast CRS
                  connection1WayDc(6),  --Unidirectional Drop and Continue
                  connection1WayDcProt(7),  --Unidirectional Drop and Continue with protection
                  connection1WayMcProt(8),  --Unidirectional multicast with protection
                  connection1WayCont(9),  --Unidirectional Continue Path
                  connection2WayCont(10)  --Bidirectional Continue Path
                }

FspR7TypeCrsCaps ::= TEXTUAL-CONVENTION
  STATUS        current
  DESCRIPTION
         "Type of Cross-Connect" 
  SYNTAX        BITS
                {
                  capUndefined(0),
                  capConnection1Way(1),
                  capConnection2Way(2),
                  capConnection1WayProt(3),
                  capConnection2WayProt(4),
                  capConnection1WayMc(5),
                  capConnection1WayDc(6),
                  capConnection1WayDcProt(7),
                  capConnection1WayMcProt(8),
                  capConnection1WayCont(9),
                  capConnection2WayCont(10)
                }

FspR7Unsigned32Caps ::= TEXTUAL-CONVENTION
  DISPLAY-HINT "4d:4d"
  STATUS        current
  DESCRIPTION
         "A FspR7Unsigned32Caps specification.
         1..4 bytes - minValue(Unsigned32),
         5..8 bytes - maxValue(Unsigned32)." 
  SYNTAX        OCTET STRING (SIZE(0..8))

FspR7UntaggedFrames ::= TEXTUAL-CONVENTION
  STATUS        current
  DESCRIPTION
         "If untagged frames shall be enabled on this port or not." 
  SYNTAX        INTEGER
                {
                  undefined(0),
                  accept(1),
                  reject(2)
                }

FspR7UntaggedFramesCaps ::= TEXTUAL-CONVENTION
  STATUS        current
  DESCRIPTION
         "If untagged frames shall be enabled on this port or not." 
  SYNTAX        BITS
                {
                  capUndefined(0),
                  capAccept(1),
                  capReject(2)
                }

FspR7VoaMode ::= TEXTUAL-CONVENTION
  STATUS        current
  DESCRIPTION
         "VOA operating mode" 
  SYNTAX        INTEGER
                {
                  undefined(0),
                  power(1),  --Constant power mode
                  att(2)  --Constant attenuation mode
                }

FspR7VoaModeCaps ::= TEXTUAL-CONVENTION
  STATUS        current
  DESCRIPTION
         "VOA operating mode" 
  SYNTAX        BITS
                {
                  capUndefined(0),
                  capPower(1),
                  capAtt(2)
                }

FspR7Swdx ::= TEXTUAL-CONVENTION
  STATUS        current
  DESCRIPTION
         "Switch to Parnter Controller" 
  SYNTAX        INTEGER
                {
                  undefined(0),
                  noAction(1),
                  manualSwitch(2)
                }

FspR7XfpDecisionThres ::= TEXTUAL-CONVENTION
  STATUS        current
  DESCRIPTION
         "XFP Decision threshold setting" 
  SYNTAX        INTEGER
                {
                  undefined(0),
                  standard(1),
                  forwardRaman(2)
                }

FspR7XfpDecisionThresCaps ::= TEXTUAL-CONVENTION
  STATUS        current
  DESCRIPTION
         "XFP Decision threshold setting" 
  SYNTAX        BITS
                {
                  capUndefined(0),
                  capStandard(1),
                  capForwardRaman(2)
                }

FspR7YesNo ::= TEXTUAL-CONVENTION
  STATUS        current
  DESCRIPTION
         "YesNo variable." 
  SYNTAX        INTEGER

                {
                  undefined(0),
                  yes(1),
                  no(2)
                }

FspR7YesNoCaps ::= TEXTUAL-CONVENTION
  STATUS        current
  DESCRIPTION
         "YesNo variable." 
  SYNTAX        BITS
                {
                  capUndefined(0),
                  capYes(1),
                  capNo(2)
                }

SourceIpAddress ::= TEXTUAL-CONVENTION
  STATUS        current
  DESCRIPTION
         "IP address which will be used as source address by client applications (i.e. FTP) to facilitate proper backward routing (i.e. server to client direction) in the DCN" 
  SYNTAX        INTEGER
                {
                  undefined(0),
                  sysIp(1),
                  defaultIp(2)
                }

SourceIpAddressCaps ::= TEXTUAL-CONVENTION
  STATUS        current
  DESCRIPTION
         "IP address which will be used as source address by client applications (i.e. FTP) to facilitate proper backward routing (i.e. server to client direction) in the DCN" 
  SYNTAX        BITS
                {
                  capUndefined(0),
                  capSysIp(1),
                  capDefaultIp(2)
                }

neSystemId OBJECT-TYPE
    SYNTAX      SnmpAdminString
    MAX-ACCESS  read-write
    STATUS      current
    DESCRIPTION   "System Identifier"
    ::=  { neAdmin 1 }

neSysType OBJECT-TYPE
    SYNTAX      FspR7SysType
    MAX-ACCESS  read-write
    STATUS      current
    DESCRIPTION
        "Type of Network Element"
    ::=  { neAdmin 2 }

neAutoProvisioning OBJECT-TYPE
    SYNTAX      FspR7YesNo
    MAX-ACCESS  read-write
    STATUS      current
    DESCRIPTION
        "When set to 'Disable', the user must manually provision equipment and facilities.
         When set to 'Enable', equipment is automatically provisioned.
         If 'Auto In Service Control' is 'Enable' then Admin State is set to 'Auto In Service'.
         If 'Auto In Service Control' is 'Disable' then Admin State is set to 'In Service'.
         Node level parameter."
    ::=  { neAdmin 3 }

neType OBJECT-TYPE
    SYNTAX      FspR7NeType
    MAX-ACCESS  read-write
    STATUS      current
    DESCRIPTION
        "Type of Network Element"
    ::=  { neAdmin 4 }

neSwVersion OBJECT-TYPE
    SYNTAX      SnmpAdminString
    MAX-ACCESS  read-only
    STATUS      current
    DESCRIPTION
        "Software Version of the NCU software. <"
    ::=  { neAdmin 5 }

neGradeInventory OBJECT-TYPE
    SYNTAX      Grade
    MAX-ACCESS  read-only
    STATUS      current
    DESCRIPTION
        "Used to distinguish between NCU capabilities (range of supported services or applications)"
    ::=  { neAdmin 6 }

neModel OBJECT-TYPE
    SYNTAX      FspR7Model
    MAX-ACCESS  read-only
    STATUS      current
    DESCRIPTION
        "Marketing model name of System"
    ::=  { neAdmin 7 }

neVendorId OBJECT-TYPE
    SYNTAX      SnmpAdminString
    MAX-ACCESS  read-only
    STATUS      current
    DESCRIPTION
        "The name of the manufacturer"
    ::=  { neAdmin 8 }

neAINSProvEnabled OBJECT-TYPE
    SYNTAX      FspR7YesNo
    MAX-ACCESS  read-write
    STATUS      current
    DESCRIPTION
        "When set to 'Disable', a manually provisioned entity has a default Admin State of 'Management'.
         When set to 'Disable', an auto provisioned entity has a default Admin State of 'In Service'.
         When set to 'Enable', a manual or auto provisioned entity has a default Admin State of 'Auto In Service'.
         Node level parameter."
    ::=  { neAdmin 9 }

neAINSDefaultTimer OBJECT-TYPE
    SYNTAX      Unsigned32 (0..5760 | 4294967295) 
    UNITS       "Min"
    MAX-ACCESS  read-write
    STATUS      current
    DESCRIPTION   "AINS Default Signal Timer. The length of time in minutes for which an
         entity must be free of service affecting conditions in order to automatically
         transition from an OOS-AU,AINS state to an inservice state. The value is set via
         the system configuration file. If the value is set to 0, an entity in the OOS-AU, AINS
         state will immediately transition to an in-service state."
    ::=  { neAdmin 10 }

nePreferredFacilityType OBJECT-TYPE
    SYNTAX      FspR7PreferredFacilityType
    MAX-ACCESS  read-write
    STATUS      current
    DESCRIPTION
        ">Default type of facility model to use for automatically created, an entity in the OOS-AU,AINS
         facilities. SDH will cause STM64, STM16, VC4, VC3 type
         state will immediately transition to an in-service state.AINS Default Signal Timer. The length of time in hours and minutes
         facilities to be auto-created. SONET will cause OC192,
         for which an entity must be free of service affecting conditions in
         OC48, STS1 and STS3c type facilities to be auto-created."
    ::=  { neAdmin 11 }

neForceDelete OBJECT-TYPE
    SYNTAX      EnableState
    MAX-ACCESS  read-write
    STATUS      current
    DESCRIPTION
        "Force Delete"
    ::=  { neAdmin 12 }

neSdhSesThreshold OBJECT-TYPE
    SYNTAX      Unsigned32 (0..100 | 4294967295) 
    UNITS       "%"
    MAX-ACCESS  read-write
    STATUS      current
    DESCRIPTION   "Severely Errorred Seconds percentage for SDH facilities. Sets the default
         relative percentage of Errorred Seconds within a PM interval at which Severely Errorred
         Seconds will be declared."
    ::=  { neAdmin 14 }

neOtnSesThreshold OBJECT-TYPE
    SYNTAX      Unsigned32 (0..100 | 4294967295) 
    UNITS       "%"
    MAX-ACCESS  read-write
    STATUS      current
    DESCRIPTION   "Severely Errorred Seconds percentage for OTN facilities. Sets the default
         relative percentage of Errorred Seconds within a PM interval at which Severely Errorred
         Seconds will be declared."
    ::=  { neAdmin 15 }

neTopologyType OBJECT-TYPE
    SYNTAX      FspR7TopologyType
    MAX-ACCESS  read-write
    STATUS      deprecated
    DESCRIPTION
        "Monitored Topology Type"
    ::=  { neAdmin 16 }

neDatabaseSerialNumber OBJECT-TYPE
    SYNTAX      SnmpAdminString
    MAX-ACCESS  read-only
    STATUS      current
    DESCRIPTION
        "read from Master Shelf and stored in the DB 'once'; only changed when a command which implies a change is given (INIT__SYS with DBSRST = ACCEPT)"
    ::=  { neAdmin 17 }

neDatabaseType OBJECT-TYPE
    SYNTAX      FspR7DatabaseType
    MAX-ACCESS  read-only
    STATUS      current
    DESCRIPTION
        "this shows whether the system is running on a temporary auxiliary DB or on the DB in ACT, which is the normal situation"
    ::=  { neAdmin 18 }

neRackSize OBJECT-TYPE
    SYNTAX      Unsigned32 (1..45 | 4294967295) 
    UNITS       "HU"
    MAX-ACCESS  read-write
    STATUS      current
    DESCRIPTION
        "Size of the Rack in HU"
    ::=  { neAdmin 19 }

neDatabaseNcuType OBJECT-TYPE
    SYNTAX      FspR7EquipmentType
    MAX-ACCESS  read-only
    STATUS      current
    DESCRIPTION
        "DB Type of NCU"
    ::=  { neAdmin 20 }

neDatabaseNcuAid OBJECT-TYPE
    SYNTAX      EntityIndex
    MAX-ACCESS  read-only
    STATUS      current
    DESCRIPTION   "Aid of NCU in database"
    ::=  { neAdmin 21 }

neModusLastRestart OBJECT-TYPE
    SYNTAX      FspR7ModusLastRestart
    MAX-ACCESS  read-only
    STATUS      current
    DESCRIPTION
        "Information over the modus of the last restart"
    ::=  { neAdmin 22 }

neSystemIp OBJECT-TYPE
    SYNTAX      IpAddress
    MAX-ACCESS  read-write
    STATUS      current
    DESCRIPTION   "System IP"
    ::=  { neAdmin 23 }

neSystemIpMask OBJECT-TYPE
    SYNTAX      IpAddress
    MAX-ACCESS  read-write
    STATUS      current
    DESCRIPTION   "System IP Mask"
    ::=  { neAdmin 24 }

neAreaId OBJECT-TYPE
    SYNTAX      IpAddress
    MAX-ACCESS  read-write
    STATUS      current
    DESCRIPTION
        "OSPF Area ID for IP Interface"
    ::=  { neAdmin 25 }

neBackupScuAvailable OBJECT-TYPE
    SYNTAX      FspR7ScuDbBackup
    MAX-ACCESS  read-only
    STATUS      current
    DESCRIPTION
        "DB Backup on SCU available"
    ::=  { neAdmin 26 }

neRouteRedistribution OBJECT-TYPE
    SYNTAX      FspR7RouteRedist
    MAX-ACCESS  read-write
    STATUS      current
    DESCRIPTION
        "Redistribution of routes in OSPF"
    ::=  { neAdmin 27 }

neAlarmActivationTime OBJECT-TYPE
    SYNTAX      Unsigned32 (0..100 | 4294967295) 
    UNITS       "0.1 s"
    MAX-ACCESS  read-write
    STATUS      current
    DESCRIPTION
        "Alarm activation time. The hold-off period during which a defect must persist in order to be raised as an alarmed event (in seconds)."
    ::=  { neAdmin 28 }

neAlarmDeactivationTime OBJECT-TYPE
    SYNTAX      Unsigned32 (0..100 | 4294967295) 
    UNITS       "0.1 s"
    MAX-ACCESS  read-write
    STATUS      current
    DESCRIPTION
        "Alarm deactivation time. The hold-on period during
         which a defect must remain absent in order for the corresponding
         previously raised alarm reporting the condition will be cleared (in seconds)."
    ::=  { neAdmin 29 }

neDate OBJECT-TYPE
    SYNTAX      FspR7Date
    MAX-ACCESS  read-write
    STATUS      current
    DESCRIPTION
        "Date"
    ::=  { neTimeConfig 1 }

neTime OBJECT-TYPE
    SYNTAX      FspR7Time
    MAX-ACCESS  read-write
    STATUS      current
    DESCRIPTION
        "Time, display rule: HH-MM-SS"
    ::=  { neTimeConfig 2 }

neTimeZone OBJECT-TYPE
    SYNTAX      SnmpAdminString
    MAX-ACCESS  read-write
    STATUS      current
    DESCRIPTION
        "Time Zone"
    ::=  { neTimeConfig 3 }

neNetworkTimeProtocol OBJECT-TYPE
    SYNTAX      EnableState
    MAX-ACCESS  read-only
    STATUS      deprecated
    DESCRIPTION   "Network Time Protocol Provisioned State."
    ::=  { neTimeConfig 4 }

neNtpServer1 OBJECT-TYPE
    SYNTAX      IpAddress
    MAX-ACCESS  read-write
    STATUS      deprecated
    DESCRIPTION
        "IP address of NTP Server 1"
    ::=  { neTimeConfig 5 }

neNtpServer2 OBJECT-TYPE
    SYNTAX      IpAddress
    MAX-ACCESS  read-write
    STATUS      deprecated
    DESCRIPTION
        "IP address of NTP Server 2"
    ::=  { neTimeConfig 6 }

neNtpServer3 OBJECT-TYPE
    SYNTAX      IpAddress
    MAX-ACCESS  read-write
    STATUS      deprecated
    DESCRIPTION
        "IP address of NTP Server 3"
    ::=  { neTimeConfig 7 }

neNtpStatusServer1 OBJECT-TYPE
    SYNTAX      FspR7NtpServerStatus
    MAX-ACCESS  read-only
    STATUS      deprecated
    DESCRIPTION   "NTP server is reachabled or unreachabled. Get is blocking for 4 second."
    ::=  { neTimeConfig 8 }

neNtpStatusServer2 OBJECT-TYPE
    SYNTAX      FspR7NtpServerStatus
    MAX-ACCESS  read-only
    STATUS      deprecated
    DESCRIPTION   "NTP server is reachabled or unreachabled. Get is blocking for 4 second."
    ::=  { neTimeConfig 9 }

neNtpStatusServer3 OBJECT-TYPE
    SYNTAX      FspR7NtpServerStatus
    MAX-ACCESS  read-only
    STATUS      deprecated
    DESCRIPTION   "NTP server is reachabled or unreachabled. Get is blocking for 4 second."
    ::=  { neTimeConfig 10 }

neNtpSourceIp OBJECT-TYPE
    SYNTAX      SourceIpAddress
    MAX-ACCESS  read-write
    STATUS      deprecated
    DESCRIPTION
        "IP address which will be used as source address by client applications (i.e. FTP) to facilitate proper backward routing (i.e. server to client direction) in the DCN"
    ::=  { neTimeConfig 11 }

neTimeZoneOffset OBJECT-TYPE
    SYNTAX      Integer32
    MAX-ACCESS  read-only
    STATUS      current
    DESCRIPTION
        "Time Zone Offset"
    ::=  { neTimeConfig 12 }

neDaylightSavingsTimeEnabled OBJECT-TYPE
    SYNTAX      FspR7YesNo
    MAX-ACCESS  read-only
    STATUS      current
    DESCRIPTION   "Boolean value indicating if Daylight Saving Time is enabled."
    ::=  { neTimeConfig 13 }

neNtpMode OBJECT-TYPE
    SYNTAX      FspR7NtpMode
    MAX-ACCESS  read-write
    STATUS      current
    DESCRIPTION
        "NTP Service Mode"
    ::=  { neTimeConfig 14 }

neTimeChangeReason OBJECT-TYPE
    SYNTAX      FspR7TimeChangeReason
    MAX-ACCESS  read-only
    STATUS      current
    DESCRIPTION
        "Time Change Reason"
    ::=  { neTimeConfig 15 }

neDateUtc OBJECT-TYPE
    SYNTAX      FspR7Date
    MAX-ACCESS  read-only
    STATUS      current
    DESCRIPTION
        "Date in UTC format"
    ::=  { neTimeConfig 16 }

neTimeUtc OBJECT-TYPE
    SYNTAX      FspR7Time
    MAX-ACCESS  read-only
    STATUS      current
    DESCRIPTION
        "Time in UTC format"
    ::=  { neTimeConfig 17 }

ntpServerTable OBJECT-TYPE
    SYNTAX      SEQUENCE OF NtpServerEntry
    MAX-ACCESS  not-accessible
    STATUS      current
    DESCRIPTION   "The NTP Server configuration table."
    ::=  { neTimeConfig 20 }

ntpServerEntry OBJECT-TYPE
    SYNTAX      NtpServerEntry
    MAX-ACCESS  not-accessible
    STATUS      current
    DESCRIPTION   "The NTP Server entity."
    INDEX       {
                  ntpServerIp
                }
    ::=  { ntpServerTable 1 }

NtpServerEntry ::=  SEQUENCE
  { ntpServerIp IpAddress,
    ntpServerSourceIp SourceIpAddress,
    ntpServerTest FspR7NtpTest,
    ntpServerTestStatus FspR7NtpTestStatus,
    ntpServerSyncStatus FspR7NtpSyncStatus,
    ntpServerAdminState FspR7NtpAdminState,
    ntpServerOperState FspR7OperState,
    ntpServerRowStatus RowStatus }

ntpServerIp OBJECT-TYPE
    SYNTAX      IpAddress
    MAX-ACCESS  accessible-for-notify
    STATUS      current
    DESCRIPTION   "The IP address of the remote NTP server."
    ::=  { ntpServerEntry 1 }

ntpServerSourceIp OBJECT-TYPE
    SYNTAX      SourceIpAddress
    MAX-ACCESS  read-write
    STATUS      current
    DESCRIPTION   "Network interface type used for NTP connection. Two interface types are defined:
         sysIp(1) and defaultIp(2).
        "
    ::=  { ntpServerEntry 2 }

ntpServerTest OBJECT-TYPE
    SYNTAX      FspR7NtpTest
    MAX-ACCESS  read-write
    STATUS      current
    DESCRIPTION   "Operational parameter for invoking a connection test procedure. If set
         to ntpTest(2) then a connection with remote NTP server is being checked.
         Result of this operation is saved under ntpServerTestStatus column. When
         operation finish then value is automaticaly set to rls(1). It cannot
         be set to rls(1) by hand.
        "
    ::=  { ntpServerEntry 3 }

ntpServerTestStatus OBJECT-TYPE
    SYNTAX      FspR7NtpTestStatus
    MAX-ACCESS  read-only
    STATUS      current
    DESCRIPTION   "Result of NTP availability check command invoked by setting ntpServerTest to ntpTest(2)."
    ::=  { ntpServerEntry 4 }

ntpServerSyncStatus OBJECT-TYPE
    SYNTAX      FspR7NtpSyncStatus
    MAX-ACCESS  read-only
    STATUS      current
    DESCRIPTION   "The NTP Synchronization status."
    ::=  { ntpServerEntry 5 }

ntpServerAdminState OBJECT-TYPE
    SYNTAX      FspR7NtpAdminState
    MAX-ACCESS  read-write
    STATUS      current
    DESCRIPTION   "Administrative state of remote NTP server. It can be set to is(2) or to dsbld(6)."
    ::=  { ntpServerEntry 6 }

ntpServerOperState OBJECT-TYPE
    SYNTAX      FspR7OperState
    MAX-ACCESS  read-only
    STATUS      current
    DESCRIPTION   "Operative state of remote NTP server."
    ::=  { ntpServerEntry 7 }

ntpServerRowStatus OBJECT-TYPE
    SYNTAX      RowStatus
    MAX-ACCESS  read-write
    STATUS      current
    DESCRIPTION   "Row status used for managing a NTP server entity. All values defined for
         RowStatus TC can be used.
        "
    ::=  { ntpServerEntry 8 }

ntpTimeZoneCapsTable OBJECT-TYPE
    SYNTAX      SEQUENCE OF NtpTimeZoneCapsEntry
    MAX-ACCESS  not-accessible
    STATUS      current
    DESCRIPTION   "Table with available time zones."
    ::=  { neTimeConfig 21 }

ntpTimeZoneCapsEntry OBJECT-TYPE
    SYNTAX      NtpTimeZoneCapsEntry
    MAX-ACCESS  not-accessible
    STATUS      current
    DESCRIPTION   "Every entry corresponds to time zone name."
    INDEX       {
                  ntpTimeZoneCapsIndex
                }
    ::=  { ntpTimeZoneCapsTable 1 }

NtpTimeZoneCapsEntry ::=  SEQUENCE
  { ntpTimeZoneCapsIndex Integer32,
    ntpTimeZoneCapsValue SnmpAdminString }

ntpTimeZoneCapsIndex OBJECT-TYPE
    SYNTAX      Integer32
    MAX-ACCESS  not-accessible
    STATUS      current
    DESCRIPTION   "Row number of ntpTimeZoneCapsTable."
    ::=  { ntpTimeZoneCapsEntry 1 }

ntpTimeZoneCapsValue OBJECT-TYPE
    SYNTAX      SnmpAdminString
    MAX-ACCESS  read-only
    STATUS      current
    DESCRIPTION   "Name of the time-zone possible to be used as neTimeZone."
    ::=  { ntpTimeZoneCapsEntry 2 }

neTimerForceOprToRls OBJECT-TYPE
    SYNTAX      Unsigned32 (1..1440 | 4294967295) 
    UNITS       "min"
    MAX-ACCESS  read-write
    STATUS      current
    DESCRIPTION
        "The length of time in minutes for which
         a FRCD__OPERATION OPR state will automatically changed to RLS state.
         The value is set via the system configuration file."
    ::=  { neAdmin 31 }

neScuRing OBJECT-TYPE
    SYNTAX      FspR7ScuRing
    MAX-ACCESS  read-write
    STATUS      current
    DESCRIPTION
        "SCU Interconnection"
    ::=  { neAdmin 32 }

neScuRingCap OBJECT-TYPE
    SYNTAX      FspR7ScuRingCaps
    MAX-ACCESS  read-only
    STATUS      current
    DESCRIPTION
        "SCU Interconnection"
    ::=  { neAdmin 33 }

neAlarmProfileApply OBJECT-TYPE
    SYNTAX      FspR7ApplyAlarmProfile
    MAX-ACCESS  read-write
    STATUS      current
    DESCRIPTION
        "Apply Alarm Profile to all existing entities"
    ::=  { neAdmin 34 }

neAlarmProfileApplyCap OBJECT-TYPE
    SYNTAX      FspR7ApplyAlarmProfileCaps
    MAX-ACCESS  read-only
    STATUS      current
    DESCRIPTION
        "Apply Alarm Profile to all existing entities"
    ::=  { neAdmin 35 }

neFtpServer OBJECT-TYPE
    SYNTAX      FspR7FtpServer
    MAX-ACCESS  read-write
    STATUS      current
    DESCRIPTION
        "FTP server enable/disable configuration"
    ::=  { neAdmin 36 }

neFtpServerCap OBJECT-TYPE
    SYNTAX      FspR7FtpServerCaps
    MAX-ACCESS  read-only
    STATUS      current
    DESCRIPTION
        "FTP server enable/disable configuration"
    ::=  { neAdmin 37 }

neFtpClient OBJECT-TYPE
    SYNTAX      FspR7FtpClient
    MAX-ACCESS  read-write
    STATUS      current
    DESCRIPTION
        "FTP client enable/disable configuration"
    ::=  { neAdmin 38 }

neSshDeamon OBJECT-TYPE
    SYNTAX      FspR7SshDeamon
    MAX-ACCESS  read-write
    STATUS      current
    DESCRIPTION
        "Secure Shell Interface Control"
    ::=  { neAdmin 39 }

neEqlzAdmin OBJECT-TYPE
    SYNTAX      FspR7EqlzAdminState
    MAX-ACCESS  read-write
    STATUS      current
    DESCRIPTION
        "Scheduled Equalization Administration"
    ::=  { neAdmin 40 }

neEqlzAdminCap OBJECT-TYPE
    SYNTAX      FspR7EqlzAdminStateCaps
    MAX-ACCESS  read-only
    STATUS      current
    DESCRIPTION
        "Scheduled Equalization Administration"
    ::=  { neAdmin 41 }

neEqlzInterval OBJECT-TYPE
    SYNTAX      FspR7EqlzInterval
    MAX-ACCESS  read-write
    STATUS      current
    DESCRIPTION
        "Scheduled Equalization Interval"
    ::=  { neAdmin 42 }

neEqlzIntervalCap OBJECT-TYPE
    SYNTAX      FspR7EqlzIntervalCaps
    MAX-ACCESS  read-only
    STATUS      current
    DESCRIPTION
        "Scheduled Equalization Interval"
    ::=  { neAdmin 43 }

neEqlzStartDate OBJECT-TYPE
    SYNTAX      FspR7Date
    MAX-ACCESS  read-write
    STATUS      current
    DESCRIPTION
        "Scheduled Equalization Start Date"
    ::=  { neAdmin 44 }

neEqlzStartTime OBJECT-TYPE
    SYNTAX      FspR7Time
    MAX-ACCESS  read-write
    STATUS      current
    DESCRIPTION
        "Scheduled Equalization Start Time"
    ::=  { neAdmin 45 }

neDefaultGateway OBJECT-TYPE
    SYNTAX      IpAddress
    MAX-ACCESS  read-write
    STATUS      current
    DESCRIPTION   "Default gateway for IP routing"
    ::=  { neAdmin 46 }

neSwType OBJECT-TYPE
    SYNTAX      FspR7EquipmentType
    MAX-ACCESS  read-only
    STATUS      current
    DESCRIPTION
        "Network Element SW Type"
    ::=  { neAdmin 47 }

neCpPcsPriority OBJECT-TYPE
    SYNTAX      Unsigned32 (0..255 | 4294967295)
    MAX-ACCESS  read-write
    STATUS      current
    DESCRIPTION
        "Path Computation Engine Priority"
    ::=  { neAdmin 48 }

neScuAutoRestoreEnabled OBJECT-TYPE
    SYNTAX      FspR7ScuDbBackup
    MAX-ACCESS  read-write
    STATUS      current
    DESCRIPTION
        "Enable/Disable Automatic Data Base Restore from SCU."
    ::=  { neAdmin 49 }

neNodeNameSyntax OBJECT-TYPE
    SYNTAX      FspR7NodeId
    MAX-ACCESS  read-write
    STATUS      current
    DESCRIPTION
        "Node Name Syntax"
    ::=  { neAdmin 50 }

neAutoProvLifCp OBJECT-TYPE
    SYNTAX      FspR7AutopLif
    MAX-ACCESS  read-write
    STATUS      current
    DESCRIPTION
        "Automatic Provisioning of LIF-CP"
    ::=  { neAdmin 51 }

authTrapSrcIp OBJECT-TYPE
    SYNTAX      IpAddress
    MAX-ACCESS  accessible-for-notify
    STATUS      current
    DESCRIPTION
        "Source IP address of sending NE."
    ::=  { neAdmin 60 }

authTrapLctIp OBJECT-TYPE
    SYNTAX      IpAddress
    MAX-ACCESS  accessible-for-notify
    STATUS      current
    DESCRIPTION
        "IP address of LCT used in NE access."
    ::=  { neAdmin 61 }

authTrapStatus OBJECT-TYPE
    SYNTAX      FspR7AccessStatus
    MAX-ACCESS  accessible-for-notify
    STATUS      current
    DESCRIPTION
        "Indication whether security operation was succesful/unsuccessful."
    ::=  { neAdmin 62 }

authTrapSessionId OBJECT-TYPE
    SYNTAX      SnmpAdminString
    MAX-ACCESS  accessible-for-notify
    STATUS      current
    DESCRIPTION
        "Session name used in NE access."
    ::=  { neAdmin 63 }

authTrapProtocol OBJECT-TYPE
    SYNTAX      FspR7AccessProtocol
    MAX-ACCESS  accessible-for-notify
    STATUS      current
    DESCRIPTION
        "Protocol type used in NE access."
    ::=  { neAdmin 64 }

authTrapPort OBJECT-TYPE
    SYNTAX      Unsigned32
    MAX-ACCESS  accessible-for-notify
    STATUS      current
    DESCRIPTION
        "Port number used in NE access."
    ::=  { neAdmin 65 }

authTrapUserName OBJECT-TYPE
    SYNTAX      SnmpAdminString
    MAX-ACCESS  accessible-for-notify
    STATUS      current
    DESCRIPTION
        "The name string for user authentication purposes"
    ::=  { neAdmin 66 }

authTrapRadUserName OBJECT-TYPE
    SYNTAX      SnmpAdminString
    MAX-ACCESS  accessible-for-notify
    STATUS      current
    DESCRIPTION
        "Name string for RADIUS authentication"
    ::=  { neAdmin 67 }

authTrapSuccessfulAuthCount OBJECT-TYPE
    SYNTAX      Unsigned32
    MAX-ACCESS  accessible-for-notify
    STATUS      current
    DESCRIPTION
        "Number of successful authentications."
    ::=  { neAdmin 68 }

authTrapUnsuccessfulAuthCount OBJECT-TYPE
    SYNTAX      Unsigned32
    MAX-ACCESS  accessible-for-notify
    STATUS      current
    DESCRIPTION
        "Number of unsuccessful authentications."
    ::=  { neAdmin 69 }

systemBusy OBJECT-TYPE
    SYNTAX      FspR7SystemBusy
    MAX-ACCESS  read-only
    STATUS      current
    DESCRIPTION
        "System Busy state."
    ::=  { neAdmin 70 }

snmpAgentStartupDate OBJECT-TYPE
    SYNTAX      DateAndTime
    MAX-ACCESS  read-only
    STATUS      current
    DESCRIPTION
        "Date"
    ::=  { neAdmin 71 }

lastErrorStatusCounter OBJECT-TYPE
    SYNTAX      Unsigned32
    MAX-ACCESS  read-only
    STATUS      current
    DESCRIPTION
        ""
    ::=  { neAdmin 72 }

lastErrorStatus OBJECT-TYPE
    SYNTAX      SnmpAdminString
    MAX-ACCESS  read-only
    STATUS      current
    DESCRIPTION
        ""
    ::=  { neAdmin 73 }

startPmSnapshot OBJECT-TYPE
    SYNTAX      FspR7StartPmSnapshot
    MAX-ACCESS  read-write
    STATUS      current
    DESCRIPTION
        "Apply reference values"
    ::=  { neAdmin 74 }

pmSnapshotStatus OBJECT-TYPE
    SYNTAX      FspR7PmSnapshotStatus
    MAX-ACCESS  read-only
    STATUS      current
    DESCRIPTION
        "Reference value Status"
    ::=  { neAdmin 75 }

maxBackplaneBandwidth OBJECT-TYPE
    SYNTAX      Unsigned32 
    UNITS       "kbps"
    MAX-ACCESS  read-only
    STATUS      current
    DESCRIPTION
        "Maximum bandwidth that can be used for LAN and LINK connections to the NCU."
    ::=  { neAdmin 76 }

usedBackplaneBandwidth OBJECT-TYPE
    SYNTAX      Unsigned32 
    UNITS       "kbps"
    MAX-ACCESS  read-only
    STATUS      current
    DESCRIPTION
        "Bandwidth used by configured LAN and LINK connections to the NCU."
    ::=  { neAdmin 77 }

neSecurityMode OBJECT-TYPE
    SYNTAX      FspR7SecurityMode
    MAX-ACCESS  read-write
    STATUS      current
    DESCRIPTION   "The switch for handling Security Mode of a Network Element. It supports basic(1) and enhanced(2) security mode.
         After switch is performed, a user is forced to change the password using fspUserManagementAuthPrivKey and
         fspUserManagementAuthPrivKeyOld objects in single set-request, otherwise SNMPv3 access to any MIB object will
         be denied due to authorization error.
         
         Switch from basic(1) to enhanced(2) security mode is allowed always. Switch in opposite direction is allowed
         only after manual user account removal - only one user account with admin(1) privilege level defined by
         FspR7SnmpPrivLevel TEXTUAL-CONVENTION must remain.
         
         In the basic(1) mode:
         * minimum password length is 8 characters,
         * maximum password length is 31 characters,
         * password cannot contain user name,
         * user name and password upper-case only,
         * password contains at least
         - one alphabetic character (a..z; A..Z);
         - one numeric character (0..9);
         - one special character ( ! , @ , # , $ , % , ^ , ( , ) , _ , + , | , ~ , { , } , [ , ] , - , . )
         
         In the enhanced(2) mode:
         * minimum password lenght is 15 characters,
         * maximum password lenght is 31 characters,
         * password cannot contain user name,
         * user name and password mixed-case supported,
         * password contains at least
         - two lowercase alphabetic character (a..z);
         - two uppercase alphabetic character(A..Z);
         - two numeric character (0..9);
         - two special character ( ! , @ , # , $ , % , ^ , ( , ) , _ , + , | , ~ , { , } , [ , ] , - , . )"
    ::=  { neAdmin 78 }

neSecurityModeCapability OBJECT-TYPE
    SYNTAX      FspR7SecurityModeCaps
    MAX-ACCESS  read-only
    STATUS      current
    DESCRIPTION
        "Security Mode"
    ::=  { neAdmin 79 }

neMinPasswordLength OBJECT-TYPE
    SYNTAX      Unsigned32 (8..31 | 4294967295)
    MAX-ACCESS  read-write
    STATUS      current
    DESCRIPTION   "Minimum password length settable in range 8..31 characters. It is
         accessible only using SNMPv3 protocol version with authentication
         and privacy"
    ::=  { neAdmin 80 }

neFiberDetect OBJECT-TYPE
    SYNTAX      FspR7FiberDetect
    MAX-ACCESS  read-write
    STATUS      current
    DESCRIPTION
        "Fiber Detect"
    ::=  { neAdmin 81 }

startOpticalPmSnapshotExport OBJECT-TYPE
    SYNTAX      FspR7StartOpticalPmSnapshotExport
    MAX-ACCESS  read-write
    STATUS      current
    DESCRIPTION
        "Update, Backup and Restore commands."
    ::=  { neAdmin 82 }

remoteAuthentication OBJECT-TYPE
    SYNTAX      FspR7RemoteAuth
    MAX-ACCESS  read-write
    STATUS      current
    DESCRIPTION
        "Type of Remote authentication"
    ::=  { neAdmin 83 }

bootloaderAccess OBJECT-TYPE
    SYNTAX      FspR7BootloaderAccess
    MAX-ACCESS  read-write
    STATUS      current
    DESCRIPTION
        "NCU boot loader access via serial line"
    ::=  { neAdmin 84 }

craftSessionTimeOut OBJECT-TYPE
    SYNTAX      Unsigned32 (30..3600 | 4294967295) 
    UNITS       "s"
    MAX-ACCESS  read-write
    STATUS      current
    DESCRIPTION
        "The time period of a user inactivity (in seconds) after which the craft application terminates"
    ::=  { neAdmin 85 }

serTelnetLogTimeOut OBJECT-TYPE
    SYNTAX      Unsigned32 (5..300 | 4294967295) 
    UNITS       "s"
    MAX-ACCESS  read-write
    STATUS      current
    DESCRIPTION
        "The time period of a user inactivity (in seconds) after which the started login process via telnet or serial line terminates"
    ::=  { neAdmin 86 }

shhLogTimeOut OBJECT-TYPE
    SYNTAX      Unsigned32 (5..300 | 4294967295) 
    UNITS       "s"
    MAX-ACCESS  read-write
    STATUS      current
    DESCRIPTION
        "The time period of a user inactivity (in seconds) after which the started login process via telnet or serial line terminates"
    ::=  { neAdmin 87 }

webGuiSessionTimeOut OBJECT-TYPE
    SYNTAX      Unsigned32 (30..3600 | 4294967295) 
    UNITS       "s"
    MAX-ACCESS  read-write
    STATUS      current
    DESCRIPTION
        "The time period of a user inactivity (in seconds) after which the Web GUI application logs the user out"
    ::=  { neAdmin 88 }

tl1LogTimeOut OBJECT-TYPE
    SYNTAX      Unsigned32 (5..300 | 4294967295) 
    UNITS       "s"
    MAX-ACCESS  read-write
    STATUS      current
    DESCRIPTION
        "The time period of a user inactivity after which the TL1 dispatcher terminates the TCP connection"
    ::=  { neAdmin 89 }

snmpSessionTimeOut OBJECT-TYPE
    SYNTAX      Unsigned32 (30..3600 | 4294967295) 
    UNITS       "s"
    MAX-ACCESS  read-write
    STATUS      current
    DESCRIPTION
        "The time period between SNMP requests for given SNMPv3 user or SNMPv1 community name after which the virtual SNMP session is deleted from SNMP Agent"
    ::=  { neAdmin 90 }

falsePasswordDelay OBJECT-TYPE
    SYNTAX      Unsigned32 (0..60 | 4294967295) 
    UNITS       "s"
    MAX-ACCESS  read-write
    STATUS      current
    DESCRIPTION   ""
    ::=  { neAdmin 91 }

passwordHistorySize OBJECT-TYPE
    SYNTAX      Unsigned32 (0..20 | 4294967295)
    MAX-ACCESS  read-write
    STATUS      current
    DESCRIPTION   ""
    ::=  { neAdmin 92 }

neTelnet OBJECT-TYPE
    SYNTAX      FspR7EnableDisable
    MAX-ACCESS  read-write
    STATUS      current
    DESCRIPTION
        "TELNET Server enable/disable configuration"
    ::=  { neAdmin 93 }

routingIpTable OBJECT-TYPE
    SYNTAX      SEQUENCE OF RoutingIpEntry
    MAX-ACCESS  not-accessible
    STATUS      current
    DESCRIPTION   "Static active routing table"
    ::=  { routingMIB 1 }

routingIpEntry OBJECT-TYPE
    SYNTAX      RoutingIpEntry
    MAX-ACCESS  not-accessible
    STATUS      current
    DESCRIPTION   ""
    INDEX       {
                  routingIpDestination,
                  routingIpMask,
                  routingIpGateway,
                  routingIpDevice
                }
    ::=  { routingIpTable 1 }

RoutingIpEntry ::=  SEQUENCE
  { routingIpDestination IpAddress,
    routingIpMask IpAddress,
    routingIpGateway IpAddress,
    routingIpDevice EntityIndex,
    routingIpRouteType FspR7Protocol,
    routingIpRoutingMetric Unsigned32,
    routingIpRowStatus RowStatus }

routingIpDestination OBJECT-TYPE
    SYNTAX      IpAddress
    MAX-ACCESS  not-accessible
    STATUS      current
    DESCRIPTION
        "Destination IP Address" 
    ::=  { routingIpEntry 1 }

routingIpMask OBJECT-TYPE
    SYNTAX      IpAddress
    MAX-ACCESS  not-accessible
    STATUS      current
    DESCRIPTION
        "Destination IP Mask." 
    ::=  { routingIpEntry 2 }

routingIpGateway OBJECT-TYPE
    SYNTAX      IpAddress
    MAX-ACCESS  not-accessible
    STATUS      current
    DESCRIPTION
        "Gateway IP Address" 
    ::=  { routingIpEntry 3 }

routingIpDevice OBJECT-TYPE
    SYNTAX      EntityIndex
    MAX-ACCESS  not-accessible
    STATUS      current
    DESCRIPTION
        "Address Identifier of IP Entity. E.g SC-1-A-C or LINK-1-A-1." 
    ::=  { routingIpEntry 4 }

routingIpRouteType OBJECT-TYPE
    SYNTAX      FspR7Protocol
    MAX-ACCESS  read-write
    STATUS      current
    DESCRIPTION
        "The Type of the IP Route." 
    ::=  { routingIpEntry 5 }

routingIpRoutingMetric OBJECT-TYPE
    SYNTAX      Unsigned32 (0..65535 | 4294967295)
    MAX-ACCESS  read-write
    STATUS      current
    DESCRIPTION
        "Routing Metric" 
    ::=  { routingIpEntry 6 }

routingIpRowStatus OBJECT-TYPE
    SYNTAX      RowStatus
    MAX-ACCESS  read-write
    STATUS      current
    DESCRIPTION   "This object is used to create, or delete a row in this table."
    ::=  { routingIpEntry 7 }

inactiveRoutingIpTable OBJECT-TYPE
    SYNTAX      SEQUENCE OF InactiveRoutingIpEntry
    MAX-ACCESS  not-accessible
    STATUS      current
    DESCRIPTION   "Static inactive routing table"
    ::=  { routingMIB 2 }

inactiveRoutingIpEntry OBJECT-TYPE
    SYNTAX      InactiveRoutingIpEntry
    MAX-ACCESS  not-accessible
    STATUS      current
    DESCRIPTION   ""
    INDEX       {
                  routingIpDestination,
                  routingIpMask,
                  routingIpGateway,
                  routingIpDevice
                }
    ::=  { inactiveRoutingIpTable 1 }

InactiveRoutingIpEntry ::=  SEQUENCE
  { inactiveRoutingIpDestination IpAddress,
    inactiveRoutingIpMask IpAddress,
    inactiveRoutingIpGateway IpAddress,
    inactiveRoutingIpDevice EntityIndex,
    inactiveRoutingIpRouteType FspR7Protocol,
    inactiveRoutingIpRoutingMetric Unsigned32,
    inactiveRoutingIpRowStatus RowStatus }

inactiveRoutingIpDestination OBJECT-TYPE
    SYNTAX      IpAddress
    MAX-ACCESS  not-accessible
    STATUS      current
    DESCRIPTION
        "Destination IP Address" 
    ::=  { inactiveRoutingIpEntry 1 }

inactiveRoutingIpMask OBJECT-TYPE
    SYNTAX      IpAddress
    MAX-ACCESS  not-accessible
    STATUS      current
    DESCRIPTION
        "Destination IP Mask." 
    ::=  { inactiveRoutingIpEntry 2 }

inactiveRoutingIpGateway OBJECT-TYPE
    SYNTAX      IpAddress
    MAX-ACCESS  not-accessible
    STATUS      current
    DESCRIPTION
        "Gateway IP Address" 
    ::=  { inactiveRoutingIpEntry 3 }

inactiveRoutingIpDevice OBJECT-TYPE
    SYNTAX      EntityIndex
    MAX-ACCESS  not-accessible
    STATUS      current
    DESCRIPTION
        "Address Identifier of IP Entity. E.g SC-1-A-C or LINK-1-A-1." 
    ::=  { inactiveRoutingIpEntry 4 }

inactiveRoutingIpRouteType OBJECT-TYPE
    SYNTAX      FspR7Protocol
    MAX-ACCESS  read-write
    STATUS      current
    DESCRIPTION
        "The Type of the IP Route." 
    ::=  { inactiveRoutingIpEntry 5 }

inactiveRoutingIpRoutingMetric OBJECT-TYPE
    SYNTAX      Unsigned32 (0..65535 | 4294967295)
    MAX-ACCESS  read-write
    STATUS      current
    DESCRIPTION
        "Routing Metric" 
    ::=  { inactiveRoutingIpEntry 6 }

inactiveRoutingIpRowStatus OBJECT-TYPE
    SYNTAX      RowStatus
    MAX-ACCESS  read-write
    STATUS      current
    DESCRIPTION   "This object is used to create, or delete a row in this table."
    ::=  { inactiveRoutingIpEntry 7 }

knownHostTable OBJECT-TYPE
    SYNTAX      SEQUENCE OF KnownHostEntry
    MAX-ACCESS  not-accessible
    STATUS      current
    DESCRIPTION   "Known host table"
    ::=  { routingMIB 3 }

knownHostEntry OBJECT-TYPE
    SYNTAX      KnownHostEntry
    MAX-ACCESS  not-accessible
    STATUS      current
    DESCRIPTION   ""
    INDEX       {
                  knownHostIP,
                  knownHostKeyEncryptAlgorithm
                }
    ::=  { knownHostTable 1 }

KnownHostEntry ::=  SEQUENCE
  { knownHostIP IpAddress,
    knownHostKeyEncryptAlgorithm FspR7SshHostKeyEncryptAlgorithm,
    knownHostRowStatus RowStatus,
    knownHostFingerprint FspR7SnmpHexString }

knownHostIP OBJECT-TYPE
    SYNTAX      IpAddress
    MAX-ACCESS  accessible-for-notify
    STATUS      current
    DESCRIPTION
        "IP Address of known host" 
    ::=  { knownHostEntry 1 }

knownHostKeyEncryptAlgorithm OBJECT-TYPE
    SYNTAX      FspR7SshHostKeyEncryptAlgorithm
    MAX-ACCESS  read-only
    STATUS      current
    DESCRIPTION
        "ssh host key encryption alogrithm" 
    ::=  { knownHostEntry 2 }

knownHostRowStatus OBJECT-TYPE
    SYNTAX      RowStatus
    MAX-ACCESS  read-write
    STATUS      current
    DESCRIPTION   "This object is used to create, or delete a row in this table."
    ::=  { knownHostEntry 3 }

knownHostFingerprint OBJECT-TYPE
    SYNTAX      FspR7SnmpHexString
    MAX-ACCESS  read-write
    STATUS      current
    DESCRIPTION
        "Fingerprint of ssh host key" 
    ::=  { knownHostEntry 4 }

fspUserSpinLock OBJECT-TYPE
    SYNTAX      Unsigned32
    MAX-ACCESS  read-write
    STATUS      current
    DESCRIPTION   ""
    ::=  { fspUser 1 }

passwordError OBJECT-TYPE
    SYNTAX      SnmpAdminString
    MAX-ACCESS  read-only
    STATUS      current
    DESCRIPTION   "Last error related to set-request perform on user password."
    ::=  { fspUser 2 }

passwordErrorReqId OBJECT-TYPE
    SYNTAX      Unsigned32
    MAX-ACCESS  read-only
    STATUS      current
    DESCRIPTION   "Set-Request id for which passwordError contains value."
    ::=  { fspUser 3 }

fspUserManagementTable OBJECT-TYPE
    SYNTAX      SEQUENCE OF FspUserManagementEntry
    MAX-ACCESS  not-accessible
    STATUS      current
    DESCRIPTION   ""
    ::=  { fspUser 10 }

fspUserManagementEntry OBJECT-TYPE
    SYNTAX      FspUserManagementEntry
    MAX-ACCESS  not-accessible
    STATUS      current
    DESCRIPTION   ""
    INDEX       {
                  fspUserManagementEngineID,
                  fspUserManagementName
                }
    ::=  { fspUserManagementTable 1 }

FspUserManagementEntry ::=  SEQUENCE
  { fspUserManagementEngineID SnmpAdminString,
    fspUserManagementName SnmpAdminString,
    fspUserManagementRowStatus RowStatus,
    fspUserManagementSecurityName SnmpAdminString,
    fspUserManagementPrivilegeLevel FspR7SnmpPrivLevel,
    fspUserManagementSecurityLevel FspR7SnmpSecuLevel,
    fspUserManagementAuthPrivKey SnmpAdminString,
    fspUserManagementInternalState FspR7TL1InternalState,
    fspUserManagementTl1TimeoutAvailable FspR7TL1TimoutAvailable,
    fspUserManagementTl1TimeoutValue Integer32,
    fspUserManagementSnmpTimeoutValue Unsigned32,
    fspUserManagementUdpSessionStatus FspR7SessionStatus,
    fspUserManagementTcpSessionStatus FspR7SessionStatus,
    fspUserManagementAuthPrivKeyOld SnmpAdminString,
    fspUserManagementAccountFlag FspR7AccountFlag,
    fspUserManagementPasswordMinAge Integer32,
    fspUserManagementPasswordMaxAge Integer32,
    fspUserManagementPasswordExpirationPeriod Integer32,
    fspUserManagementAccountState FspR7AccState,
    fspUserManagementPasswordExpirationDate SnmpAdminString,
    fspUserManagementPasswordLastChangeDate SnmpAdminString,
    fspUserManagementFailedLoginAttempts Integer32,
    fspUserManagementLastLoginFailInfo SnmpAdminString,
    fspUserManagementLastLoginSuccessInfo SnmpAdminString,
    fspUserManagementInactivityPeriod Integer32,
    fspUserManagementAccessStartTime FspR7TimeShort,
    fspUserManagementAccessEndTime FspR7TimeShort,
    fspUserManagementAccessDays SnmpAdminString,
    fspUserManagementExpirationDate FspR7Date,
    fspUserManagementActiveIn SnmpAdminString,
    fspUserManagementTerminateSessions FspR7TerminateSessions }

fspUserManagementEngineID OBJECT-TYPE
    SYNTAX      SnmpAdminString
    MAX-ACCESS  not-accessible
    STATUS      current
    DESCRIPTION
        "" 
    ::=  { fspUserManagementEntry 1 }

fspUserManagementName OBJECT-TYPE
    SYNTAX      SnmpAdminString
    MAX-ACCESS  not-accessible
    STATUS      current
    DESCRIPTION
        "The name string for user authentication purposes" 
    ::=  { fspUserManagementEntry 2 }

fspUserManagementRowStatus OBJECT-TYPE
    SYNTAX      RowStatus
    MAX-ACCESS  read-write
    STATUS      current
    DESCRIPTION
        "RowStatus" 
    ::=  { fspUserManagementEntry 3 }

fspUserManagementSecurityName OBJECT-TYPE
    SYNTAX      SnmpAdminString
    MAX-ACCESS  read-write
    STATUS      current
    DESCRIPTION
        "The name string for user authentication purposes" 
    ::=  { fspUserManagementEntry 4 }

fspUserManagementPrivilegeLevel OBJECT-TYPE
    SYNTAX      FspR7SnmpPrivLevel
    MAX-ACCESS  read-write
    STATUS      current
    DESCRIPTION
        "" 
    ::=  { fspUserManagementEntry 5 }

fspUserManagementSecurityLevel OBJECT-TYPE
    SYNTAX      FspR7SnmpSecuLevel
    MAX-ACCESS  read-write
    STATUS      current
    DESCRIPTION
        "" 
    ::=  { fspUserManagementEntry 6 }

fspUserManagementAuthPrivKey OBJECT-TYPE
    SYNTAX      SnmpAdminString
    MAX-ACCESS  read-write
    STATUS      current
    DESCRIPTION
        "A human readable string representing the current or new password for user
         account.
        " 
    ::=  { fspUserManagementEntry 7 }

fspUserManagementInternalState OBJECT-TYPE
    SYNTAX      FspR7TL1InternalState
    MAX-ACCESS  read-write
    STATUS      deprecated
    DESCRIPTION
        "" 
    ::=  { fspUserManagementEntry 8 }

fspUserManagementTl1TimeoutAvailable OBJECT-TYPE
    SYNTAX      FspR7TL1TimoutAvailable
    MAX-ACCESS  read-write
    STATUS      current
    DESCRIPTION
        "" 
    ::=  { fspUserManagementEntry 9 }

fspUserManagementTl1TimeoutValue OBJECT-TYPE
    SYNTAX      Integer32 (1..60 | -2147483648)
    MAX-ACCESS  read-write
    STATUS      current
    DESCRIPTION
        "" 
    ::=  { fspUserManagementEntry 10 }

fspUserManagementSnmpTimeoutValue OBJECT-TYPE
    SYNTAX      Unsigned32 (30..3600 | 4294967295) 
    UNITS       "s"
    MAX-ACCESS  read-only
    STATUS      current
    DESCRIPTION
        "The time period between SNMP requests for given SNMPv3 user or SNMPv1 community name after which the virtual SNMP session is deleted from SNMP Agent" 
    ::=  { fspUserManagementEntry 11 }

fspUserManagementUdpSessionStatus OBJECT-TYPE
    SYNTAX      FspR7SessionStatus
    MAX-ACCESS  read-only
    STATUS      current
    DESCRIPTION
        "UDP-based User Session Status" 
    ::=  { fspUserManagementEntry 12 }

fspUserManagementTcpSessionStatus OBJECT-TYPE
    SYNTAX      FspR7SessionStatus
    MAX-ACCESS  read-only
    STATUS      current
    DESCRIPTION
        "TCP-based User Session Status" 
    ::=  { fspUserManagementEntry 13 }

fspUserManagementAuthPrivKeyOld OBJECT-TYPE
    SYNTAX      SnmpAdminString
    MAX-ACCESS  read-write
    STATUS      current
    DESCRIPTION
        "A human readable string representing the old password for user
         account. This object should be used only for password change
         procedure.
        " 
    ::=  { fspUserManagementEntry 14 }

fspUserManagementAccountFlag OBJECT-TYPE
    SYNTAX      FspR7AccountFlag
    MAX-ACCESS  read-write
    STATUS      current
    DESCRIPTION   "User account flag used currently to set the forced authentication
         change request. See the FspR7AccountFlag Textual-Convention."
    ::=  { fspUserManagementEntry 15 }

fspUserManagementPasswordMinAge OBJECT-TYPE
    SYNTAX      Integer32
    MAX-ACCESS  read-write
    STATUS      current
    DESCRIPTION
        "" 
    ::=  { fspUserManagementEntry 16 }

fspUserManagementPasswordMaxAge OBJECT-TYPE
    SYNTAX      Integer32
    MAX-ACCESS  read-write
    STATUS      current
    DESCRIPTION
        "" 
    ::=  { fspUserManagementEntry 17 }

fspUserManagementPasswordExpirationPeriod OBJECT-TYPE
    SYNTAX      Integer32
    MAX-ACCESS  read-write
    STATUS      current
    DESCRIPTION
        "" 
    ::=  { fspUserManagementEntry 18 }

fspUserManagementAccountState OBJECT-TYPE
    SYNTAX      FspR7AccState
    MAX-ACCESS  read-write
    STATUS      current
    DESCRIPTION
        "" 
    ::=  { fspUserManagementEntry 19 }

fspUserManagementPasswordExpirationDate OBJECT-TYPE
    SYNTAX      SnmpAdminString
    MAX-ACCESS  read-only
    STATUS      current
    DESCRIPTION
        "PASSWORD_EXPIRATION_DATE" 
    ::=  { fspUserManagementEntry 20 }

fspUserManagementPasswordLastChangeDate OBJECT-TYPE
    SYNTAX      SnmpAdminString
    MAX-ACCESS  read-only
    STATUS      current
    DESCRIPTION
        "PASSWORD_LASTCHANGE_DATE" 
    ::=  { fspUserManagementEntry 21 }

fspUserManagementFailedLoginAttempts OBJECT-TYPE
    SYNTAX      Integer32 (0..10 | -2147483648)
    MAX-ACCESS  read-write
    STATUS      current
    DESCRIPTION
        "" 
    ::=  { fspUserManagementEntry 22 }

fspUserManagementLastLoginFailInfo OBJECT-TYPE
    SYNTAX      SnmpAdminString
    MAX-ACCESS  read-only
    STATUS      current
    DESCRIPTION
        "FAIL_INFO" 
    ::=  { fspUserManagementEntry 23 }

fspUserManagementLastLoginSuccessInfo OBJECT-TYPE
    SYNTAX      SnmpAdminString
    MAX-ACCESS  read-only
    STATUS      current
    DESCRIPTION
        "SUCCESS_INFO" 
    ::=  { fspUserManagementEntry 24 }

fspUserManagementInactivityPeriod OBJECT-TYPE
    SYNTAX      Integer32 (0..999 | -2147483648) 
    UNITS       "day"
    MAX-ACCESS  read-write
    STATUS      current
    DESCRIPTION
        "Account parameter; Account is locked when user hasn't logged in for INACTIVITY_PERIOD of time." 
    ::=  { fspUserManagementEntry 25 }

fspUserManagementAccessStartTime OBJECT-TYPE
    SYNTAX      FspR7TimeShort
    MAX-ACCESS  read-write
    STATUS      current
    DESCRIPTION
        "Time (in HH-MM format) when user can log in." 
    ::=  { fspUserManagementEntry 26 }

fspUserManagementAccessEndTime OBJECT-TYPE
    SYNTAX      FspR7TimeShort
    MAX-ACCESS  read-write
    STATUS      current
    DESCRIPTION
        "Time (in HH-MM format) when user must logout or is forced off the node." 
    ::=  { fspUserManagementEntry 27 }

fspUserManagementAccessDays OBJECT-TYPE
    SYNTAX      SnmpAdminString
    MAX-ACCESS  read-write
    STATUS      current
    DESCRIPTION
        "Days of the week a user is authorized to log in to the node." 
    ::=  { fspUserManagementEntry 28 }

fspUserManagementExpirationDate OBJECT-TYPE
    SYNTAX      FspR7Date
    MAX-ACCESS  read-write
    STATUS      current
    DESCRIPTION
        "Date" 
    ::=  { fspUserManagementEntry 29 }

fspUserManagementActiveIn OBJECT-TYPE
    SYNTAX      SnmpAdminString
    MAX-ACCESS  read-only
    STATUS      deprecated
    DESCRIPTION
        "List of protocols in which user is active." 
    ::=  { fspUserManagementEntry 30 }

fspUserManagementTerminateSessions OBJECT-TYPE
    SYNTAX      FspR7TerminateSessions
    MAX-ACCESS  read-write
    STATUS      deprecated
    DESCRIPTION
        "Shows forced logout availability for selected user and allows to take such an action." 
    ::=  { fspUserManagementEntry 31 }

fspUserManagementCapTable OBJECT-TYPE
    SYNTAX      SEQUENCE OF FspUserManagementCapEntry
    MAX-ACCESS  not-accessible
    STATUS      current
    DESCRIPTION   ""
    ::=  { fspUser 11 }

fspUserManagementCapEntry OBJECT-TYPE
    SYNTAX      FspUserManagementCapEntry
    MAX-ACCESS  not-accessible
    STATUS      current
    DESCRIPTION   ""
    INDEX       {
                  fspUserManagementEngineID,
                  fspUserManagementName
                }
    ::=  { fspUserManagementCapTable 1 }

FspUserManagementCapEntry ::=  SEQUENCE
  { fspUserManagementCapRowStatus FspR7RowStatusCaps,
    fspUserManagementCapPrivilegeLevel FspR7SnmpPrivLevelCaps,
    fspUserManagementCapSecurityLevel FspR7SnmpSecuLevelCaps,
    fspUserManagementCapInternalState FspR7TL1InternalStateCaps,
    fspUserManagementCapTimeoutAvailable FspR7TL1TimoutAvailableCaps,
    fspUserManagementCapPasswordMinAge FspR7Integer32Caps,
    fspUserManagementCapPasswordMaxAge FspR7Integer32Caps,
    fspUserManagementCapPasswordExpirationPeriod FspR7Integer32Caps,
    fspUserManagementCapFailedLoginAttempts FspR7Integer32Caps,
    fspUserManagementCapAccountState FspR7AccStateCaps,
    fspUserManagementCapInactivityPeriod FspR7Integer32Caps }

fspUserManagementCapRowStatus OBJECT-TYPE
    SYNTAX      FspR7RowStatusCaps
    MAX-ACCESS  read-only
    STATUS      current
    DESCRIPTION
        "RowStatus" 
    ::=  { fspUserManagementCapEntry 1 }

fspUserManagementCapPrivilegeLevel OBJECT-TYPE
    SYNTAX      FspR7SnmpPrivLevelCaps
    MAX-ACCESS  read-only
    STATUS      current
    DESCRIPTION
        "" 
    ::=  { fspUserManagementCapEntry 2 }

fspUserManagementCapSecurityLevel OBJECT-TYPE
    SYNTAX      FspR7SnmpSecuLevelCaps
    MAX-ACCESS  read-only
    STATUS      current
    DESCRIPTION
        "" 
    ::=  { fspUserManagementCapEntry 3 }

fspUserManagementCapInternalState OBJECT-TYPE
    SYNTAX      FspR7TL1InternalStateCaps
    MAX-ACCESS  read-only
    STATUS      deprecated
    DESCRIPTION
        "" 
    ::=  { fspUserManagementCapEntry 4 }

fspUserManagementCapTimeoutAvailable OBJECT-TYPE
    SYNTAX      FspR7TL1TimoutAvailableCaps
    MAX-ACCESS  read-only
    STATUS      current
    DESCRIPTION
        "" 
    ::=  { fspUserManagementCapEntry 5 }

fspUserManagementCapPasswordMinAge OBJECT-TYPE
    SYNTAX      FspR7Integer32Caps
    MAX-ACCESS  read-only
    STATUS      current
    DESCRIPTION
        "" 
    ::=  { fspUserManagementCapEntry 6 }

fspUserManagementCapPasswordMaxAge OBJECT-TYPE
    SYNTAX      FspR7Integer32Caps
    MAX-ACCESS  read-only
    STATUS      current
    DESCRIPTION
        "" 
    ::=  { fspUserManagementCapEntry 7 }

fspUserManagementCapPasswordExpirationPeriod OBJECT-TYPE
    SYNTAX      FspR7Integer32Caps
    MAX-ACCESS  read-only
    STATUS      current
    DESCRIPTION
        "" 
    ::=  { fspUserManagementCapEntry 8 }

fspUserManagementCapFailedLoginAttempts OBJECT-TYPE
    SYNTAX      FspR7Integer32Caps
    MAX-ACCESS  read-only
    STATUS      current
    DESCRIPTION
        "" 
    ::=  { fspUserManagementCapEntry 9 }

fspUserManagementCapAccountState OBJECT-TYPE
    SYNTAX      FspR7AccStateCaps
    MAX-ACCESS  read-only
    STATUS      current
    DESCRIPTION
        "" 
    ::=  { fspUserManagementCapEntry 10 }

fspUserManagementCapInactivityPeriod OBJECT-TYPE
    SYNTAX      FspR7Integer32Caps
    UNITS       "day"
    MAX-ACCESS  read-only
    STATUS      current
    DESCRIPTION
        "Account parameter; Account is locked when user hasn't logged in for INACTIVITY_PERIOD of time." 
    ::=  { fspUserManagementCapEntry 11 }

fspUserManagementDefaultsTable OBJECT-TYPE
    SYNTAX      SEQUENCE OF FspUserManagementDefaultsEntry
    MAX-ACCESS  not-accessible
    STATUS      current
    DESCRIPTION   ""
    ::=  { fspUser 12 }

fspUserManagementDefaultsEntry OBJECT-TYPE
    SYNTAX      FspUserManagementDefaultsEntry
    MAX-ACCESS  not-accessible
    STATUS      current
    DESCRIPTION   ""
    INDEX       {
                  fspUserManagementEngineID,
                  fspUserManagementName
                }
    ::=  { fspUserManagementDefaultsTable 1 }

FspUserManagementDefaultsEntry ::=  SEQUENCE
  { fspUserManagementDefaultsPrivilegeLevel FspR7SnmpPrivLevel,
    fspUserManagementDefaultsSecurityLevel FspR7SnmpSecuLevel,
    fspUserManagementDefaultsInternalState FspR7TL1InternalState,
    fspUserManagementDefaultsTimeoutAvailable FspR7TL1TimoutAvailable,
    fspUserManagementDefaultsTimeoutValue Integer32,
    fspUserManagementDefaultsSnmpTimeoutValue Unsigned32,
    fspUserManagementDefaultsPasswordMinAge Integer32,
    fspUserManagementDefaultsPasswordMaxAge Integer32,
    fspUserManagementDefaultsPasswordExpirationPeriod Integer32,
    fspUserManagementDefaultsFailedLoginAttempts Integer32,
    fspUserManagementDefaultsAccountState FspR7AccState,
    fspUserManagementDefaultsInactivityPeriod Integer32 }

fspUserManagementDefaultsPrivilegeLevel OBJECT-TYPE
    SYNTAX      FspR7SnmpPrivLevel
    MAX-ACCESS  read-only
    STATUS      current
    DESCRIPTION
        "" 
    ::=  { fspUserManagementDefaultsEntry 1 }

fspUserManagementDefaultsSecurityLevel OBJECT-TYPE
    SYNTAX      FspR7SnmpSecuLevel
    MAX-ACCESS  read-only
    STATUS      current
    DESCRIPTION
        "" 
    ::=  { fspUserManagementDefaultsEntry 2 }

fspUserManagementDefaultsInternalState OBJECT-TYPE
    SYNTAX      FspR7TL1InternalState
    MAX-ACCESS  read-only
    STATUS      deprecated
    DESCRIPTION
        "" 
    ::=  { fspUserManagementDefaultsEntry 3 }

fspUserManagementDefaultsTimeoutAvailable OBJECT-TYPE
    SYNTAX      FspR7TL1TimoutAvailable
    MAX-ACCESS  read-only
    STATUS      current
    DESCRIPTION
        "" 
    ::=  { fspUserManagementDefaultsEntry 4 }

fspUserManagementDefaultsTimeoutValue OBJECT-TYPE
    SYNTAX      Integer32 (1..60 | -2147483648)
    MAX-ACCESS  read-only
    STATUS      current
    DESCRIPTION
        "" 
    ::=  { fspUserManagementDefaultsEntry 5 }

fspUserManagementDefaultsSnmpTimeoutValue OBJECT-TYPE
    SYNTAX      Unsigned32 (30..3600 | 4294967295) 
    UNITS       "s"
    MAX-ACCESS  read-only
    STATUS      current
    DESCRIPTION
        "The time period between SNMP requests for given SNMPv3 user or SNMPv1 community name after which the virtual SNMP session is deleted from SNMP Agent" 
    ::=  { fspUserManagementDefaultsEntry 6 }

fspUserManagementDefaultsPasswordMinAge OBJECT-TYPE
    SYNTAX      Integer32
    MAX-ACCESS  read-only
    STATUS      current
    DESCRIPTION
        "" 
    ::=  { fspUserManagementDefaultsEntry 7 }

fspUserManagementDefaultsPasswordMaxAge OBJECT-TYPE
    SYNTAX      Integer32
    MAX-ACCESS  read-only
    STATUS      current
    DESCRIPTION
        "" 
    ::=  { fspUserManagementDefaultsEntry 8 }

fspUserManagementDefaultsPasswordExpirationPeriod OBJECT-TYPE
    SYNTAX      Integer32
    MAX-ACCESS  read-only
    STATUS      current
    DESCRIPTION
        "" 
    ::=  { fspUserManagementDefaultsEntry 9 }

fspUserManagementDefaultsFailedLoginAttempts OBJECT-TYPE
    SYNTAX      Integer32 (0..10 | -2147483648)
    MAX-ACCESS  read-only
    STATUS      current
    DESCRIPTION
        "" 
    ::=  { fspUserManagementDefaultsEntry 10 }

fspUserManagementDefaultsAccountState OBJECT-TYPE
    SYNTAX      FspR7AccState
    MAX-ACCESS  read-only
    STATUS      current
    DESCRIPTION
        "" 
    ::=  { fspUserManagementDefaultsEntry 11 }

fspUserManagementDefaultsInactivityPeriod OBJECT-TYPE
    SYNTAX      Integer32 (0..999 | -2147483648) 
    UNITS       "day"
    MAX-ACCESS  read-only
    STATUS      current
    DESCRIPTION
        "Account parameter; Account is locked when user hasn't logged in for INACTIVITY_PERIOD of time." 
    ::=  { fspUserManagementDefaultsEntry 12 }

deployProvSyslogTable OBJECT-TYPE
    SYNTAX      SEQUENCE OF DeployProvSyslogEntry
    MAX-ACCESS  not-accessible
    STATUS      current
    DESCRIPTION   ""
    ::=  { srvSyslog 1 }

deployProvSyslogEntry OBJECT-TYPE
    SYNTAX      DeployProvSyslogEntry
    MAX-ACCESS  not-accessible
    STATUS      current
    DESCRIPTION   ""
    INDEX       {
                  syslogDataIp
                }
    ::=  { deployProvSyslogTable 1 }

DeployProvSyslogEntry ::=  SEQUENCE
  { deployProvSyslogRowStatus RowStatus,
    deployProvSyslogStatus FspR7EnableDisable,
    deployProvSyslogReportsStatus FspR7EnableDisable,
    deployProvSyslogSourceIp SourceIpAddress }

deployProvSyslogRowStatus OBJECT-TYPE
    SYNTAX      RowStatus
    MAX-ACCESS  read-write
    STATUS      current
    DESCRIPTION   "RowStatus"
    ::=  { deployProvSyslogEntry 1 }

deployProvSyslogStatus OBJECT-TYPE
    SYNTAX      FspR7EnableDisable
    MAX-ACCESS  read-write
    STATUS      current
    DESCRIPTION
        "Syslog" 
    ::=  { deployProvSyslogEntry 2 }

deployProvSyslogReportsStatus OBJECT-TYPE
    SYNTAX      FspR7EnableDisable
    MAX-ACCESS  read-write
    STATUS      current
    DESCRIPTION
        "Enable or disable sending DB change events" 
    ::=  { deployProvSyslogEntry 3 }

deployProvSyslogSourceIp OBJECT-TYPE
    SYNTAX      SourceIpAddress
    MAX-ACCESS  read-write
    STATUS      deprecated
    DESCRIPTION
        "IP address which will be used as source address by client applications (i.e. FTP) to facilitate proper backward routing (i.e. server to client direction) in the DCN" 
    ::=  { deployProvSyslogEntry 4 }

syslogConfigTable OBJECT-TYPE
    SYNTAX      SEQUENCE OF SyslogConfigEntry
    MAX-ACCESS  not-accessible
    STATUS      current
    DESCRIPTION   ""
    ::=  { srvSyslog 4 }

syslogConfigEntry OBJECT-TYPE
    SYNTAX      SyslogConfigEntry
    MAX-ACCESS  not-accessible
    STATUS      current
    DESCRIPTION   ""
    INDEX       {
                  syslogDataIp
                }
    ::=  { syslogConfigTable 1 }

SyslogConfigEntry ::=  SEQUENCE
  { syslogConfigStatus FspR7EnableDisable,
    syslogConfigReportsStatus FspR7EnableDisable,
    syslogConfigSourceIp SourceIpAddress }

syslogConfigStatus OBJECT-TYPE
    SYNTAX      FspR7EnableDisable
    MAX-ACCESS  read-write
    STATUS      current
    DESCRIPTION
        "Syslog" 
    ::=  { syslogConfigEntry 1 }

syslogConfigReportsStatus OBJECT-TYPE
    SYNTAX      FspR7EnableDisable
    MAX-ACCESS  read-write
    STATUS      current
    DESCRIPTION
        "Enable or disable sending DB change events" 
    ::=  { syslogConfigEntry 2 }

syslogConfigSourceIp OBJECT-TYPE
    SYNTAX      SourceIpAddress
    MAX-ACCESS  read-write
    STATUS      deprecated
    DESCRIPTION
        "IP address which will be used as source address by client applications (i.e. FTP) to facilitate proper backward routing (i.e. server to client direction) in the DCN" 
    ::=  { syslogConfigEntry 3 }

syslogDataTable OBJECT-TYPE
    SYNTAX      SEQUENCE OF SyslogDataEntry
    MAX-ACCESS  not-accessible
    STATUS      current
    DESCRIPTION   ""
    ::=  { srvSyslog 6 }

syslogDataEntry OBJECT-TYPE
    SYNTAX      SyslogDataEntry
    MAX-ACCESS  not-accessible
    STATUS      current
    DESCRIPTION   ""
    INDEX       {
                  syslogDataIp
                }
    ::=  { syslogDataTable 1 }

SyslogDataEntry ::=  SEQUENCE
  { syslogDataIp IpAddress,
    syslogDataIpAddr IpAddress }

syslogDataIp OBJECT-TYPE
    SYNTAX      IpAddress
    MAX-ACCESS  accessible-for-notify
    STATUS      current
    DESCRIPTION
        "IP index" 
    ::=  { syslogDataEntry 1 }

syslogDataIpAddr OBJECT-TYPE
    SYNTAX      IpAddress
    MAX-ACCESS  read-only
    STATUS      current
    DESCRIPTION   "The IP address of the IP host where Syslog notifications should be sent. Derived from AID."
    ::=  { syslogDataEntry 2 }

nodeChannelTraceTable OBJECT-TYPE
    SYNTAX      SEQUENCE OF NodeChannelTraceEntry
    MAX-ACCESS  not-accessible
    STATUS      current
    DESCRIPTION   "The nodeChannelTrace table describes particular connection type between
         two ports. Connection may be done within a module or between two modules'
         ports.
        "
    ::=  { channelTrace 2 }

nodeChannelTraceEntry OBJECT-TYPE
    SYNTAX      NodeChannelTraceEntry
    MAX-ACCESS  not-accessible
    STATUS      current
    DESCRIPTION   ""
    INDEX       {
                  nodeChannelTraceStartAid,
                  nodeChannelTraceChannelNumber,
                  nodeChannelTraceRouteId,
                  nodeChannelTraceRouteElementId
                }
    ::=  { nodeChannelTraceTable 1 }

NodeChannelTraceEntry ::=  SEQUENCE
  { nodeChannelTraceStartAid EntityIndex,
    nodeChannelTraceChannelNumber FspR7ChannelNumber,
    nodeChannelTraceRouteId FspR7NCTraceId,
    nodeChannelTraceRouteElementId EntityIndex,
    nodeChannelTraceFromAid EntityIndex,
    nodeChannelTraceToAid EntityIndex,
    nodeChannelTraceRouteType FspR7NCTRouteType,
    nodeChannelTraceChannelRx FspR7ChannelNumber,
    nodeChannelTraceChannelTx FspR7ChannelNumber,
    nodeChannelTraceFromAidString SnmpAdminString,
    nodeChannelTraceToAidString SnmpAdminString }

nodeChannelTraceStartAid OBJECT-TYPE
    SYNTAX      EntityIndex
    MAX-ACCESS  accessible-for-notify
    STATUS      current
    DESCRIPTION
        "TL1 Access Identifier" 
    ::=  { nodeChannelTraceEntry 1 }

nodeChannelTraceChannelNumber OBJECT-TYPE
    SYNTAX      FspR7ChannelNumber
    MAX-ACCESS  accessible-for-notify
    STATUS      current
    DESCRIPTION
        "CWDM channels; DWDM frequencies (50 GHz grid according ITU-T" 
    ::=  { nodeChannelTraceEntry 2 }

nodeChannelTraceRouteId OBJECT-TYPE
    SYNTAX      FspR7NCTraceId
    MAX-ACCESS  accessible-for-notify
    STATUS      current
    DESCRIPTION
        "Node Channel Trace ID - It associates each direction of a channel trace through a node." 
    ::=  { nodeChannelTraceEntry 3 }

nodeChannelTraceRouteElementId OBJECT-TYPE
    SYNTAX      EntityIndex
    MAX-ACCESS  accessible-for-notify
    STATUS      current
    DESCRIPTION
        "" 
    ::=  { nodeChannelTraceEntry 4 }

nodeChannelTraceFromAid OBJECT-TYPE
    SYNTAX      EntityIndex
    MAX-ACCESS  read-only
    STATUS      current
    DESCRIPTION
        "FROM-end of equipment connection (jumper). FROM direction is significant only for 1WAY connections." 
    ::=  { nodeChannelTraceEntry 5 }

nodeChannelTraceToAid OBJECT-TYPE
    SYNTAX      EntityIndex
    MAX-ACCESS  read-only
    STATUS      current
    DESCRIPTION
        "TO-end of equipment connection (jumper). TO direction is signaificant only for 1WAY" 
    ::=  { nodeChannelTraceEntry 6 }

nodeChannelTraceRouteType OBJECT-TYPE
    SYNTAX      FspR7NCTRouteType
    MAX-ACCESS  read-only
    STATUS      current
    DESCRIPTION   "FspR7NCTRouteType Textual-Convention indicates the connection type between two ports.
         If a connection between the two ports is within a module (i.e. Client to Network port),
         the Route-Type is either provisioned(6) of fixed ( equipment(5) ). If the connection
         is between two modules ports, then the Route-Type is fiber(2), cable(3) or backPlane(4).
        "
    ::=  { nodeChannelTraceEntry 7 }

nodeChannelTraceChannelRx OBJECT-TYPE
    SYNTAX      FspR7ChannelNumber
    MAX-ACCESS  read-only
    STATUS      current
    DESCRIPTION
        "Channel Number for the Receive Interface" 
    ::=  { nodeChannelTraceEntry 8 }

nodeChannelTraceChannelTx OBJECT-TYPE
    SYNTAX      FspR7ChannelNumber
    MAX-ACCESS  read-only
    STATUS      current
    DESCRIPTION
        "Channel Number for the Transmit Interface" 
    ::=  { nodeChannelTraceEntry 9 }

nodeChannelTraceFromAidString OBJECT-TYPE
    SYNTAX      SnmpAdminString
    MAX-ACCESS  read-only
    STATUS      current
    DESCRIPTION
        "AID FROM represented as string" 
    ::=  { nodeChannelTraceEntry 10 }

nodeChannelTraceToAidString OBJECT-TYPE
    SYNTAX      SnmpAdminString
    MAX-ACCESS  read-only
    STATUS      current
    DESCRIPTION
        "AID TO represented as string" 
    ::=  { nodeChannelTraceEntry 11 }

dcnOspfAreaTable OBJECT-TYPE
    SYNTAX      SEQUENCE OF DcnOspfAreaEntry
    MAX-ACCESS  not-accessible
    STATUS      current
    DESCRIPTION   "This table relates to DCN functionality of defining OSPF Area entities
         which may be marked as Stub or Non-Stub."
    ::=  { dcnOspf 1 }

dcnOspfAreaEntry OBJECT-TYPE
    SYNTAX      DcnOspfAreaEntry
    MAX-ACCESS  not-accessible
    STATUS      current
    DESCRIPTION   "Table row represents an OSPF Area entity."
    INDEX       {
                  dcnOspfAreaId,
                  dcnOspfAreaType
                }
    ::=  { dcnOspfAreaTable 1 }

DcnOspfAreaEntry ::=  SEQUENCE
  { dcnOspfAreaId IpAddress,
    dcnOspfAreaType FspR7OspfAreaType,
    dcnOspfAreaRowStatus RowStatus,
    dcnOspfAreaIfListSize Unsigned32,
    dcnOspfAreaStubDefaultMetric Unsigned32 }

dcnOspfAreaId OBJECT-TYPE
    SYNTAX      IpAddress
    MAX-ACCESS  accessible-for-notify
    STATUS      current
    DESCRIPTION
        "OSPF Area ID for IP Interface" 
    ::=  { dcnOspfAreaEntry 1 }

dcnOspfAreaType OBJECT-TYPE
    SYNTAX      FspR7OspfAreaType
    MAX-ACCESS  accessible-for-notify
    STATUS      current
    DESCRIPTION
        "Area Type" 
    ::=  { dcnOspfAreaEntry 2 }

dcnOspfAreaRowStatus OBJECT-TYPE
    SYNTAX      RowStatus
    MAX-ACCESS  read-create
    STATUS      current
    DESCRIPTION
        "RowStatus" 
    ::=  { dcnOspfAreaEntry 3 }

dcnOspfAreaIfListSize OBJECT-TYPE
    SYNTAX      Unsigned32
    MAX-ACCESS  read-only
    STATUS      current
    DESCRIPTION
        "A number of attached interfaces." 
    ::=  { dcnOspfAreaEntry 4 }

dcnOspfAreaStubDefaultMetric OBJECT-TYPE
    SYNTAX      Unsigned32 (0..65535 | 4294967295)
    MAX-ACCESS  read-create
    STATUS      current
    DESCRIPTION
        "Stub Default Route Cost" 
    ::=  { dcnOspfAreaEntry 5 }

dcnOspfAreaCapTable OBJECT-TYPE
    SYNTAX      SEQUENCE OF DcnOspfAreaCapEntry
    MAX-ACCESS  not-accessible
    STATUS      current
    DESCRIPTION   "This table contains OSPF Area Entity creation/modification capabilities."
    ::=  { dcnOspf 2 }

dcnOspfAreaCapEntry OBJECT-TYPE
    SYNTAX      DcnOspfAreaCapEntry
    MAX-ACCESS  not-accessible
    STATUS      current
    DESCRIPTION   "Table row represents creation/modification capabilities for particular
         OSPF Area entity."
    INDEX       {
                  dcnOspfAreaId,
                  dcnOspfAreaType
                }
    ::=  { dcnOspfAreaCapTable 1 }

DcnOspfAreaCapEntry ::=  SEQUENCE
  { dcnOspfAreaCapRowStatus FspR7RowStatusCaps,
    dcnOspfAreaCapStubDefaultMetric FspR7Unsigned32Caps }

dcnOspfAreaCapRowStatus OBJECT-TYPE
    SYNTAX      FspR7RowStatusCaps
    MAX-ACCESS  read-only
    STATUS      current
    DESCRIPTION
        "RowStatus" 
    ::=  { dcnOspfAreaCapEntry 1 }

dcnOspfAreaCapStubDefaultMetric OBJECT-TYPE
    SYNTAX      FspR7Unsigned32Caps
    MAX-ACCESS  read-only
    STATUS      current
    DESCRIPTION
        "Stub Default Route Cost" 
    ::=  { dcnOspfAreaCapEntry 2 }

dcnOspfAreaInterfaceTable OBJECT-TYPE
    SYNTAX      SEQUENCE OF DcnOspfAreaInterfaceEntry
    MAX-ACCESS  not-accessible
    STATUS      current
    DESCRIPTION   "This table contains OSPF Area Entity creation/modification capabilities."
    ::=  { dcnOspf 3 }

dcnOspfAreaInterfaceEntry OBJECT-TYPE
    SYNTAX      DcnOspfAreaInterfaceEntry
    MAX-ACCESS  not-accessible
    STATUS      current
    DESCRIPTION   "Table row represents creation/modification capabilities for particular
         OSPF Area entity."
    INDEX       {
                  dcnOspfAreaId,
                  entityIndex
                }
    ::=  { dcnOspfAreaInterfaceTable 1 }

DcnOspfAreaInterfaceEntry ::=  SEQUENCE
  { dcnOspfAreaInterfaceIndexAid SnmpAdminString }

dcnOspfAreaInterfaceIndexAid OBJECT-TYPE
    SYNTAX      SnmpAdminString
    MAX-ACCESS  read-only
    STATUS      current
    DESCRIPTION
        "Name" 
    ::=  { dcnOspfAreaInterfaceEntry 1 }

highAvailabilityTable OBJECT-TYPE
    SYNTAX      SEQUENCE OF HighAvailabilityEntry
    MAX-ACCESS  not-accessible
    STATUS      current
    DESCRIPTION   ""
    ::=  { haMIB 1 }

highAvailabilityEntry OBJECT-TYPE
    SYNTAX      HighAvailabilityEntry
    MAX-ACCESS  not-accessible
    STATUS      current
    DESCRIPTION   ""
    INDEX       {
                  entityIndex
                }
    ::=  { highAvailabilityTable 1 }

HighAvailabilityEntry ::=  SEQUENCE
  { highAvailabilityProtectionIndexAid EntityIndex,
    highAvailabilityInhSwitching FspR7YesNo,
    highAvailabilitySwitchToDuplex FspR7Swdx,
    highAvailabilitySwitchOverCause FspR7SwitchOverCause,
    highAvailabilitySoftwareVersion SnmpAdminString }

highAvailabilityProtectionIndexAid OBJECT-TYPE
    SYNTAX      EntityIndex
    MAX-ACCESS  read-only
    STATUS      current
    DESCRIPTION
        "(Protection AID) AID of protection entity involved in the protection group." 
    ::=  { highAvailabilityEntry 1 }

highAvailabilityInhSwitching OBJECT-TYPE
    SYNTAX      FspR7YesNo
    MAX-ACCESS  read-write
    STATUS      current
    DESCRIPTION
        "(Inhibit Controller Switching) Prevents protection switch to partner controller." 
    ::=  { highAvailabilityEntry 2 }

highAvailabilitySwitchToDuplex OBJECT-TYPE
    SYNTAX      FspR7Swdx
    MAX-ACCESS  read-write
    STATUS      current
    DESCRIPTION
        "Switch to Parnter Controller" 
    ::=  { highAvailabilityEntry 3 }

highAvailabilitySwitchOverCause OBJECT-TYPE
    SYNTAX      FspR7SwitchOverCause
    MAX-ACCESS  read-only
    STATUS      current
    DESCRIPTION
        "Cause of Fail-Over or Switch-Over to Partner Controller" 
    ::=  { highAvailabilityEntry 4 }

highAvailabilitySoftwareVersion OBJECT-TYPE
    SYNTAX      SnmpAdminString
    MAX-ACCESS  read-only
    STATUS      current
    DESCRIPTION
        "Software Version of the NCU software. <" 
    ::=  { highAvailabilityEntry 5 }

remoteServerTable OBJECT-TYPE
    SYNTAX      SEQUENCE OF RemoteServerEntry
    MAX-ACCESS  not-accessible
    STATUS      current
    DESCRIPTION   "Radius configuration table."
    ::=  { radius 1 }

remoteServerEntry OBJECT-TYPE
    SYNTAX      RemoteServerEntry
    MAX-ACCESS  not-accessible
    STATUS      current
    DESCRIPTION   "Table entry represents the radius server."
    INDEX       {
                  remoteServerPriority
                }
    ::=  { remoteServerTable 1 }

RemoteServerEntry ::=  SEQUENCE
  { remoteServerPriority Unsigned32,
    remoteServerIp IpAddress,
    remoteServerUdpPort Unsigned32,
    remoteServerRemoteTimeout Unsigned32,
    remoteServerRemoteSecret SnmpAdminString,
    remoteServerOwnIp SourceIpAddress,
    remoteServerAdminState FspR7NtpAdminState,
    remoteServerRowStatus RowStatus }

remoteServerPriority OBJECT-TYPE
    SYNTAX      Unsigned32 (0..255)
    MAX-ACCESS  accessible-for-notify
    STATUS      current
    DESCRIPTION   ""
    ::=  { remoteServerEntry 1 }

remoteServerIp OBJECT-TYPE
    SYNTAX      IpAddress
    MAX-ACCESS  read-write
    STATUS      current
    DESCRIPTION   "The IP address of the remote server."
    ::=  { remoteServerEntry 2 }

remoteServerUdpPort OBJECT-TYPE
    SYNTAX      Unsigned32 (1..65535 | 4294967295)
    MAX-ACCESS  read-write
    STATUS      current
    DESCRIPTION   ""
    ::=  { remoteServerEntry 3 }

remoteServerRemoteTimeout OBJECT-TYPE
    SYNTAX      Unsigned32 (1..60 | 4294967295) 
    UNITS       "s"
    MAX-ACCESS  read-write
    STATUS      current
    DESCRIPTION   ""
    ::=  { remoteServerEntry 4 }

remoteServerRemoteSecret OBJECT-TYPE
    SYNTAX      SnmpAdminString
    MAX-ACCESS  read-write
    STATUS      current
    DESCRIPTION   ""
    ::=  { remoteServerEntry 5 }

remoteServerOwnIp OBJECT-TYPE
    SYNTAX      SourceIpAddress
    MAX-ACCESS  read-write
    STATUS      current
    DESCRIPTION   ""
    ::=  { remoteServerEntry 6 }

remoteServerAdminState OBJECT-TYPE
    SYNTAX      FspR7NtpAdminState
    MAX-ACCESS  read-write
    STATUS      current
    DESCRIPTION   ""
    ::=  { remoteServerEntry 7 }

remoteServerRowStatus OBJECT-TYPE
    SYNTAX      RowStatus
    MAX-ACCESS  read-write
    STATUS      current
    DESCRIPTION   "Row status used for managing a remote server entity. All values defined for
         RowStatus TC can be used.
        "
    ::=  { remoteServerEntry 8 }

communityCmd OBJECT-TYPE
    SYNTAX      FspR7CommunityCmd
    MAX-ACCESS  read-write
    STATUS      current
    DESCRIPTION   "This scalar should be used for creating and deleting SNMP communities in system.
         Three values can be used. 'idle' is returned on each get-request on this scalar. 'create' should be used,
         while creating. First 'communityName' and 'communitySecurityName' should be set (these objects are mandatory).
         Now the 'create' can be performed. Scalars 'communityIpAddr' and 'communityIpAddrMask' are optional and
         when needed should be set before 'create' command."
    ::=  { snmpCommunityMIB 1 }

communityName OBJECT-TYPE
    SYNTAX      SnmpAdminString
    MAX-ACCESS  read-write
    STATUS      current
    DESCRIPTION   "This scalar specifies the SNMP communiy name. Mandatory object."
    ::=  { snmpCommunityMIB 2 }

communitySecurityName OBJECT-TYPE
    SYNTAX      FspR7SecurityName
    MAX-ACCESS  read-write
    STATUS      current
    DESCRIPTION   "This scalar specifies the security of the SNMP communiy - Read-Write / Read-Only. Mandatory object."
    ::=  { snmpCommunityMIB 3 }

communityIpAddr OBJECT-TYPE
    SYNTAX      IpAddress
    MAX-ACCESS  read-write
    STATUS      current
    DESCRIPTION   "This scalar specifies the restriction on IP address of the SNMP communiy. Optional object."
    ::=  { snmpCommunityMIB 4 }

communityIpAddrMask OBJECT-TYPE
    SYNTAX      IpAddress
    MAX-ACCESS  read-write
    STATUS      current
    DESCRIPTION   "This scalar specifies the restriction on subnet of IP addresses of the SNMP communiy. Optional object."
    ::=  { snmpCommunityMIB 5 }

snmpCommunityTable OBJECT-TYPE
    SYNTAX      SEQUENCE OF SnmpCommunityEntry
    MAX-ACCESS  not-accessible
    STATUS      current
    DESCRIPTION   "This table shows the SNMP community strings."
    ::=  { snmpCommunityMIB 10 }

snmpCommunityEntry OBJECT-TYPE
    SYNTAX      SnmpCommunityEntry
    MAX-ACCESS  not-accessible
    STATUS      current
    DESCRIPTION   ""
    INDEX       {
                  snmpCommunityIndex
                }
    ::=  { snmpCommunityTable 1 }

SnmpCommunityEntry ::=  SEQUENCE
  { snmpCommunityIndex Unsigned32,
    snmpCommunityName SnmpAdminString,
    snmpCommunitySecurityName FspR7SecurityName,
    snmpCommunityIpAddr IpAddress,
    snmpCommunityIpAddrMask IpAddress }

snmpCommunityIndex OBJECT-TYPE
    SYNTAX      Unsigned32
    MAX-ACCESS  not-accessible
    STATUS      current
    DESCRIPTION   "Ordinal index. First all RO objects, then all RW objects, are shown."
    ::=  { snmpCommunityEntry 1 }

snmpCommunityName OBJECT-TYPE
    SYNTAX      SnmpAdminString
    MAX-ACCESS  read-only
    STATUS      current
    DESCRIPTION   "The SNMP community name."
    ::=  { snmpCommunityEntry 2 }

snmpCommunitySecurityName OBJECT-TYPE
    SYNTAX      FspR7SecurityName
    MAX-ACCESS  read-only
    STATUS      current
    DESCRIPTION   "The security of the SNMP communiy - Read-Write / Read-Only."
    ::=  { snmpCommunityEntry 3 }

snmpCommunityIpAddr OBJECT-TYPE
    SYNTAX      IpAddress
    MAX-ACCESS  read-only
    STATUS      current
    DESCRIPTION   "The restriction on IP address of the SNMP communiy. Value 0.0.0.0 means no restrictions."
    ::=  { snmpCommunityEntry 4 }

snmpCommunityIpAddrMask OBJECT-TYPE
    SYNTAX      IpAddress
    MAX-ACCESS  read-only
    STATUS      current
    DESCRIPTION   "The restriction on subnet of IP addresses of the SNMP communiy. Value 255.255.255.255 means no restrictions."
    ::=  { snmpCommunityEntry 5 }

profileIndexLock OBJECT-TYPE
    SYNTAX      Unsigned32
    MAX-ACCESS  read-write
    STATUS      current
    DESCRIPTION   "The index locker object for configProfileEntry. It shall be used
         for entry creation in configProfileTable. Procedure is following:
         - read the current value of profileIndexLock.0
         - save the read value to profileIndexLock.0; this
         action will increment object value by 1."
    ::=  { profileMIB 1 }

profileName OBJECT-TYPE
    SYNTAX      SnmpAdminString
    MAX-ACCESS  read-write
    STATUS      current
    DESCRIPTION   "Profile name indicated for manipulation."
    ::=  { profileMIB 2 }

profileForceCopyEnabled OBJECT-TYPE
    SYNTAX      FspR7Overwrite
    MAX-ACCESS  read-write
    STATUS      current
    DESCRIPTION   "By default this object is set to no(1). If set to yes(2) then
         profile from RDISK may overwrite read-only profile kept in
         PDISK."
    ::=  { profileMIB 3 }

profileCmd OBJECT-TYPE
    SYNTAX      FspR7ProfileCmd
    MAX-ACCESS  read-write
    STATUS      current
    DESCRIPTION   "Executable command for profile manipulation."
    ::=  { profileMIB 4 }

configProfileTable OBJECT-TYPE
    SYNTAX      SEQUENCE OF ConfigProfileEntry
    MAX-ACCESS  not-accessible
    STATUS      current
    DESCRIPTION   "External Channel Interface Profile table."
    ::=  { profileMIB 10 }

configProfileEntry OBJECT-TYPE
    SYNTAX      ConfigProfileEntry
    MAX-ACCESS  not-accessible
    STATUS      current
    DESCRIPTION   "Entry represents a profile file existing on PDISK."
    INDEX       {
                  configProfileId
                }
    ::=  { configProfileTable 1 }

ConfigProfileEntry ::=  SEQUENCE
  { configProfileId Unsigned32,
    configProfileRowStatus RowStatus,
    configProfileName SnmpAdminString,
    configProfileSourceEntityIndex EntityIndex,
    configProfileSourceEntityExtIndex SnmpAdminString,
    configProfileType FspR7ProfileType,
    configProfileEntityType FspR7EntityType,
    configProfileMaxAccessLevel FspR7AccessLevel }

configProfileId OBJECT-TYPE
    SYNTAX      Unsigned32
    MAX-ACCESS  not-accessible
    STATUS      current
    DESCRIPTION
        "A standard Unsigned32 parameter type." 
    ::=  { configProfileEntry 1 }

configProfileRowStatus OBJECT-TYPE
    SYNTAX      RowStatus
    MAX-ACCESS  read-create
    STATUS      current
    DESCRIPTION
        "RowStatus" 
    ::=  { configProfileEntry 2 }

configProfileName OBJECT-TYPE
    SYNTAX      SnmpAdminString
    MAX-ACCESS  read-create
    STATUS      current
    DESCRIPTION
        "" 
    ::=  { configProfileEntry 3 }

configProfileSourceEntityIndex OBJECT-TYPE
    SYNTAX      EntityIndex
    MAX-ACCESS  read-create
    STATUS      current
    DESCRIPTION
        "" 
    ::=  { configProfileEntry 4 }

configProfileSourceEntityExtIndex OBJECT-TYPE
    SYNTAX      SnmpAdminString
    MAX-ACCESS  read-create
    STATUS      current
    DESCRIPTION
        "" 
    ::=  { configProfileEntry 5 }

configProfileType OBJECT-TYPE
    SYNTAX      FspR7ProfileType
    MAX-ACCESS  read-only
    STATUS      current
    DESCRIPTION
        "Profile Type" 
    ::=  { configProfileEntry 6 }

configProfileEntityType OBJECT-TYPE
    SYNTAX      FspR7EntityType
    MAX-ACCESS  read-only
    STATUS      current
    DESCRIPTION
        "" 
    ::=  { configProfileEntry 7 }

configProfileMaxAccessLevel OBJECT-TYPE
    SYNTAX      FspR7AccessLevel
    MAX-ACCESS  read-only
    STATUS      current
    DESCRIPTION
        "File Access" 
    ::=  { configProfileEntry 8 }

contentProfileDataTable OBJECT-TYPE
    SYNTAX      SEQUENCE OF ContentProfileDataEntry
    MAX-ACCESS  not-accessible
    STATUS      current
    DESCRIPTION   "External Channel Interface Content Profile Data table."
    ::=  { profileMIB 11 }

contentProfileDataEntry OBJECT-TYPE
    SYNTAX      ContentProfileDataEntry
    MAX-ACCESS  not-accessible
    STATUS      current
    DESCRIPTION   "Entry represents a content data of profile file existing on PDISK."
    INDEX       {
                  configProfileId
                }
    ::=  { contentProfileDataTable 1 }

ContentProfileDataEntry ::=  SEQUENCE
  { contentProfileDataBitrate Unsigned32,
    contentProfileDataFecType FspR7FecType,
    contentProfileDataLineCoding FspR7LineCoding,
    contentProfileDataFrameFormat FspR7FrameFormat,
    contentProfileDataOpticalPowerTx Integer32,
    contentProfileDataOSNRTransmit Unsigned32,
    contentProfileDataPMDTransmit Unsigned32,
    contentProfileDataChromaticDispersionTx Integer32,
    contentProfileDataMinimumOSNRRcv Unsigned32,
    contentProfileDataMinimumOpticalPowerRcv Integer32,
    contentProfileDataMaximumOpticalPowerRcv Integer32,
    contentProfileDataMaximumPMDRcv Unsigned32,
    contentProfileDataMinChromaticDispersionRcv Integer32,
    contentProfileDataMaxChromaticDispersionRcv Integer32,
    contentProfileDataMaxBitErrorRate FspR7MaxBitErrorRate,
    contentProfileDataAlias SnmpAdminString,
    contentProfileDataFarEndLocation SnmpAdminString }

contentProfileDataBitrate OBJECT-TYPE
    SYNTAX      Unsigned32 
    UNITS       "Mbps"
    MAX-ACCESS  read-only
    STATUS      current
    DESCRIPTION
        "Derived from TYPE" 
    ::=  { contentProfileDataEntry 1 }

contentProfileDataFecType OBJECT-TYPE
    SYNTAX      FspR7FecType
    MAX-ACCESS  read-only
    STATUS      current
    DESCRIPTION
        "Forward Error Correction (Only relevant where TYPE = OTU#)" 
    ::=  { contentProfileDataEntry 2 }

contentProfileDataLineCoding OBJECT-TYPE
    SYNTAX      FspR7LineCoding
    MAX-ACCESS  read-only
    STATUS      current
    DESCRIPTION
        "Line Coding" 
    ::=  { contentProfileDataEntry 3 }

contentProfileDataFrameFormat OBJECT-TYPE
    SYNTAX      FspR7FrameFormat
    MAX-ACCESS  read-only
    STATUS      current
    DESCRIPTION
        "Frame Format" 
    ::=  { contentProfileDataEntry 4 }

contentProfileDataOpticalPowerTx OBJECT-TYPE
    SYNTAX      Integer32 (-9900..600 | -2147483648) 
    UNITS       "0.1 dBm"
    MAX-ACCESS  read-only
    STATUS      current
    DESCRIPTION
        "Optical Power Transmit" 
    ::=  { contentProfileDataEntry 5 }

contentProfileDataOSNRTransmit OBJECT-TYPE
    SYNTAX      Unsigned32 (0..58 | 4294967295) 
    UNITS       "dB"
    MAX-ACCESS  read-only
    STATUS      current
    DESCRIPTION
        "Optical Signal to Noise Ratio Transmit" 
    ::=  { contentProfileDataEntry 6 }

contentProfileDataPMDTransmit OBJECT-TYPE
    SYNTAX      Unsigned32 (0..30 | 4294967295) 
    UNITS       "ps"
    MAX-ACCESS  read-only
    STATUS      current
    DESCRIPTION
        "Polarization Mode Dispersion Transmit" 
    ::=  { contentProfileDataEntry 7 }

contentProfileDataChromaticDispersionTx OBJECT-TYPE
    SYNTAX      Integer32 (-60000..60000 | -2147483648) 
    UNITS       "ps/nm"
    MAX-ACCESS  read-only
    STATUS      current
    DESCRIPTION
        "Chromatic Dispersion Transmit" 
    ::=  { contentProfileDataEntry 8 }

contentProfileDataMinimumOSNRRcv OBJECT-TYPE
    SYNTAX      Unsigned32 (10..58 | 4294967295) 
    UNITS       "dB"
    MAX-ACCESS  read-only
    STATUS      current
    DESCRIPTION
        "Minimum Optical Signal to Noise Ratio, Rcv" 
    ::=  { contentProfileDataEntry 9 }

contentProfileDataMinimumOpticalPowerRcv OBJECT-TYPE
    SYNTAX      Integer32 (-2500..1000 | -2147483648) 
    UNITS       "0.1 dBm"
    MAX-ACCESS  read-only
    STATUS      current
    DESCRIPTION
        "Minimum Optical Power Received" 
    ::=  { contentProfileDataEntry 10 }

contentProfileDataMaximumOpticalPowerRcv OBJECT-TYPE
    SYNTAX      Integer32 (-2500..1000 | -2147483648) 
    UNITS       "0.1 dBm"
    MAX-ACCESS  read-only
    STATUS      current
    DESCRIPTION
        "Maximum Optical Power Received" 
    ::=  { contentProfileDataEntry 11 }

contentProfileDataMaximumPMDRcv OBJECT-TYPE
    SYNTAX      Unsigned32 (0..30 | 4294967295) 
    UNITS       "ps"
    MAX-ACCESS  read-only
    STATUS      current
    DESCRIPTION
        "Maximum Polarization Mode Dispersion Rcv" 
    ::=  { contentProfileDataEntry 12 }

contentProfileDataMinChromaticDispersionRcv OBJECT-TYPE
    SYNTAX      Integer32 (-60000..60000 | -2147483648) 
    UNITS       "ps/nm"
    MAX-ACCESS  read-only
    STATUS      current
    DESCRIPTION
        "Minimum Chromatic Dispersion Rcv" 
    ::=  { contentProfileDataEntry 13 }

contentProfileDataMaxChromaticDispersionRcv OBJECT-TYPE
    SYNTAX      Integer32 (-60000..60000 | -2147483648) 
    UNITS       "ps/nm"
    MAX-ACCESS  read-only
    STATUS      current
    DESCRIPTION
        "Maximum Chromatic Dispersion Rcv" 
    ::=  { contentProfileDataEntry 14 }

contentProfileDataMaxBitErrorRate OBJECT-TYPE
    SYNTAX      FspR7MaxBitErrorRate
    MAX-ACCESS  read-only
    STATUS      current
    DESCRIPTION
        "Maximum Bit Error Rate" 
    ::=  { contentProfileDataEntry 15 }

contentProfileDataAlias OBJECT-TYPE
    SYNTAX      SnmpAdminString
    MAX-ACCESS  read-only
    STATUS      current
    DESCRIPTION
        "User Applied Descriptor" 
    ::=  { contentProfileDataEntry 16 }

contentProfileDataFarEndLocation OBJECT-TYPE
    SYNTAX      SnmpAdminString
    MAX-ACCESS  read-only
    STATUS      current
    DESCRIPTION
        "FEND Location" 
    ::=  { contentProfileDataEntry 17 }

conditionSeverityTable OBJECT-TYPE
    SYNTAX      SEQUENCE OF ConditionSeverityEntry
    MAX-ACCESS  not-accessible
    STATUS      current
    DESCRIPTION   "This table contains a severity value for each defined standing condition reported by an entity in the NE."
    ::=  { conditionFilters 1 }

conditionSeverityEntry OBJECT-TYPE
    SYNTAX      ConditionSeverityEntry
    MAX-ACCESS  not-accessible
    STATUS      current
    DESCRIPTION   "Each entry in the table represents the severity assigned to a condition."
    INDEX       {
                  entityIndex,
                  conditionSeverityType
                }
    ::=  { conditionSeverityTable 1 }

ConditionSeverityEntry ::=  SEQUENCE
  { conditionSeverityType FspR7StandingConditionTypes,
    conditionSeverityValue TrapAlarmSeverity }

conditionSeverityType OBJECT-TYPE
    SYNTAX      FspR7StandingConditionTypes
    MAX-ACCESS  not-accessible
    STATUS      current
    DESCRIPTION   "This object identifies the type of alarm."
    ::=  { conditionSeverityEntry 1 }

conditionSeverityValue OBJECT-TYPE
    SYNTAX      TrapAlarmSeverity
    MAX-ACCESS  read-write
    STATUS      current
    DESCRIPTION   "This object identifies the severity assigned to this alarm."
    ::=  { conditionSeverityEntry 2 }

ntpSysConditionSeverityTable OBJECT-TYPE
    SYNTAX      SEQUENCE OF NtpSysConditionSeverityEntry
    MAX-ACCESS  not-accessible
    STATUS      current
    DESCRIPTION   "This table contains a severity value for each defined alarm (standing condition) present on NTP System Entity."
    ::=  { conditionFilters 2 }

ntpSysConditionSeverityEntry OBJECT-TYPE
    SYNTAX      NtpSysConditionSeverityEntry
    MAX-ACCESS  not-accessible
    STATUS      current
    DESCRIPTION   "Each entry in the table represents the severity assigned to a condition."
    INDEX       {
                  ntpSysConditionSeverityType
                }
    ::=  { ntpSysConditionSeverityTable 1 }

NtpSysConditionSeverityEntry ::=  SEQUENCE
  { ntpSysConditionSeverityType FspR7StandingConditionTypes,
    ntpSysConditionSeverityValue TrapAlarmSeverity }

ntpSysConditionSeverityType OBJECT-TYPE
    SYNTAX      FspR7StandingConditionTypes
    MAX-ACCESS  not-accessible
    STATUS      current
    DESCRIPTION   "This object identifies the type of alarm."
    ::=  { ntpSysConditionSeverityEntry 1 }

ntpSysConditionSeverityValue OBJECT-TYPE
    SYNTAX      TrapAlarmSeverity
    MAX-ACCESS  read-write
    STATUS      current
    DESCRIPTION   "This object identifies the severity assigned to this alarm."
    ::=  { ntpSysConditionSeverityEntry 2 }

ntpSrvConditionSeverityTable OBJECT-TYPE
    SYNTAX      SEQUENCE OF NtpSrvConditionSeverityEntry
    MAX-ACCESS  not-accessible
    STATUS      current
    DESCRIPTION   "This table contains a severity value for each defined alarm (standing condition) present on NTP Server Entity."
    ::=  { conditionFilters 3 }

ntpSrvConditionSeverityEntry OBJECT-TYPE
    SYNTAX      NtpSrvConditionSeverityEntry
    MAX-ACCESS  not-accessible
    STATUS      current
    DESCRIPTION   "Each entry in the table represents the severity assigned to a condition."
    INDEX       {
                  ntpServerIp,
                  ntpSysConditionSeverityType
                }
    ::=  { ntpSrvConditionSeverityTable 1 }

NtpSrvConditionSeverityEntry ::=  SEQUENCE
  { ntpSrvConditionSeverityType FspR7StandingConditionTypes,
    ntpSrvConditionSeverityValue TrapAlarmSeverity }

ntpSrvConditionSeverityType OBJECT-TYPE
    SYNTAX      FspR7StandingConditionTypes
    MAX-ACCESS  not-accessible
    STATUS      current
    DESCRIPTION   "This object identifies the type of alarm."
    ::=  { ntpSrvConditionSeverityEntry 1 }

ntpSrvConditionSeverityValue OBJECT-TYPE
    SYNTAX      TrapAlarmSeverity
    MAX-ACCESS  read-write
    STATUS      current
    DESCRIPTION   "This object identifies the severity assigned to this alarm."
    ::=  { ntpSrvConditionSeverityEntry 2 }

ptpConditionSeverityTable OBJECT-TYPE
    SYNTAX      SEQUENCE OF PtpConditionSeverityEntry
    MAX-ACCESS  not-accessible
    STATUS      current
    DESCRIPTION   "This table contains a severity value for each defined standing condition reported by an entity in the NE."
    ::=  { conditionFilters 4 }

ptpConditionSeverityEntry OBJECT-TYPE
    SYNTAX      PtpConditionSeverityEntry
    MAX-ACCESS  not-accessible
    STATUS      current
    DESCRIPTION   "Each entry in the table represents the severity assigned to a condition.'"
    INDEX       {
                  ptpEntityIndex,
                  conditionSeverityType
                }
    ::=  { ptpConditionSeverityTable 1 }

PtpConditionSeverityEntry ::=  SEQUENCE
  { ptpConditionSeverityType FspR7StandingConditionTypes,
    ptpConditionSeverityValue TrapAlarmSeverity }

ptpConditionSeverityType OBJECT-TYPE
    SYNTAX      FspR7StandingConditionTypes
    MAX-ACCESS  not-accessible
    STATUS      current
    DESCRIPTION   "This object identifies the type of alarm."
    ::=  { ptpConditionSeverityEntry 1 }

ptpConditionSeverityValue OBJECT-TYPE
    SYNTAX      TrapAlarmSeverity
    MAX-ACCESS  read-write
    STATUS      current
    DESCRIPTION   "This object identifies the severity assigned to this alarm."
    ::=  { ptpConditionSeverityEntry 2 }

currentConditionTable OBJECT-TYPE
    SYNTAX      SEQUENCE OF CurrentConditionEntry
    MAX-ACCESS  not-accessible
    STATUS      current
    DESCRIPTION   ""
    ::=  { currentConditions 1 }

currentConditionEntry OBJECT-TYPE
    SYNTAX      CurrentConditionEntry
    MAX-ACCESS  not-accessible
    STATUS      current
    DESCRIPTION   ""
    INDEX       {
                  entityIndex,
                  currentConditionType
                }
    ::=  { currentConditionTable 1 }

CurrentConditionEntry ::=  SEQUENCE
  { currentConditionType FspR7StandingConditionTypes,
    currentConditionSeverity TrapAlarmSeverity,
    currentConditionAffect ServiceImpairment,
    currentConditionTimeStamp DateAndTime }

currentConditionType OBJECT-TYPE
    SYNTAX      FspR7StandingConditionTypes
    MAX-ACCESS  not-accessible
    STATUS      current
    DESCRIPTION   "List of all alarms."
    ::=  { currentConditionEntry 1 }

currentConditionSeverity OBJECT-TYPE
    SYNTAX      TrapAlarmSeverity
    MAX-ACCESS  read-only
    STATUS      current
    DESCRIPTION   "Current alarm severity."
    ::=  { currentConditionEntry 2 }

currentConditionAffect OBJECT-TYPE
    SYNTAX      ServiceImpairment
    MAX-ACCESS  read-only
    STATUS      current
    DESCRIPTION   "This object indicates the service impairment affect of the alarm."
    ::=  { currentConditionEntry 3 }

currentConditionTimeStamp OBJECT-TYPE
    SYNTAX      DateAndTime
    MAX-ACCESS  read-only
    STATUS      current
    DESCRIPTION   "Timestamp."
    ::=  { currentConditionEntry 4 }

ntpSysCurrentConditionTable OBJECT-TYPE
    SYNTAX      SEQUENCE OF NtpSysCurrentConditionEntry
    MAX-ACCESS  not-accessible
    STATUS      current
    DESCRIPTION   ""
    ::=  { currentConditions 2 }

ntpSysCurrentConditionEntry OBJECT-TYPE
    SYNTAX      NtpSysCurrentConditionEntry
    MAX-ACCESS  not-accessible
    STATUS      current
    DESCRIPTION   ""
    INDEX       {
                  ntpSysConditionSeverityType
                }
    ::=  { ntpSysCurrentConditionTable 1 }

NtpSysCurrentConditionEntry ::=  SEQUENCE
  { ntpSysCurrentConditionType FspR7StandingConditionTypes,
    ntpSysCurrentConditionSeverity TrapAlarmSeverity,
    ntpSysCurrentConditionAffect ServiceImpairment,
    ntpSysCurrentConditionTimeStamp DateAndTime }

ntpSysCurrentConditionType OBJECT-TYPE
    SYNTAX      FspR7StandingConditionTypes
    MAX-ACCESS  not-accessible
    STATUS      current
    DESCRIPTION   "List of all alarms."
    ::=  { ntpSysCurrentConditionEntry 1 }

ntpSysCurrentConditionSeverity OBJECT-TYPE
    SYNTAX      TrapAlarmSeverity
    MAX-ACCESS  read-only
    STATUS      current
    DESCRIPTION   "Current alarm severity."
    ::=  { ntpSysCurrentConditionEntry 2 }

ntpSysCurrentConditionAffect OBJECT-TYPE
    SYNTAX      ServiceImpairment
    MAX-ACCESS  read-only
    STATUS      current
    DESCRIPTION   "This object indicates the service impairment affect of the alarm."
    ::=  { ntpSysCurrentConditionEntry 3 }

ntpSysCurrentConditionTimeStamp OBJECT-TYPE
    SYNTAX      DateAndTime
    MAX-ACCESS  read-only
    STATUS      current
    DESCRIPTION   "Timestamp."
    ::=  { ntpSysCurrentConditionEntry 4 }

ntpSrvCurrentConditionTable OBJECT-TYPE
    SYNTAX      SEQUENCE OF NtpSrvCurrentConditionEntry
    MAX-ACCESS  not-accessible
    STATUS      current
    DESCRIPTION   ""
    ::=  { currentConditions 3 }

ntpSrvCurrentConditionEntry OBJECT-TYPE
    SYNTAX      NtpSrvCurrentConditionEntry
    MAX-ACCESS  not-accessible
    STATUS      current
    DESCRIPTION   ""
    INDEX       {
                  ntpServerIp,
                  ntpSrvConditionSeverityType
                }
    ::=  { ntpSrvCurrentConditionTable 1 }

NtpSrvCurrentConditionEntry ::=  SEQUENCE
  { ntpSrvCurrentConditionType FspR7StandingConditionTypes,
    ntpSrvCurrentConditionSeverity TrapAlarmSeverity,
    ntpSrvCurrentConditionAffect ServiceImpairment,
    ntpSrvCurrentConditionTimeStamp DateAndTime }

ntpSrvCurrentConditionType OBJECT-TYPE
    SYNTAX      FspR7StandingConditionTypes
    MAX-ACCESS  not-accessible
    STATUS      current
    DESCRIPTION   "List of all alarms."
    ::=  { ntpSrvCurrentConditionEntry 1 }

ntpSrvCurrentConditionSeverity OBJECT-TYPE
    SYNTAX      TrapAlarmSeverity
    MAX-ACCESS  read-only
    STATUS      current
    DESCRIPTION   "Current alarm severity."
    ::=  { ntpSrvCurrentConditionEntry 2 }

ntpSrvCurrentConditionAffect OBJECT-TYPE
    SYNTAX      ServiceImpairment
    MAX-ACCESS  read-only
    STATUS      current
    DESCRIPTION   "This object indicates the service impairment affect of the alarm."
    ::=  { ntpSrvCurrentConditionEntry 3 }

ntpSrvCurrentConditionTimeStamp OBJECT-TYPE
    SYNTAX      DateAndTime
    MAX-ACCESS  read-only
    STATUS      current
    DESCRIPTION   "Timestamp."
    ::=  { ntpSrvCurrentConditionEntry 4 }

ptpCurrentConditionTable OBJECT-TYPE
    SYNTAX      SEQUENCE OF PtpCurrentConditionEntry
    MAX-ACCESS  not-accessible
    STATUS      current
    DESCRIPTION   ""
    ::=  { currentConditions 4 }

ptpCurrentConditionEntry OBJECT-TYPE
    SYNTAX      PtpCurrentConditionEntry
    MAX-ACCESS  not-accessible
    STATUS      current
    DESCRIPTION   ""
    INDEX       {
                  ptpEntityIndex,
                  currentConditionType
                }
    ::=  { ptpCurrentConditionTable 1 }

PtpCurrentConditionEntry ::=  SEQUENCE
  { ptpCurrentConditionType FspR7StandingConditionTypes,
    ptpCurrentConditionSeverity TrapAlarmSeverity,
    ptpCurrentConditionAffect ServiceImpairment,
    ptpCurrentConditionTimeStamp DateAndTime }

ptpCurrentConditionType OBJECT-TYPE
    SYNTAX      FspR7StandingConditionTypes
    MAX-ACCESS  not-accessible
    STATUS      current
    DESCRIPTION   "List of all interface conditions"
    ::=  { ptpCurrentConditionEntry 1 }

ptpCurrentConditionSeverity OBJECT-TYPE
    SYNTAX      TrapAlarmSeverity
    MAX-ACCESS  read-only
    STATUS      current
    DESCRIPTION   "This object identifies the current severity of alarm."
    ::=  { ptpCurrentConditionEntry 2 }

ptpCurrentConditionAffect OBJECT-TYPE
    SYNTAX      ServiceImpairment
    MAX-ACCESS  read-only
    STATUS      current
    DESCRIPTION   "This object indicates the service impairment affect of the alarm."
    ::=  { ptpCurrentConditionEntry 3 }

ptpCurrentConditionTimeStamp OBJECT-TYPE
    SYNTAX      DateAndTime
    MAX-ACCESS  read-only
    STATUS      current
    DESCRIPTION   "Timestamp"
    ::=  { ptpCurrentConditionEntry 4 }

alarmProfileTable OBJECT-TYPE
    SYNTAX      SEQUENCE OF AlarmProfileEntry
    MAX-ACCESS  not-accessible
    STATUS      current
    DESCRIPTION   ""
    ::=  { alarmProfileConfig 1 }

alarmProfileEntry OBJECT-TYPE
    SYNTAX      AlarmProfileEntry
    MAX-ACCESS  not-accessible
    STATUS      current
    DESCRIPTION   ""
    INDEX       {
                  alarmProfileAidType,
                  conditionSeverityType
                }
    ::=  { alarmProfileTable 1 }

AlarmProfileEntry ::=  SEQUENCE
  { alarmProfileAidType FspR7AidType,
    alarmProfileValue TrapAlarmSeverity,
    alarmProfileDefaultValue TrapAlarmSeverity }

alarmProfileAidType OBJECT-TYPE
    SYNTAX      FspR7AidType
    MAX-ACCESS  not-accessible
    STATUS      current
    DESCRIPTION   ""
    ::=  { alarmProfileEntry 1 }

alarmProfileValue OBJECT-TYPE
    SYNTAX      TrapAlarmSeverity
    MAX-ACCESS  read-write
    STATUS      current
    DESCRIPTION   "This object identifies the severity assigned to this alarm."
    ::=  { alarmProfileEntry 2 }

alarmProfileDefaultValue OBJECT-TYPE
    SYNTAX      TrapAlarmSeverity
    MAX-ACCESS  read-only
    STATUS      current
    DESCRIPTION   "This object identifies the default severity of this alarm."
    ::=  { alarmProfileEntry 3 }


chassisCreation NOTIFICATION-TYPE 
    OBJECTS     { entityClass,
                  neEventLogTimeStamp,
                  neEventLogIdentityTranslation
                } 
    STATUS      current
    DESCRIPTION   "This trap is sent every time a chassis is created. N containers
         or other sub-entities in the chassis are reported created by this trap,
         the NMS must read these data. The trap is sent when all the sub-entities
         are present in the entity just created.
         Note: not sent for insertion of NCU chassis, but this is instead
         represented by a coldStart trap."
    ::=  { trapMibPrefix 2 }

chassisDeletion NOTIFICATION-TYPE 
    OBJECTS     { entityClass,
                  neEventLogTimeStamp,
                  neEventLogIdentityTranslation
                } 
    STATUS      current
    DESCRIPTION   "This trap is sent every time a chassis is deleted. The
         sub-entities (containers, modules, etc.) are not reported deleted.
         Note: cannot be reported when the NCU chassis is removed or fails.
        "
    ::=  { trapMibPrefix 3 }

entityCreation NOTIFICATION-TYPE 
    OBJECTS     { entityContainedIn,
                  entityClass,
                  neEventLogTimeStamp,
                  neEventLogIdentityTranslation
                } 
    STATUS      current
    DESCRIPTION   "This trap is sent every time an entity is created. No containers
         or other sub-entities in the chassis are reported created by this trap,
         the NMS must read these data."
    ::=  { trapMibPrefix 4 }

entityDeletion NOTIFICATION-TYPE 
    OBJECTS     { entityClass,
                  neEventLogTimeStamp,
                  neEventLogIdentityTranslation
                } 
    STATUS      current
    DESCRIPTION   "This trap is sent every time an entity is deleted. The
         sub-entities (containers, modules, etc.) are not reported deleted.
        "
    ::=  { trapMibPrefix 5 }

neTrapsinkObjectCreation NOTIFICATION-TYPE 
    OBJECTS     { neTrapsinkAddress,
                  neEventLogTimeStamp,
                  neEventLogIdentityTranslation
                } 
    STATUS      current
    DESCRIPTION   "This trap is sent every time a trapsink is created."
    ::=  { trapMibPrefix 6 }

neTrapsinkObjectDeletion NOTIFICATION-TYPE 
    OBJECTS     { neTrapsinkAddress,
                  neEventLogTimeStamp,
                  neEventLogIdentityTranslation
                } 
    STATUS      current
    DESCRIPTION   "This trap is sent every time a trapsink is deleted.."
    ::=  { trapMibPrefix 7 }

equipmentInserted NOTIFICATION-TYPE 
    OBJECTS     { entityClass,
                  neEventLogTimeStamp,
                  neEventLogIdentityTranslation
                } 
    STATUS      current
    DESCRIPTION   "This trap is sent every time an equipment is inserted."
    ::=  { trapMibPrefix 8 }

equipmentRemoved NOTIFICATION-TYPE 
    OBJECTS     { entityClass,
                  neEventLogTimeStamp,
                  neEventLogIdentityTranslation
                } 
    STATUS      current
    DESCRIPTION   "This trap is sent every time an equipment is removed."
    ::=  { trapMibPrefix 9 }

crossConnectionCreation NOTIFICATION-TYPE 
    OBJECTS     { crsConnDeployProvConn,
                  neEventLogTimeStamp,
                  neEventLogIdentityTranslation
                } 
    STATUS      current
    DESCRIPTION   "This trap is sent every time an cross connection is created."
    ::=  { trapMibPrefix 10 }

crossConnectionDeletion NOTIFICATION-TYPE 
    OBJECTS     { crsConnDeployProvFrom,
                  neEventLogTimeStamp,
                  neEventLogIdentityTranslation
                } 
    STATUS      current
    DESCRIPTION   "This trap is sent every time an cross connection is deleted."
    ::=  { trapMibPrefix 11 }

neStateChange NOTIFICATION-TYPE 
    OBJECTS     { neEventLogTimeStamp,
                  neEventLogIdentityTranslation
                } 
    STATUS      current
    DESCRIPTION   "This trap is sent when an network element state is changed.
         Only one state is present in each trap. The first varbind
         will contain one of the following scalar entries:
         neSwUpgradeState (ADVA Common MIB)."
    ::=  { trapMibPrefix 20 }

entityStateChange NOTIFICATION-TYPE 
    OBJECTS     { neEventLogTimeStamp,
                  neEventLogIdentityTranslation
                } 
    STATUS      current
    DESCRIPTION   "This trap is sent when an entity state is changed.
         Only one state is present in each trap. The first varbind
         will contain one of the following table entries:
         entityStateAdmin,
         entityStateOper,
         entitySecondaryStates."
    ::=  { trapMibPrefix 21 }

neSysTypeChanged NOTIFICATION-TYPE 
    OBJECTS     { neSysType,
                  neEventLogTimeStamp
                } 
    STATUS      current
    DESCRIPTION   "This trap is sent when changes are detected in the nodeTrafficConfig.."
    ::=  { trapMibPrefix 22 }

neAttributeValueChange NOTIFICATION-TYPE 
    OBJECTS     { neEventLogTimeStamp,
                  neEventLogIdentityTranslation
                } 
    STATUS      current
    DESCRIPTION   "This trap is sent when an attribute related to the
         Network Element is changed.
         One attribute is present in each trap. The first varbind
         contains one of the following scalar or table entries:
         sysLocation (RFC 1213)
         sysContact (RFC 1213)
         
         neTrapsinkTable (ADVAMIB):
         neTrapsinkCommunity
         neSwUpgradeRequest (ADVAMIB)
         neSwUpgradeServerAddress (ADVAMIB)
         neSwUpgradeServerLogin (ADVAMIB)
         neSwUpgradeServerPasswd (ADVAMIB)
         neSwUpgradeServerDirectory (ADVAMIB)
         neSwUpgradeFileName (ADVAMIB)."
    ::=  { trapMibPrefix 30 }

facilityAttributeValueChange NOTIFICATION-TYPE 
    OBJECTS     { neEventLogTimeStamp,
                  neEventLogIdentityTranslation
                } 
    STATUS      current
    DESCRIPTION   "This trap is sent when an attribute related to a facility is changed.
         One attribute is present in each trap. The first varbind
         contains one of the following table entries:
         gfpVchConfigTable,
         gfpVchConfigCir,"
    ::=  { trapMibPrefix 31 }

loopbackChange NOTIFICATION-TYPE 
    OBJECTS     { entityIndex,
                  interfaceConfigLoopConfig,
                  neEventLogTimeStamp,
                  neEventLogIdentityTranslation
                } 
    STATUS      current
    DESCRIPTION   "This trap is sent when loopback is changed."
    ::=  { trapMibPrefix 32 }

snmpAgentStateChanged NOTIFICATION-TYPE 
    OBJECTS     { snmpProxyEntrySingleTargetOutNodeAgentStatus,
                  neEventLogTimeStamp
                } 
    STATUS      current
    DESCRIPTION   "This trap is send when remote agent is unavailable."
    ::=  { trapMibPrefix 33 }

snmpAgentSynchronizationStageChanged NOTIFICATION-TYPE 
    OBJECTS     { snmpProxyServerSynchroStage,
                  neEventLogTimeStamp
                } 
    STATUS      current
    DESCRIPTION   "This trap is send when remote agent is unavailable."
    ::=  { trapMibPrefix 34 }

coldStartAgentReconfigured NOTIFICATION-TYPE 
    OBJECTS     { neEventLogTimeStamp
                } 
    STATUS      current
    DESCRIPTION   "This trap is send after a cold start to inditcate that reconfiguration
         required SNMP agent to be restart. Pair of traps coldStart and
         coldStartAgentReconfigured indicates that a reconfiguration occured.
        "
    ::=  { trapMibPrefix 35 }

dcnOspfAreaCreation NOTIFICATION-TYPE 
    OBJECTS     { dcnOspfAreaId,
                  dcnOspfAreaType,
                  neEventLogTimeStamp,
                  neEventLogIdentityTranslation
                } 
    STATUS      current
    DESCRIPTION   "This trap indicates creation of an OSPF Area entity."
    ::=  { trapMibPrefix 36 }

dcnOspfAreaDeletion NOTIFICATION-TYPE 
    OBJECTS     { dcnOspfAreaId,
                  dcnOspfAreaType,
                  neEventLogTimeStamp,
                  neEventLogIdentityTranslation
                } 
    STATUS      current
    DESCRIPTION   "This trap indicates deletion of an OSPF Area entity."
    ::=  { trapMibPrefix 37 }

dcnOspfAreaPropertiesChange NOTIFICATION-TYPE 
    OBJECTS     { dcnOspfAreaId,
                  dcnOspfAreaType,
                  dcnOspfAreaStubDefaultMetric,
                  neEventLogTimeStamp,
                  neEventLogIdentityTranslation
                } 
    STATUS      current
    DESCRIPTION   "This trap indicates modification of some OSPF Area entity properties."
    ::=  { trapMibPrefix 38 }

timeNtpAttributeValueChange NOTIFICATION-TYPE 
    STATUS      current
    DESCRIPTION   "Some attributes of TIME entity changed. Modified attributes are attached as varbinds."
    ::=  { trapMibPrefix 39 }

ntpSrvAttributeValueChange NOTIFICATION-TYPE 
    STATUS      current
    DESCRIPTION   "Some attributes of NTP Server entity changed. Modified attributes are attached as varbinds."
    ::=  { trapMibPrefix 40 }

ntpSrvObjectChange NOTIFICATION-TYPE 
    STATUS      current
    DESCRIPTION   "NTP server state has been changed."
    ::=  { trapMibPrefix 41 }

ntpSrvCreation NOTIFICATION-TYPE 
    STATUS      current
    DESCRIPTION   "NTP server has been created."
    ::=  { trapMibPrefix 42 }

ntpSrvDeletion NOTIFICATION-TYPE 
    STATUS      current
    DESCRIPTION   "NTP server has been removed."
    ::=  { trapMibPrefix 43 }

knownHostCreation NOTIFICATION-TYPE 
    OBJECTS     { knownHostIP,
                  knownHostKeyEncryptAlgorithm,
                  neEventLogTimeStamp,
                  neEventLogIdentityTranslation
                } 
    STATUS      current
    DESCRIPTION   "This trap indicates creation of an entry in knownHostTable."
    ::=  { trapMibPrefix 44 }

knownHostDeletion NOTIFICATION-TYPE 
    OBJECTS     { knownHostIP,
                  knownHostKeyEncryptAlgorithm,
                  neEventLogTimeStamp,
                  neEventLogIdentityTranslation
                } 
    STATUS      current
    DESCRIPTION   "This trap indicates deletion of an entry in knownHostTable."
    ::=  { trapMibPrefix 45 }

radiusSrvObjectChange NOTIFICATION-TYPE 
    STATUS      current
    DESCRIPTION   "Radius server state has been changed."
    ::=  { trapMibPrefix 46 }

radiusSrvCreation NOTIFICATION-TYPE 
    OBJECTS     { remoteServerPriority,
                  neEventLogTimeStamp,
                  neEventLogIdentityTranslation
                } 
    STATUS      current
    DESCRIPTION   "Radius server has been created."
    ::=  { trapMibPrefix 47 }

radiusSrvDeletion NOTIFICATION-TYPE 
    OBJECTS     { remoteServerPriority,
                  neEventLogTimeStamp,
                  neEventLogIdentityTranslation
                } 
    STATUS      current
    DESCRIPTION   "Radius server has been removed."
    ::=  { trapMibPrefix 48 }

radiusSrvAttributeValueChange NOTIFICATION-TYPE 
    STATUS      current
    DESCRIPTION   "Some attributes of NTP Server entity changed. Modified attributes are attached as varbinds."
    ::=  { trapMibPrefix 49 }

ptpEntityCreation NOTIFICATION-TYPE 
    OBJECTS     { ptpEntityContainedIn,
                  ptpEntityClass,
                  neEventLogTimeStamp,
                  neEventLogIdentityTranslation
                } 
    STATUS      current
    DESCRIPTION   "This trap is sent every time PTP entity is created. No containers
         or other sub-entities in the chassis are reported created by this trap,
         the NMS must read these data."
    ::=  { trapMibPrefix 50 }

ptpEntityDeletion NOTIFICATION-TYPE 
    OBJECTS     { ptpEntityClass,
                  neEventLogTimeStamp,
                  neEventLogIdentityTranslation
                } 
    STATUS      current
    DESCRIPTION   "This trap is sent every time PTP entity is deleted. The
         sub-entities (containers, modules, etc.) are not reported deleted.
        "
    ::=  { trapMibPrefix 51 }

entityObjectChange NOTIFICATION-TYPE 
    OBJECTS     { entityIndex,
                  neEventLogTimeStamp,
                  neEventLogIdentityTranslation
                } 
    STATUS      current
    DESCRIPTION   "This trap is sent some object is changed."
    ::=  { trapMibPrefix 100 }

crsConnObjectChange NOTIFICATION-TYPE 
    OBJECTS     { crsConnDeployProvFrom,
                  neEventLogTimeStamp,
                  neEventLogIdentityTranslation
                } 
    STATUS      current
    DESCRIPTION   "This trap is sent some cross connect object is changed."
    ::=  { trapMibPrefix 101 }

authenticationNotification NOTIFICATION-TYPE 
    OBJECTS     { authTrapSrcIp,
                  authTrapLctIp,
                  authTrapStatus,
                  authTrapSessionId,
                  authTrapProtocol,
                  authTrapPort,
                  authTrapUserName,
                  authTrapRadUserName,
                  neEventLogTimeStamp,
                  neEventLogIdentityTranslation
                } 
    STATUS      current
    DESCRIPTION   "This trap is sent when authentication attempt happens."
    ::=  { trapMibPrefix 102 }

authenticationNotificationSummary NOTIFICATION-TYPE 
    OBJECTS     { authTrapProtocol,
                  authTrapSuccessfulAuthCount,
                  authTrapUnsuccessfulAuthCount,
                  neEventLogTimeStamp
                } 
    STATUS      current
    DESCRIPTION   "This trap is sent when authentication attempt happens more often
         than 5 times within 10 seconds.
        "
    ::=  { trapMibPrefix 103 }

wdmTunnelResultNotification NOTIFICATION-TYPE 
    OBJECTS     { entityIndex,
                  neEventLogTimeStamp,
                  neEventLogIdentityTranslation,
                  tunnelWdmDataErrorCodeMajor,
                  tunnelWdmDataErrorCodeMinor,
                  tunnelWdmDataErrorCategory,
                  tunnelWdmDataErrorIp,
                  tunnelWdmDataErrorTid,
                  tunnelWdmDataSpecificErrorMessage
                } 
    STATUS      current
    DESCRIPTION   "Trap for the result for WDM Tunnel creation or modification."
    ::=  { trapMibPrefix 110 }

ethTunnelResultNotification NOTIFICATION-TYPE 
    OBJECTS     { entityIndex,
                  neEventLogTimeStamp,
                  neEventLogIdentityTranslation,
                  tunnelEthDataErrorCodeMajor,
                  tunnelEthDataErrorCodeMinor,
                  tunnelEthDataErrorCategory,
                  tunnelEthDataErrorIp,
                  tunnelEthDataErrorTid,
                  tunnelEthDataSpecificErrorMessage
                } 
    STATUS      current
    DESCRIPTION   "Trap for the result for ETH Tunnel creation or modification."
    ::=  { trapMibPrefix 111 }

ptpEntityObjectChange NOTIFICATION-TYPE 
    OBJECTS     { ptpEntityIndex,
                  neEventLogTimeStamp,
                  neEventLogIdentityTranslation
                } 
    STATUS      current
    DESCRIPTION   "This trap is sent when some object is changed at PTP entity."
    ::=  { trapMibPrefix 112 }

alarmInputTIF NOTIFICATION-TYPE 
    OBJECTS     { currentConditionSeverity,
                  currentConditionAffect,
                  tifiConfigTifAlarmType,
                  tifiConfigTifAlarmMessage,
                  neEventLogTimeStamp,
                  neEventLogIdentityTranslation
                } 
    STATUS      current
    DESCRIPTION   "Telemetry interface alarm."
    ::=  { trapMibPrefix 1215 }

alarmPtpEntityOosDisabled NOTIFICATION-TYPE 
    STATUS      current
    DESCRIPTION   "Non-Specific Disablement of Management Access"
    ::=  { trapMibPrefix 1452 }

ptpEntityOosManagement NOTIFICATION-TYPE 
    STATUS      current
    DESCRIPTION   "Alarms are logged but not notified, service affecting changes are permitted"
    ::=  { trapMibPrefix 1453 }

ptpEntityOosMaintenance NOTIFICATION-TYPE 
    STATUS      current
    DESCRIPTION   "Alarms are logged but not notified, service affecting changes and operations are permitted"
    ::=  { trapMibPrefix 1454 }

ptpEntityOosAins NOTIFICATION-TYPE 
    STATUS      current
    DESCRIPTION   "Automatic In Service"
    ::=  { trapMibPrefix 1455 }

transientSoftwareActivation NOTIFICATION-TYPE 
    OBJECTS     { entityIndex,
                  neRestoreConfig
                } 
    STATUS      current
    DESCRIPTION   "Reboot starts immediately."
    ::=  { trapMibPrefix 3036 }

transientSoftwareRestart NOTIFICATION-TYPE 
    OBJECTS     { entityIndex,
                  neRestoreConfig
                } 
    STATUS      current
    DESCRIPTION   "SW reboot without SW update"
    ::=  { trapMibPrefix 3228 }

transientCnxSegmentAdded NOTIFICATION-TYPE 
    OBJECTS     { controlPlaneWdmEntityIndex,
                  connectionWdmDataTunnelId,
                  connectionWdmDataFromAid,
                  connectionWdmDataFromAidString
                } 
    STATUS      current
    DESCRIPTION   "ControlPlane Connection Segment Added"
    ::=  { trapMibPrefix 3229 }

transientCnxSegmentRemoved NOTIFICATION-TYPE 
    OBJECTS     { controlPlaneWdmEntityIndex,
                  connectionWdmDataTunnelId
                } 
    STATUS      current
    DESCRIPTION   "ControlPlane Connection Segment Removed"
    ::=  { trapMibPrefix 3230 }

alarmThirdPartyPlug NOTIFICATION-TYPE 
    OBJECTS     { currentConditionSeverity,currentConditionAffect,neEventLogTimeStamp,neEventLogIdentityTranslation } 
    STATUS      current
    DESCRIPTION   "Equipment Accepted by Customer with Voided Warranty"
    ::=  { trapMibPrefix 1001 }


alarmFacilityLoopback NOTIFICATION-TYPE 
    OBJECTS     { currentConditionSeverity,currentConditionAffect,neEventLogTimeStamp,neEventLogIdentityTranslation } 
    STATUS      current
    DESCRIPTION   "External (Line) Loopback on Interface"
    ::=  { trapMibPrefix 1002 }


alarmTerminalLoopback NOTIFICATION-TYPE 
    OBJECTS     { currentConditionSeverity,currentConditionAffect,neEventLogTimeStamp,neEventLogIdentityTranslation } 
    STATUS      current
    DESCRIPTION   "Inward Loopback on Interface"
    ::=  { trapMibPrefix 1003 }


alarmFacilityForcedOn NOTIFICATION-TYPE 
    OBJECTS     { currentConditionSeverity,currentConditionAffect,neEventLogTimeStamp,neEventLogIdentityTranslation } 
    STATUS      current
    DESCRIPTION   "Laser or Switch forced ON"
    ::=  { trapMibPrefix 1004 }


alarmOosDisabled NOTIFICATION-TYPE 
    OBJECTS     { currentConditionSeverity,currentConditionAffect,neEventLogTimeStamp,neEventLogIdentityTranslation } 
    STATUS      current
    DESCRIPTION   "Non-Specific Disablement of Management Access"
    ::=  { trapMibPrefix 1005 }


alarmReceiverDisabled NOTIFICATION-TYPE 
    OBJECTS     { currentConditionSeverity,currentConditionAffect,neEventLogTimeStamp,neEventLogIdentityTranslation } 
    STATUS      current
    DESCRIPTION   "Disablement of Management Access with Receiver OFF"
    ::=  { trapMibPrefix 1006 }


alarmTransmitterDisabledOff NOTIFICATION-TYPE 
    OBJECTS     { currentConditionSeverity,currentConditionAffect,neEventLogTimeStamp,neEventLogIdentityTranslation } 
    STATUS      current
    DESCRIPTION   "Disablement of Management Access with Transmitter OFF"
    ::=  { trapMibPrefix 1007 }


alarmTransmittedDisabledIdle NOTIFICATION-TYPE 
    OBJECTS     { currentConditionSeverity,currentConditionAffect,neEventLogTimeStamp,neEventLogIdentityTranslation } 
    STATUS      current
    DESCRIPTION   "Disablement of Management Access with Transmitter IDLE"
    ::=  { trapMibPrefix 1008 }


alarmTransmitterDisabledAis NOTIFICATION-TYPE 
    OBJECTS     { currentConditionSeverity,currentConditionAffect,neEventLogTimeStamp,neEventLogIdentityTranslation } 
    STATUS      current
    DESCRIPTION   "Disablement of Management Access with Transmitter Sending Maintenance Signal AIS"
    ::=  { trapMibPrefix 1009 }


alarmTransmitterDisabledEpc NOTIFICATION-TYPE 
    OBJECTS     { currentConditionSeverity,currentConditionAffect,neEventLogTimeStamp,neEventLogIdentityTranslation } 
    STATUS      current
    DESCRIPTION   "Disablement of Management Access with Transmitter Sending Maintenance Signal EPC"
    ::=  { trapMibPrefix 1010 }


alarmOosManagement NOTIFICATION-TYPE 
    OBJECTS     { currentConditionSeverity,currentConditionAffect,neEventLogTimeStamp,neEventLogIdentityTranslation } 
    STATUS      current
    DESCRIPTION   "Alarms are logged but not notified, service affecting changes are permitted"
    ::=  { trapMibPrefix 1011 }


alarmOosMaintenance NOTIFICATION-TYPE 
    OBJECTS     { currentConditionSeverity,currentConditionAffect,neEventLogTimeStamp,neEventLogIdentityTranslation } 
    STATUS      current
    DESCRIPTION   "Alarms are logged but not notified, service affecting changes and operations are permitted"
    ::=  { trapMibPrefix 1012 }


alarmOosAins NOTIFICATION-TYPE 
    OBJECTS     { currentConditionSeverity,currentConditionAffect,neEventLogTimeStamp,neEventLogIdentityTranslation } 
    STATUS      current
    DESCRIPTION   "Automatic In Service"
    ::=  { trapMibPrefix 1013 }


alarmDcnCommunicationFail NOTIFICATION-TYPE 
    OBJECTS     { currentConditionSeverity,currentConditionAffect,neEventLogTimeStamp,neEventLogIdentityTranslation } 
    STATUS      current
    DESCRIPTION   "The connection to the shelf is dysfunctional or the connection to the module within the shelf is dysfunctional"
    ::=  { trapMibPrefix 1014 }


alarmRemoved NOTIFICATION-TYPE 
    OBJECTS     { currentConditionSeverity,currentConditionAffect,neEventLogTimeStamp,neEventLogIdentityTranslation } 
    STATUS      current
    DESCRIPTION   "The equipment has been removed / unplugged / disconnected.
         This condition has been determined to be more probable than that below,
         which is also supersedes."
    ::=  { trapMibPrefix 1015 }


alarmMismatch NOTIFICATION-TYPE 
    OBJECTS     { currentConditionSeverity,currentConditionAffect,neEventLogTimeStamp,neEventLogIdentityTranslation } 
    STATUS      current
    DESCRIPTION   "Non-Specific Mismatch. Equipment Not Match Provisioned Hardware"
    ::=  { trapMibPrefix 1016 }


alarmEquipmentNotAccepted NOTIFICATION-TYPE 
    OBJECTS     { currentConditionSeverity,currentConditionAffect,neEventLogTimeStamp,neEventLogIdentityTranslation } 
    STATUS      current
    DESCRIPTION   "The Plug cannot support any of the services provisionable on this card OR the Plug is unrecognizable"
    ::=  { trapMibPrefix 1017 }


alarmFacilityDataRateNotSupported NOTIFICATION-TYPE 
    OBJECTS     { currentConditionSeverity,currentConditionAffect,neEventLogTimeStamp,neEventLogIdentityTranslation } 
    STATUS      current
    DESCRIPTION   "The Plug inserted cannot support the actual service provisioned on this card: this is superseded by the above"
    ::=  { trapMibPrefix 1018 }


alarmEquipmentNotSupportedByPhysicalLayer NOTIFICATION-TYPE 
    OBJECTS     { currentConditionSeverity,currentConditionAffect,neEventLogTimeStamp,neEventLogIdentityTranslation } 
    STATUS      current
    DESCRIPTION   "Equipment not Support Configured Physical Layer"
    ::=  { trapMibPrefix 1019 }


alarmEquipmentNotApproved NOTIFICATION-TYPE 
    OBJECTS     { currentConditionSeverity,currentConditionAffect,neEventLogTimeStamp,neEventLogIdentityTranslation } 
    STATUS      current
    DESCRIPTION   "The Plug is recognizable to the extent that service support can
         be determined, but is not approved: this is susperseded by SGEO-RATE"
    ::=  { trapMibPrefix 1020 }


alarmEquipmentMismatch NOTIFICATION-TYPE 
    OBJECTS     { currentConditionSeverity,currentConditionAffect,neEventLogTimeStamp,neEventLogIdentityTranslation } 
    STATUS      current
    DESCRIPTION   "The Plug is approved but does not match the specific Plug provisioned: this is superseded by MEA-APPROVE"
    ::=  { trapMibPrefix 1021 }


alarmFuseAlarm1 NOTIFICATION-TYPE 
    OBJECTS     { currentConditionSeverity,currentConditionAffect,neEventLogTimeStamp,neEventLogIdentityTranslation } 
    STATUS      deprecated
    DESCRIPTION   ""
    ::=  { trapMibPrefix 1022 }


alarmFuseAlarm2 NOTIFICATION-TYPE 
    OBJECTS     { currentConditionSeverity,currentConditionAffect,neEventLogTimeStamp,neEventLogIdentityTranslation } 
    STATUS      deprecated
    DESCRIPTION   ""
    ::=  { trapMibPrefix 1023 }


alarmFanAlarm NOTIFICATION-TYPE 
    OBJECTS     { currentConditionSeverity,currentConditionAffect,neEventLogTimeStamp,neEventLogIdentityTranslation } 
    STATUS      deprecated
    DESCRIPTION   "Fan has failed"
    ::=  { trapMibPrefix 1024 }


alarmFanUnitAlarm NOTIFICATION-TYPE 
    OBJECTS     { currentConditionSeverity,currentConditionAffect,neEventLogTimeStamp,neEventLogIdentityTranslation } 
    STATUS      deprecated
    DESCRIPTION   "More than one FAN has failed within the FANUNIT"
    ::=  { trapMibPrefix 1025 }


alarmPowerMissing NOTIFICATION-TYPE 
    OBJECTS     { currentConditionSeverity,currentConditionAffect,neEventLogTimeStamp,neEventLogIdentityTranslation } 
    STATUS      current
    DESCRIPTION   "Power Unit Missing"
    ::=  { trapMibPrefix 1026 }


alarmPowerFailure NOTIFICATION-TYPE 
    OBJECTS     { currentConditionSeverity,currentConditionAffect,neEventLogTimeStamp,neEventLogIdentityTranslation } 
    STATUS      deprecated
    DESCRIPTION   "Power Unit Failure"
    ::=  { trapMibPrefix 1027 }


alarmVoltageTooLow NOTIFICATION-TYPE 
    OBJECTS     { currentConditionSeverity,currentConditionAffect,neEventLogTimeStamp,neEventLogIdentityTranslation } 
    STATUS      deprecated
    DESCRIPTION   "Voltage Low Threshold Exceeded"
    ::=  { trapMibPrefix 1028 }


alarmVoltageTooHigh NOTIFICATION-TYPE 
    OBJECTS     { currentConditionSeverity,currentConditionAffect,neEventLogTimeStamp,neEventLogIdentityTranslation } 
    STATUS      deprecated
    DESCRIPTION   "Voltage High Threshold Exceeded"
    ::=  { trapMibPrefix 1029 }


alarmTemperatureTooLow NOTIFICATION-TYPE 
    OBJECTS     { currentConditionSeverity,currentConditionAffect,neEventLogTimeStamp,neEventLogIdentityTranslation } 
    STATUS      current
    DESCRIPTION   "Temperature Fixed Low Thershold Exceeded"
    ::=  { trapMibPrefix 1030 }


alarmTemperatureTooHigh NOTIFICATION-TYPE 
    OBJECTS     { currentConditionSeverity,currentConditionAffect,neEventLogTimeStamp,neEventLogIdentityTranslation } 
    STATUS      current
    DESCRIPTION   "Temperature Fixed High Threshold Exceeded"
    ::=  { trapMibPrefix 1031 }


alarmReceiverFailure NOTIFICATION-TYPE 
    OBJECTS     { currentConditionSeverity,currentConditionAffect,neEventLogTimeStamp,neEventLogIdentityTranslation } 
    STATUS      deprecated
    DESCRIPTION   "Rx Failure"
    ::=  { trapMibPrefix 1032 }


alarmOpticalInputPowerReceiverFailure NOTIFICATION-TYPE 
    OBJECTS     { currentConditionSeverity,currentConditionAffect,neEventLogTimeStamp,neEventLogIdentityTranslation } 
    STATUS      deprecated
    DESCRIPTION   "???"
    ::=  { trapMibPrefix 1033 }


alarmLossOfSignal NOTIFICATION-TYPE 
    OBJECTS     { currentConditionSeverity,currentConditionAffect,neEventLogTimeStamp,neEventLogIdentityTranslation } 
    STATUS      current
    DESCRIPTION   "Loss of Signal"
    ::=  { trapMibPrefix 1034 }


alarmIdleSignalReceived NOTIFICATION-TYPE 
    OBJECTS     { currentConditionSeverity,currentConditionAffect,neEventLogTimeStamp,neEventLogIdentityTranslation } 
    STATUS      deprecated
    DESCRIPTION   ""
    ::=  { trapMibPrefix 1035 }


alarmLossOfLinkPulse NOTIFICATION-TYPE 
    OBJECTS     { currentConditionSeverity,currentConditionAffect,neEventLogTimeStamp,neEventLogIdentityTranslation } 
    STATUS      deprecated
    DESCRIPTION   "Loss of Link Pulse"
    ::=  { trapMibPrefix 1036 }


alarmLossOfReceiverClockRecovery NOTIFICATION-TYPE 
    OBJECTS     { currentConditionSeverity,currentConditionAffect,neEventLogTimeStamp,neEventLogIdentityTranslation } 
    STATUS      current
    DESCRIPTION   "Rx Clock Sync Failure"
    ::=  { trapMibPrefix 1037 }


alarmElasticStoreOverflowReceiver NOTIFICATION-TYPE 
    OBJECTS     { currentConditionSeverity,currentConditionAffect,neEventLogTimeStamp,neEventLogIdentityTranslation } 
    STATUS      deprecated
    DESCRIPTION   "Rx Elast. Store Overflow"
    ::=  { trapMibPrefix 1038 }


alarmLossOfTransmitterClockRecovery NOTIFICATION-TYPE 
    OBJECTS     { currentConditionSeverity,currentConditionAffect,neEventLogTimeStamp,neEventLogIdentityTranslation } 
    STATUS      deprecated
    DESCRIPTION   "Tx Clock Sync Failure"
    ::=  { trapMibPrefix 1039 }


alarmLaserFailure NOTIFICATION-TYPE 
    OBJECTS     { currentConditionSeverity,currentConditionAffect,neEventLogTimeStamp,neEventLogIdentityTranslation } 
    STATUS      current
    DESCRIPTION   "Optical Power Transmitted Failure: Laser Failure"
    ::=  { trapMibPrefix 1040 }


alarmSwitchFailed NOTIFICATION-TYPE 
    OBJECTS     { currentConditionSeverity,currentConditionAffect,neEventLogTimeStamp,neEventLogIdentityTranslation } 
    STATUS      current
    DESCRIPTION   "Failure to Respond to Switch/Bridge Request within 50 ms"
    ::=  { trapMibPrefix 1041 }


alarmElasticStoreOverflowTransmitter NOTIFICATION-TYPE 
    OBJECTS     { currentConditionSeverity,currentConditionAffect,neEventLogTimeStamp,neEventLogIdentityTranslation } 
    STATUS      deprecated
    DESCRIPTION   "Tx Elast. Store Overflow"
    ::=  { trapMibPrefix 1042 }


alarmAutoShutdownLaserOffDueToErrFwd NOTIFICATION-TYPE 
    OBJECTS     { currentConditionSeverity,currentConditionAffect,neEventLogTimeStamp,neEventLogIdentityTranslation } 
    STATUS      current
    DESCRIPTION   "Forward ALS"
    ::=  { trapMibPrefix 1043 }


alarmAutoShutdown NOTIFICATION-TYPE 
    OBJECTS     { currentConditionSeverity,currentConditionAffect,neEventLogTimeStamp,neEventLogIdentityTranslation } 
    STATUS      deprecated
    DESCRIPTION   "Automatic Shutdown with Transmitter sending Connection Detection Pulses"
    ::=  { trapMibPrefix 1044 }


alarmAutoShutdownAls NOTIFICATION-TYPE 
    OBJECTS     { currentConditionSeverity,currentConditionAffect,neEventLogTimeStamp,neEventLogIdentityTranslation } 
    STATUS      current
    DESCRIPTION   "Auto Shutdown (ALS)"
    ::=  { trapMibPrefix 1045 }


alarmAutoShutdownSendingIdle NOTIFICATION-TYPE 
    OBJECTS     { currentConditionSeverity,currentConditionAffect,neEventLogTimeStamp,neEventLogIdentityTranslation } 
    STATUS      deprecated
    DESCRIPTION   "Auto Shutdown (IDLE)"
    ::=  { trapMibPrefix 1046 }


alarmThermoElectricCoolerEndOfLife NOTIFICATION-TYPE 
    OBJECTS     { currentConditionSeverity,currentConditionAffect,neEventLogTimeStamp,neEventLogIdentityTranslation } 
    STATUS      current
    DESCRIPTION   "TEC End of Life"
    ::=  { trapMibPrefix 1047 }


alarmOpticalInputPwrReceivedTooLow NOTIFICATION-TYPE 
    OBJECTS     { currentConditionSeverity,currentConditionAffect,neEventLogTimeStamp,neEventLogIdentityTranslation } 
    STATUS      current
    DESCRIPTION   "Optical Power Receive Low Threshold Exceeded"
    ::=  { trapMibPrefix 1048 }


alarmOpticalInputPwrReceivedTooHigh NOTIFICATION-TYPE 
    OBJECTS     { currentConditionSeverity,currentConditionAffect,neEventLogTimeStamp,neEventLogIdentityTranslation } 
    STATUS      current
    DESCRIPTION   "Optical Power Receive High Threshold Exceeded"
    ::=  { trapMibPrefix 1049 }


alarmLaserTemperatureTooHigh NOTIFICATION-TYPE 
    OBJECTS     { currentConditionSeverity,currentConditionAffect,neEventLogTimeStamp,neEventLogIdentityTranslation } 
    STATUS      current
    DESCRIPTION   "TCA - Fixed high threshold of Laser Temperature has been crossed."
    ::=  { trapMibPrefix 1050 }


alarmLaserTemperatureTooLow NOTIFICATION-TYPE 
    OBJECTS     { currentConditionSeverity,currentConditionAffect,neEventLogTimeStamp,neEventLogIdentityTranslation } 
    STATUS      current
    DESCRIPTION   "TCA - Fixed low threshold of Laser Temperature has been crossed."
    ::=  { trapMibPrefix 1051 }


alarmOpticalOutputPowerTransmittedTooLow NOTIFICATION-TYPE 
    OBJECTS     { currentConditionSeverity,currentConditionAffect,neEventLogTimeStamp,neEventLogIdentityTranslation } 
    STATUS      current
    DESCRIPTION   "Optical Power Transmit (output) Low Threshold Exceeded"
    ::=  { trapMibPrefix 1052 }


alarmOpticalOutputPowerTransmittedTooHigh NOTIFICATION-TYPE 
    OBJECTS     { currentConditionSeverity,currentConditionAffect,neEventLogTimeStamp,neEventLogIdentityTranslation } 
    STATUS      current
    DESCRIPTION   "Optical Power Transmitted (output) High Threshold Exceeded"
    ::=  { trapMibPrefix 1053 }


alarmLaserBiasCurrentNormalizedtooHigh NOTIFICATION-TYPE 
    OBJECTS     { currentConditionSeverity,currentConditionAffect,neEventLogTimeStamp,neEventLogIdentityTranslation } 
    STATUS      current
    DESCRIPTION   "TCA - Laser Bias Current Level too High. Fixed threshold has been crossed."
    ::=  { trapMibPrefix 1054 }


alarmLossOfSignalTransmitter NOTIFICATION-TYPE 
    OBJECTS     { currentConditionSeverity,currentConditionAffect,neEventLogTimeStamp,neEventLogIdentityTranslation } 
    STATUS      current
    DESCRIPTION   "A Loss of signal has been detected on the FAR-END facility."
    ::=  { trapMibPrefix 1055 }


alarmAttOnReceiverFiberLowerThanMonitor NOTIFICATION-TYPE 
    OBJECTS     { currentConditionSeverity,currentConditionAffect,neEventLogTimeStamp,neEventLogIdentityTranslation } 
    STATUS      current
    DESCRIPTION   "Attenuation Rx Too Low"
    ::=  { trapMibPrefix 1056 }


alarmAttOnReceiverFiberHigherThanMonitor NOTIFICATION-TYPE 
    OBJECTS     { currentConditionSeverity,currentConditionAffect,neEventLogTimeStamp,neEventLogIdentityTranslation } 
    STATUS      current
    DESCRIPTION   "Attenuation Rx Too High"
    ::=  { trapMibPrefix 1057 }


alarmAttOnTransmitterFiberLowerThanMonitor NOTIFICATION-TYPE 
    OBJECTS     { currentConditionSeverity,currentConditionAffect,neEventLogTimeStamp,neEventLogIdentityTranslation } 
    STATUS      current
    DESCRIPTION   "Attenuation Tx Too Low"
    ::=  { trapMibPrefix 1058 }


alarmAttOnTransmitterFiberHigherThanMonitor NOTIFICATION-TYPE 
    OBJECTS     { currentConditionSeverity,currentConditionAffect,neEventLogTimeStamp,neEventLogIdentityTranslation } 
    STATUS      current
    DESCRIPTION   "Attenuation Tx Too High"
    ::=  { trapMibPrefix 1059 }


alarmAutoShutdownSendingAisOtu NOTIFICATION-TYPE 
    OBJECTS     { currentConditionSeverity,currentConditionAffect,neEventLogTimeStamp,neEventLogIdentityTranslation } 
    STATUS      current
    DESCRIPTION   "Auto Shutdown (OTU-AIS)"
    ::=  { trapMibPrefix 1060 }


alarmLossOfFrameOtu NOTIFICATION-TYPE 
    OBJECTS     { currentConditionSeverity,currentConditionAffect,neEventLogTimeStamp,neEventLogIdentityTranslation } 
    STATUS      current
    DESCRIPTION   "OTU LOF"
    ::=  { trapMibPrefix 1061 }


alarmLossOfMultiFrameOtu NOTIFICATION-TYPE 
    OBJECTS     { currentConditionSeverity,currentConditionAffect,neEventLogTimeStamp,neEventLogIdentityTranslation } 
    STATUS      current
    DESCRIPTION   "OTU LOM"
    ::=  { trapMibPrefix 1062 }


alarmAlarmIndicationSignalOtu NOTIFICATION-TYPE 
    OBJECTS     { currentConditionSeverity,currentConditionAffect,neEventLogTimeStamp,neEventLogIdentityTranslation } 
    STATUS      current
    DESCRIPTION   "Alarm Indication Signal OTU Section Monitoring"
    ::=  { trapMibPrefix 1063 }


alarmSignalDegradeOtu NOTIFICATION-TYPE 
    OBJECTS     { currentConditionSeverity,currentConditionAffect,neEventLogTimeStamp,neEventLogIdentityTranslation } 
    STATUS      current
    DESCRIPTION   "OTU Signal Degrade alarm; related to a configurable threshold"
    ::=  { trapMibPrefix 1064 }


alarmBackwardDefectIndicationOtu NOTIFICATION-TYPE 
    OBJECTS     { currentConditionSeverity,currentConditionAffect,neEventLogTimeStamp,neEventLogIdentityTranslation } 
    STATUS      current
    DESCRIPTION   "OTU Backward Defect Indication"
    ::=  { trapMibPrefix 1065 }


alarmAutoShutdownSendingAisOdu NOTIFICATION-TYPE 
    OBJECTS     { currentConditionSeverity,currentConditionAffect,neEventLogTimeStamp,neEventLogIdentityTranslation } 
    STATUS      current
    DESCRIPTION   "Auto Shutdown (ODU-AIS)"
    ::=  { trapMibPrefix 1066 }


alarmLossOfFrameLossOfMultiFrameOdu NOTIFICATION-TYPE 
    OBJECTS     { currentConditionSeverity,currentConditionAffect,neEventLogTimeStamp,neEventLogIdentityTranslation } 
    STATUS      current
    DESCRIPTION   "ODU LOF/LOM"
    ::=  { trapMibPrefix 1067 }


alarmAlarmIndicationSignalOdu NOTIFICATION-TYPE 
    OBJECTS     { currentConditionSeverity,currentConditionAffect,neEventLogTimeStamp,neEventLogIdentityTranslation } 
    STATUS      current
    DESCRIPTION   "Alarm Indication Signal ODU Path Monitoring"
    ::=  { trapMibPrefix 1068 }


alarmOpenConnectionIndicationOdu NOTIFICATION-TYPE 
    OBJECTS     { currentConditionSeverity,currentConditionAffect,neEventLogTimeStamp,neEventLogIdentityTranslation } 
    STATUS      current
    DESCRIPTION   "Open Connection Indication ODU"
    ::=  { trapMibPrefix 1069 }


alarmLockedDefectOdu NOTIFICATION-TYPE 
    OBJECTS     { currentConditionSeverity,currentConditionAffect,neEventLogTimeStamp,neEventLogIdentityTranslation } 
    STATUS      current
    DESCRIPTION   "ODU Locked"
    ::=  { trapMibPrefix 1070 }


alarmSignalDegradeOdu NOTIFICATION-TYPE 
    OBJECTS     { currentConditionSeverity,currentConditionAffect,neEventLogTimeStamp,neEventLogIdentityTranslation } 
    STATUS      current
    DESCRIPTION   "ODU Signal Degrade alarm; Related to a configurable threshold"
    ::=  { trapMibPrefix 1071 }


alarmBackwardDefectIndicationOdu NOTIFICATION-TYPE 
    OBJECTS     { currentConditionSeverity,currentConditionAffect,neEventLogTimeStamp,neEventLogIdentityTranslation } 
    STATUS      current
    DESCRIPTION   "ODU Backward Defect Indication"
    ::=  { trapMibPrefix 1072 }


alarmAlarmIndicationSignalOduTcmA NOTIFICATION-TYPE 
    OBJECTS     { currentConditionSeverity,currentConditionAffect,neEventLogTimeStamp,neEventLogIdentityTranslation } 
    STATUS      current
    DESCRIPTION   "Alarm Indication Signal ODU Tandem Connection Monitoring Instance A"
    ::=  { trapMibPrefix 1073 }


alarmOpenConnectionIndicationOduTcmA NOTIFICATION-TYPE 
    OBJECTS     { currentConditionSeverity,currentConditionAffect,neEventLogTimeStamp,neEventLogIdentityTranslation } 
    STATUS      current
    DESCRIPTION   "Open Connection Indication ODU Tandem Connection Monitoring A"
    ::=  { trapMibPrefix 1074 }


alarmLockedDefectOduTcmA NOTIFICATION-TYPE 
    OBJECTS     { currentConditionSeverity,currentConditionAffect,neEventLogTimeStamp,neEventLogIdentityTranslation } 
    STATUS      current
    DESCRIPTION   "Locked Defect ODU TCM Instance A"
    ::=  { trapMibPrefix 1075 }


alarmLossofTandemConnectionOduTcmA NOTIFICATION-TYPE 
    OBJECTS     { currentConditionSeverity,currentConditionAffect,neEventLogTimeStamp,neEventLogIdentityTranslation } 
    STATUS      current
    DESCRIPTION   "Loss of Tandem Connection ODU Tandem Connection Monitoring Instane A"
    ::=  { trapMibPrefix 1076 }


alarmSignalDegradeOduTcmA NOTIFICATION-TYPE 
    OBJECTS     { currentConditionSeverity,currentConditionAffect,neEventLogTimeStamp,neEventLogIdentityTranslation } 
    STATUS      current
    DESCRIPTION   "Signal Degrade ODU Tandem Connection Monitoring Instance A. Related to a configurable threshold"
    ::=  { trapMibPrefix 1077 }


alarmBackwardDefectIndicationOduTcmA NOTIFICATION-TYPE 
    OBJECTS     { currentConditionSeverity,currentConditionAffect,neEventLogTimeStamp,neEventLogIdentityTranslation } 
    STATUS      current
    DESCRIPTION   "ODU Tandem Connection Monitoring A Backward Defect Indication"
    ::=  { trapMibPrefix 1078 }


alarmPayloadMismatchOPU NOTIFICATION-TYPE 
    OBJECTS     { currentConditionSeverity,currentConditionAffect,neEventLogTimeStamp,neEventLogIdentityTranslation } 
    STATUS      current
    DESCRIPTION   "OPU Payload Mismatch"
    ::=  { trapMibPrefix 1079 }


alarmMultiplexStructureIdentifierMismatchOPU NOTIFICATION-TYPE 
    OBJECTS     { currentConditionSeverity,currentConditionAffect,neEventLogTimeStamp,neEventLogIdentityTranslation } 
    STATUS      current
    DESCRIPTION   "Multiplex Structure Identifier Mismatch OPU"
    ::=  { trapMibPrefix 1080 }


alarmLossOfFrame NOTIFICATION-TYPE 
    OBJECTS     { currentConditionSeverity,currentConditionAffect,neEventLogTimeStamp,neEventLogIdentityTranslation } 
    STATUS      current
    DESCRIPTION   "Section (SONET) / Regeneration Section (SDH) - Loss of Frame"
    ::=  { trapMibPrefix 1081 }


alarmSectionSignalFailure NOTIFICATION-TYPE 
    OBJECTS     { currentConditionSeverity,currentConditionAffect,neEventLogTimeStamp,neEventLogIdentityTranslation } 
    STATUS      deprecated
    DESCRIPTION   "This is a very severe degradation BER This is a very severe degradation BER Errored Seconds>Errored Seconds Section>= 10**-3 Section= 10**-3"
    ::=  { trapMibPrefix 1082 }


alarmAutoShutdownSendingAisLine NOTIFICATION-TYPE 
    OBJECTS     { currentConditionSeverity,currentConditionAffect,neEventLogTimeStamp,neEventLogIdentityTranslation } 
    STATUS      current
    DESCRIPTION   "Auto Shutdown (L-AIS)"
    ::=  { trapMibPrefix 1083 }


alarmAlarmIndicationSignalLine NOTIFICATION-TYPE 
    OBJECTS     { currentConditionSeverity,currentConditionAffect,neEventLogTimeStamp,neEventLogIdentityTranslation } 
    STATUS      current
    DESCRIPTION   "Alarm Indication Signal Line / Multiplex Section"
    ::=  { trapMibPrefix 1084 }


alarmRemoteDefectIndicationLine NOTIFICATION-TYPE 
    OBJECTS     { currentConditionSeverity,currentConditionAffect,neEventLogTimeStamp,neEventLogIdentityTranslation } 
    STATUS      current
    DESCRIPTION   "Line / Multiplex Section RDI"
    ::=  { trapMibPrefix 1085 }


alarmSignalDegradeLine NOTIFICATION-TYPE 
    OBJECTS     { currentConditionSeverity,currentConditionAffect,neEventLogTimeStamp,neEventLogIdentityTranslation } 
    STATUS      current
    DESCRIPTION   "Line/Mux Section SD alarm; related to a configurable threshold"
    ::=  { trapMibPrefix 1086 }


alarmAlarmIndicationSignalHigherOrderPath NOTIFICATION-TYPE 
    OBJECTS     { currentConditionSeverity,currentConditionAffect,neEventLogTimeStamp,neEventLogIdentityTranslation } 
    STATUS      current
    DESCRIPTION   "Alarm Indication Signal Path"
    ::=  { trapMibPrefix 1087 }


alarmLossOfPointerHigherOrderPath NOTIFICATION-TYPE 
    OBJECTS     { currentConditionSeverity,currentConditionAffect,neEventLogTimeStamp,neEventLogIdentityTranslation } 
    STATUS      current
    DESCRIPTION   "Path LOP"
    ::=  { trapMibPrefix 1088 }


alarmLossofMultiframeHigherOrderPath NOTIFICATION-TYPE 
    OBJECTS     { currentConditionSeverity,currentConditionAffect,neEventLogTimeStamp,neEventLogIdentityTranslation } 
    STATUS      current
    DESCRIPTION   "Path LOM"
    ::=  { trapMibPrefix 1089 }


alarmLossofSequenceHigherOrderPath NOTIFICATION-TYPE 
    OBJECTS     { currentConditionSeverity,currentConditionAffect,neEventLogTimeStamp,neEventLogIdentityTranslation } 
    STATUS      current
    DESCRIPTION   "Path Loss Of Sequence"
    ::=  { trapMibPrefix 1090 }


alarmUnequippedHigherOrderPath NOTIFICATION-TYPE 
    OBJECTS     { currentConditionSeverity,currentConditionAffect,neEventLogTimeStamp,neEventLogIdentityTranslation } 
    STATUS      current
    DESCRIPTION   "Path UNEQ"
    ::=  { trapMibPrefix 1091 }


alarmPayloadMismatchHigherOrderPath NOTIFICATION-TYPE 
    OBJECTS     { currentConditionSeverity,currentConditionAffect,neEventLogTimeStamp,neEventLogIdentityTranslation } 
    STATUS      current
    DESCRIPTION   "SONET/SDH Path Payload Mismatch"
    ::=  { trapMibPrefix 1092 }


alarmRemoteDefectIndicationHigherOrderPath NOTIFICATION-TYPE 
    OBJECTS     { currentConditionSeverity,currentConditionAffect,neEventLogTimeStamp,neEventLogIdentityTranslation } 
    STATUS      current
    DESCRIPTION   "Path RDI"
    ::=  { trapMibPrefix 1093 }


alarmSignalDegradeHigherOrderPath NOTIFICATION-TYPE 
    OBJECTS     { currentConditionSeverity,currentConditionAffect,neEventLogTimeStamp,neEventLogIdentityTranslation } 
    STATUS      deprecated
    DESCRIPTION   "Path Signal Degrade alarm; related to a configurable threshold"
    ::=  { trapMibPrefix 1094 }


alarmAlarmIndicationSignalLowerOrderPath NOTIFICATION-TYPE 
    OBJECTS     { currentConditionSeverity,currentConditionAffect,neEventLogTimeStamp,neEventLogIdentityTranslation } 
    STATUS      current
    DESCRIPTION   "Alarm Indication Signal Lower Order Path"
    ::=  { trapMibPrefix 1095 }


alarmLossOfPointerLowerOrderPath NOTIFICATION-TYPE 
    OBJECTS     { currentConditionSeverity,currentConditionAffect,neEventLogTimeStamp,neEventLogIdentityTranslation } 
    STATUS      current
    DESCRIPTION   "Is this the same as LOF-LP"
    ::=  { trapMibPrefix 1096 }


alarmLossofMultiframeLowerOrderPath NOTIFICATION-TYPE 
    OBJECTS     { currentConditionSeverity,currentConditionAffect,neEventLogTimeStamp,neEventLogIdentityTranslation } 
    STATUS      current
    DESCRIPTION   "LO-Path Loss Of Multiframe Condition"
    ::=  { trapMibPrefix 1097 }


alarmLossofSequenceLowerOrderPath NOTIFICATION-TYPE 
    OBJECTS     { currentConditionSeverity,currentConditionAffect,neEventLogTimeStamp,neEventLogIdentityTranslation } 
    STATUS      current
    DESCRIPTION   "LO-Path Loss Of Sequence"
    ::=  { trapMibPrefix 1098 }


alarmUnequippedLowerOrderPath NOTIFICATION-TYPE 
    OBJECTS     { currentConditionSeverity,currentConditionAffect,neEventLogTimeStamp,neEventLogIdentityTranslation } 
    STATUS      current
    DESCRIPTION   "LO-Path Unequipped"
    ::=  { trapMibPrefix 1099 }


alarmPayloadMismatchLowerOrderPath NOTIFICATION-TYPE 
    OBJECTS     { currentConditionSeverity,currentConditionAffect,neEventLogTimeStamp,neEventLogIdentityTranslation } 
    STATUS      current
    DESCRIPTION   "LO-Path Payload Mismatch"
    ::=  { trapMibPrefix 1100 }


alarmRemoteDefectIndicationLowerOrderPath NOTIFICATION-TYPE 
    OBJECTS     { currentConditionSeverity,currentConditionAffect,neEventLogTimeStamp,neEventLogIdentityTranslation } 
    STATUS      current
    DESCRIPTION   "LO-Path Remote Defect Indication"
    ::=  { trapMibPrefix 1101 }


alarmLossOfMultiframeVCG NOTIFICATION-TYPE 
    OBJECTS     { currentConditionSeverity,currentConditionAffect,neEventLogTimeStamp,neEventLogIdentityTranslation } 
    STATUS      deprecated
    DESCRIPTION   "Until the VCG is cross-connected the alarm should not be sent"
    ::=  { trapMibPrefix 1102 }


alarmLossOfSequenceVCG NOTIFICATION-TYPE 
    OBJECTS     { currentConditionSeverity,currentConditionAffect,neEventLogTimeStamp,neEventLogIdentityTranslation } 
    STATUS      deprecated
    DESCRIPTION   "Until the VCG is cross-connected the alarm should not be sent"
    ::=  { trapMibPrefix 1103 }


alarmLossofAlignmentVCG NOTIFICATION-TYPE 
    OBJECTS     { currentConditionSeverity,currentConditionAffect,neEventLogTimeStamp,neEventLogIdentityTranslation } 
    STATUS      deprecated
    DESCRIPTION   "Loss of Alignment"
    ::=  { trapMibPrefix 1104 }


alarmAutoShutdownSendingEPC NOTIFICATION-TYPE 
    OBJECTS     { currentConditionSeverity,currentConditionAffect,neEventLogTimeStamp,neEventLogIdentityTranslation } 
    STATUS      current
    DESCRIPTION   "Auto Shutdown (EPC)"
    ::=  { trapMibPrefix 1105 }


alarmThres15MinExceededPhysConvES NOTIFICATION-TYPE 
    OBJECTS     { currentConditionSeverity,currentConditionAffect,neEventLogTimeStamp,neEventLogIdentityTranslation } 
    STATUS      current
    DESCRIPTION   "Errored Seconds Physical Coding Layer"
    ::=  { trapMibPrefix 1106 }


alarmThres15MinExceededPhysConvCV NOTIFICATION-TYPE 
    OBJECTS     { currentConditionSeverity,currentConditionAffect,neEventLogTimeStamp,neEventLogIdentityTranslation } 
    STATUS      current
    DESCRIPTION   "Coding Violations Physical Coding Layer"
    ::=  { trapMibPrefix 1107 }


alarmThres15MinExceededPhysConvDE NOTIFICATION-TYPE 
    OBJECTS     { currentConditionSeverity,currentConditionAffect,neEventLogTimeStamp,neEventLogIdentityTranslation } 
    STATUS      current
    DESCRIPTION   "Disparity Errors Physical Coding Layer"
    ::=  { trapMibPrefix 1108 }


alarmThres15MinExceededPhysConvCVDE NOTIFICATION-TYPE 
    OBJECTS     { currentConditionSeverity,currentConditionAffect,neEventLogTimeStamp,neEventLogIdentityTranslation } 
    STATUS      current
    DESCRIPTION   "Coding Violations And Disparity Errors Physical Coding Layer"
    ::=  { trapMibPrefix 1109 }


alarmLossOfGfpFrame NOTIFICATION-TYPE 
    OBJECTS     { currentConditionSeverity,currentConditionAffect,neEventLogTimeStamp,neEventLogIdentityTranslation } 
    STATUS      current
    DESCRIPTION   "GFP LOF"
    ::=  { trapMibPrefix 1110 }


alarmPayloadMismatchGfp NOTIFICATION-TYPE 
    OBJECTS     { currentConditionSeverity,currentConditionAffect,neEventLogTimeStamp,neEventLogIdentityTranslation } 
    STATUS      current
    DESCRIPTION   "GFP Payload Mismatch"
    ::=  { trapMibPrefix 1111 }


alarmGfpLossOfClientSig NOTIFICATION-TYPE 
    OBJECTS     { currentConditionSeverity,currentConditionAffect,neEventLogTimeStamp,neEventLogIdentityTranslation } 
    STATUS      current
    DESCRIPTION   "GFP Loss Of Client Signal"
    ::=  { trapMibPrefix 1112 }


alarmLossOfCharSyncFromFarEnd NOTIFICATION-TYPE 
    OBJECTS     { currentConditionSeverity,currentConditionAffect,neEventLogTimeStamp,neEventLogIdentityTranslation } 
    STATUS      current
    DESCRIPTION   "Loss of Character Synchronization from FEND"
    ::=  { trapMibPrefix 1113 }


alarmSwitchtoProtectionInhibited NOTIFICATION-TYPE 
    OBJECTS     { currentConditionSeverity,currentConditionAffect,neEventLogTimeStamp,neEventLogIdentityTranslation } 
    STATUS      current
    DESCRIPTION   "Protection Switch Inhibited. Switch to PROTN facility Locked Out. Reported by WKG facility. Leads to PSI state."
    ::=  { trapMibPrefix 1114 }


alarmSwitchtoWorkingInhibited NOTIFICATION-TYPE 
    OBJECTS     { currentConditionSeverity,currentConditionAffect,neEventLogTimeStamp,neEventLogIdentityTranslation } 
    STATUS      current
    DESCRIPTION   "Protection Release Inhibited. Switch back to WKG facility Locked Out. Reported by PROTN facility. Leads to PRI state."
    ::=  { trapMibPrefix 1115 }


alarmOTDRMeasuringinProgress NOTIFICATION-TYPE 
    OBJECTS     { currentConditionSeverity,currentConditionAffect,neEventLogTimeStamp,neEventLogIdentityTranslation } 
    STATUS      current
    DESCRIPTION   ""
    ::=  { trapMibPrefix 1116 }


alarmProtectionNotAvailable NOTIFICATION-TYPE 
    OBJECTS     { currentConditionSeverity,currentConditionAffect,neEventLogTimeStamp,neEventLogIdentityTranslation } 
    STATUS      current
    DESCRIPTION   "(Protection Not Available)
         In the case of Channel Card Protection: due to unequipped or mismatched partner equipment - sent by active facility.
         In the case of HST Channel Protection: due to unequipped or mismatched partner plug - sent by active facility;
         on an OLM, the pilot laser has been switched off for a defined perion to allow an Optical Time Domain Reflectormeter to be deployed.
         In the case of Controller Protection: due to partner OOS-AU or OOS-MA, DSBLD (Protection Not Available)."
    ::=  { trapMibPrefix 1117 }


alarmApsConfigMismatch NOTIFICATION-TYPE 
    OBJECTS     { currentConditionSeverity,currentConditionAffect,neEventLogTimeStamp,neEventLogIdentityTranslation } 
    STATUS      current
    DESCRIPTION   "Configuration Mismatch between NEND and FEND. Reported by working facility (PATHID==WKG) or protection facility (PATHID==PROTN)"
    ::=  { trapMibPrefix 1118 }


alarmEmbeddedOperationsChannelFailure NOTIFICATION-TYPE 
    OBJECTS     { currentConditionSeverity,currentConditionAffect,neEventLogTimeStamp,neEventLogIdentityTranslation } 
    STATUS      current
    DESCRIPTION   "Embedded Management Communication Channel Failure"
    ::=  { trapMibPrefix 1119 }


alarmSignalDegradeSection NOTIFICATION-TYPE 
    OBJECTS     { currentConditionSeverity,currentConditionAffect,neEventLogTimeStamp,neEventLogIdentityTranslation } 
    STATUS      deprecated
    DESCRIPTION   "Section / Regeneration Section Signal Degrade"
    ::=  { trapMibPrefix 1120 }


alarmSignalDegradationonLinkVector NOTIFICATION-TYPE 
    OBJECTS     { currentConditionSeverity,currentConditionAffect,neEventLogTimeStamp,neEventLogIdentityTranslation } 
    STATUS      current
    DESCRIPTION   "Signal Degradation on Link Vector. Superseeded by SF-LINK."
    ::=  { trapMibPrefix 1121 }


alarmSignalFailureonLinkVector NOTIFICATION-TYPE 
    OBJECTS     { currentConditionSeverity,currentConditionAffect,neEventLogTimeStamp,neEventLogIdentityTranslation } 
    STATUS      current
    DESCRIPTION   "Signal Fail Link Vector"
    ::=  { trapMibPrefix 1122 }


alarmInputVoltageFailure NOTIFICATION-TYPE 
    OBJECTS     { currentConditionSeverity,currentConditionAffect,neEventLogTimeStamp,neEventLogIdentityTranslation } 
    STATUS      current
    DESCRIPTION   "Failure of Input Voltage"
    ::=  { trapMibPrefix 1123 }


alarmPowerSupplyUnitFailure NOTIFICATION-TYPE 
    OBJECTS     { currentConditionSeverity,currentConditionAffect,neEventLogTimeStamp,neEventLogIdentityTranslation } 
    STATUS      current
    DESCRIPTION   ""
    ::=  { trapMibPrefix 1124 }


alarmCurrentTooLow NOTIFICATION-TYPE 
    OBJECTS     { currentConditionSeverity,currentConditionAffect,neEventLogTimeStamp,neEventLogIdentityTranslation } 
    STATUS      current
    DESCRIPTION   "Output Current Too Low"
    ::=  { trapMibPrefix 1125 }


alarmCurrentTooHigh NOTIFICATION-TYPE 
    OBJECTS     { currentConditionSeverity,currentConditionAffect,neEventLogTimeStamp,neEventLogIdentityTranslation } 
    STATUS      current
    DESCRIPTION   "Output Current Too High"
    ::=  { trapMibPrefix 1126 }


alarmMultipleFanFailure NOTIFICATION-TYPE 
    OBJECTS     { currentConditionSeverity,currentConditionAffect,neEventLogTimeStamp,neEventLogIdentityTranslation } 
    STATUS      current
    DESCRIPTION   "Fan is failing or failed and needs replacement."
    ::=  { trapMibPrefix 1127 }


alarmSingleFanFailure NOTIFICATION-TYPE 
    OBJECTS     { currentConditionSeverity,currentConditionAffect,neEventLogTimeStamp,neEventLogIdentityTranslation } 
    STATUS      current
    DESCRIPTION   "Fan operation is degraded and needs attention (cleaning, filter replacement or possible fan replacement)."
    ::=  { trapMibPrefix 1128 }


alarmLinkDown NOTIFICATION-TYPE 
    OBJECTS     { currentConditionSeverity,currentConditionAffect,neEventLogTimeStamp,neEventLogIdentityTranslation } 
    STATUS      current
    DESCRIPTION   "Failure of External Linkage"
    ::=  { trapMibPrefix 1129 }


alarmVoltageOutOfRange NOTIFICATION-TYPE 
    OBJECTS     { currentConditionSeverity,currentConditionAffect,neEventLogTimeStamp,neEventLogIdentityTranslation } 
    STATUS      current
    DESCRIPTION   "Voltage Out of Range"
    ::=  { trapMibPrefix 1130 }


alarmPeerLink NOTIFICATION-TYPE 
    OBJECTS     { currentConditionSeverity,currentConditionAffect,neEventLogTimeStamp,neEventLogIdentityTranslation } 
    STATUS      current
    DESCRIPTION   "Failure of Internal Link or Link Protocol (could be protocol incompatibility) between cards in Protection or Regeneration Pair or between Encryption cards"
    ::=  { trapMibPrefix 1131 }


alarmHwFailure NOTIFICATION-TYPE 
    OBJECTS     { currentConditionSeverity,currentConditionAffect,neEventLogTimeStamp,neEventLogIdentityTranslation } 
    STATUS      current
    DESCRIPTION   "General Hardware Failure"
    ::=  { trapMibPrefix 1132 }


alarmAlarmIndicationSignalOduTcmB NOTIFICATION-TYPE 
    OBJECTS     { currentConditionSeverity,currentConditionAffect,neEventLogTimeStamp,neEventLogIdentityTranslation } 
    STATUS      current
    DESCRIPTION   "Alarm Indication Signal ODU Tandem Connection Monitoring Instance B"
    ::=  { trapMibPrefix 1133 }


alarmOpenConnectionIndicationOduTcmB NOTIFICATION-TYPE 
    OBJECTS     { currentConditionSeverity,currentConditionAffect,neEventLogTimeStamp,neEventLogIdentityTranslation } 
    STATUS      current
    DESCRIPTION   "Open Connection Indication ODU Tandem Connection Monitoring B"
    ::=  { trapMibPrefix 1134 }


alarmLockedDefectOduTcmB NOTIFICATION-TYPE 
    OBJECTS     { currentConditionSeverity,currentConditionAffect,neEventLogTimeStamp,neEventLogIdentityTranslation } 
    STATUS      current
    DESCRIPTION   "Locked Defect ODU TCM Instance B"
    ::=  { trapMibPrefix 1135 }


alarmLossofTandemConnectionOduTcmB NOTIFICATION-TYPE 
    OBJECTS     { currentConditionSeverity,currentConditionAffect,neEventLogTimeStamp,neEventLogIdentityTranslation } 
    STATUS      current
    DESCRIPTION   "Loss of Tandem Connection ODU Tandem Connection Monitoring Instane B"
    ::=  { trapMibPrefix 1136 }


alarmSignalDegradeOduTcmB NOTIFICATION-TYPE 
    OBJECTS     { currentConditionSeverity,currentConditionAffect,neEventLogTimeStamp,neEventLogIdentityTranslation } 
    STATUS      current
    DESCRIPTION   "Signal Degrade ODU Tandem Connection Monitoring Instance B. Related to a configurable threshold"
    ::=  { trapMibPrefix 1137 }


alarmBackwardDefectIndicationOduTcmB NOTIFICATION-TYPE 
    OBJECTS     { currentConditionSeverity,currentConditionAffect,neEventLogTimeStamp,neEventLogIdentityTranslation } 
    STATUS      current
    DESCRIPTION   "ODU Tandem Connection Monitoring B Backward Defect Indication"
    ::=  { trapMibPrefix 1138 }


alarmApsProtocolFailure NOTIFICATION-TYPE 
    OBJECTS     { currentConditionSeverity,currentConditionAffect,neEventLogTimeStamp,neEventLogIdentityTranslation } 
    STATUS      current
    DESCRIPTION   "Protocol Failure between NEND and FEND. Reported by protecting facility (PATHID==PROTN)."
    ::=  { trapMibPrefix 1139 }


alarmApdLowVoltage NOTIFICATION-TYPE 
    OBJECTS     { currentConditionSeverity,currentConditionAffect,neEventLogTimeStamp,neEventLogIdentityTranslation } 
    STATUS      deprecated
    DESCRIPTION   "Instantaneous Amplifying Photo Diode Low Voltage"
    ::=  { trapMibPrefix 1140 }


alarmApdHighVoltage NOTIFICATION-TYPE 
    OBJECTS     { currentConditionSeverity,currentConditionAffect,neEventLogTimeStamp,neEventLogIdentityTranslation } 
    STATUS      deprecated
    DESCRIPTION   "Instantaneous Amplifying Photo Diode High Voltage"
    ::=  { trapMibPrefix 1141 }


alarmLinkControlProtocolFailure NOTIFICATION-TYPE 
    OBJECTS     { currentConditionSeverity,currentConditionAffect,neEventLogTimeStamp,neEventLogIdentityTranslation } 
    STATUS      current
    DESCRIPTION   "Link Control Protocol setup error or timeout"
    ::=  { trapMibPrefix 1142 }


alarmReceiverLowTemp NOTIFICATION-TYPE 
    OBJECTS     { currentConditionSeverity,currentConditionAffect,neEventLogTimeStamp,neEventLogIdentityTranslation } 
    STATUS      deprecated
    DESCRIPTION   "Instantaneous Receiver Temperature"
    ::=  { trapMibPrefix 1143 }


alarmReceiverHighTemp NOTIFICATION-TYPE 
    OBJECTS     { currentConditionSeverity,currentConditionAffect,neEventLogTimeStamp,neEventLogIdentityTranslation } 
    STATUS      deprecated
    DESCRIPTION   "Instantaneous Receiver Temperature"
    ::=  { trapMibPrefix 1144 }


alarmThermoElectricCoolerCurrentTooLow NOTIFICATION-TYPE 
    OBJECTS     { currentConditionSeverity,currentConditionAffect,neEventLogTimeStamp,neEventLogIdentityTranslation } 
    STATUS      deprecated
    DESCRIPTION   "Thermo Elecetric Cooler Low Current Level"
    ::=  { trapMibPrefix 1145 }


alarmThermoElectricCoolerCurrentTooHigh NOTIFICATION-TYPE 
    OBJECTS     { currentConditionSeverity,currentConditionAffect,neEventLogTimeStamp,neEventLogIdentityTranslation } 
    STATUS      deprecated
    DESCRIPTION   "Thermo Elecetric Cooler High Current Level"
    ::=  { trapMibPrefix 1146 }


alarmSubModuleTempTooHigh NOTIFICATION-TYPE 
    OBJECTS     { currentConditionSeverity,currentConditionAffect,neEventLogTimeStamp,neEventLogIdentityTranslation } 
    STATUS      current
    DESCRIPTION   "Relevant only when ERRFWD=LSROFF. Enables/disables theSubmodule Tempe
         possibility to delay turning off the laser.Relevant only when ERRFWD=LSROFF. Enables/disables theSubmodule Temperature too High
         possibility to delay turning off the laser.
         This applies to the case when turning off the laserrature too High
         is done as an error forwarding mechanism.
         This applies to the case when turning off the laser
         is done as an error forwarding mechanism."
    ::=  { trapMibPrefix 1147 }


alarmSignalDegradeOlm NOTIFICATION-TYPE 
    OBJECTS     { currentConditionSeverity,currentConditionAffect,neEventLogTimeStamp,neEventLogIdentityTranslation } 
    STATUS      current
    DESCRIPTION   "Signal Degrade"
    ::=  { trapMibPrefix 1148 }


alarmReceiverOverloadProtection NOTIFICATION-TYPE 
    OBJECTS     { currentConditionSeverity,currentConditionAffect,neEventLogTimeStamp,neEventLogIdentityTranslation } 
    STATUS      current
    DESCRIPTION   "Safety condition, protecting the system against too high receive power."
    ::=  { trapMibPrefix 1149 }


alarmLossOfFrameMux NOTIFICATION-TYPE 
    OBJECTS     { currentConditionSeverity,currentConditionAffect,neEventLogTimeStamp,neEventLogIdentityTranslation } 
    STATUS      current
    DESCRIPTION   "Multiplexer Loss of Frame"
    ::=  { trapMibPrefix 1150 }


alarmLossOfFrameMuxFarEnd NOTIFICATION-TYPE 
    OBJECTS     { currentConditionSeverity,currentConditionAffect,neEventLogTimeStamp,neEventLogIdentityTranslation } 
    STATUS      current
    DESCRIPTION   "Multiplexer Loss of Frame on Far End"
    ::=  { trapMibPrefix 1151 }


alarmLossOfCharSync NOTIFICATION-TYPE 
    OBJECTS     { currentConditionSeverity,currentConditionAffect,neEventLogTimeStamp,neEventLogIdentityTranslation } 
    STATUS      current
    DESCRIPTION   "Unable to syncronise on the characters in the incoming datastream"
    ::=  { trapMibPrefix 1152 }


alarmThres15MinExceededFecCE NOTIFICATION-TYPE 
    OBJECTS     { currentConditionSeverity,currentConditionAffect,neEventLogTimeStamp,neEventLogIdentityTranslation } 
    STATUS      current
    DESCRIPTION   "FEC Corrected Errors Exceeded 15 Minute Threshold"
    ::=  { trapMibPrefix 1153 }


alarmThres15MinExceededFecUBE NOTIFICATION-TYPE 
    OBJECTS     { currentConditionSeverity,currentConditionAffect,neEventLogTimeStamp,neEventLogIdentityTranslation } 
    STATUS      current
    DESCRIPTION   "FEC Uncorrected Block Error 15 Minute Threshold Exceeded"
    ::=  { trapMibPrefix 1154 }


alarmThres15MinExceededFecES NOTIFICATION-TYPE 
    OBJECTS     { currentConditionSeverity,currentConditionAffect,neEventLogTimeStamp,neEventLogIdentityTranslation } 
    STATUS      current
    DESCRIPTION   "Errored Seconds FEC OTU Monitoring"
    ::=  { trapMibPrefix 1155 }


alarmThres15MinExceededFecSES NOTIFICATION-TYPE 
    OBJECTS     { currentConditionSeverity,currentConditionAffect,neEventLogTimeStamp,neEventLogIdentityTranslation } 
    STATUS      current
    DESCRIPTION   "Severely Errored Seconds FEC 15 Minute Threshold Exceeded"
    ::=  { trapMibPrefix 1156 }


alarmThres15MinExceededMuxES NOTIFICATION-TYPE 
    OBJECTS     { currentConditionSeverity,currentConditionAffect,neEventLogTimeStamp,neEventLogIdentityTranslation } 
    STATUS      current
    DESCRIPTION   "Multiplex Error Second High Threshold 15 min crossed"
    ::=  { trapMibPrefix 1157 }


alarmThres15MinExceededMuxSES NOTIFICATION-TYPE 
    OBJECTS     { currentConditionSeverity,currentConditionAffect,neEventLogTimeStamp,neEventLogIdentityTranslation } 
    STATUS      current
    DESCRIPTION   "Severely Errored Second Mux 15 Minute Threshold Exceeded"
    ::=  { trapMibPrefix 1158 }


alarmThres15MinExceededGfpCHEC NOTIFICATION-TYPE 
    OBJECTS     { currentConditionSeverity,currentConditionAffect,neEventLogTimeStamp,neEventLogIdentityTranslation } 
    STATUS      current
    DESCRIPTION   "C-HEC 15Min Exceeded"
    ::=  { trapMibPrefix 1159 }


alarmThres15MinExceededGfpTHEC NOTIFICATION-TYPE 
    OBJECTS     { currentConditionSeverity,currentConditionAffect,neEventLogTimeStamp,neEventLogIdentityTranslation } 
    STATUS      current
    DESCRIPTION   "tHEC Corrected Error 15 Minute Threshold Exceeded"
    ::=  { trapMibPrefix 1160 }


alarmThres15MinExceededGfpTHecDisc NOTIFICATION-TYPE 
    OBJECTS     { currentConditionSeverity,currentConditionAffect,neEventLogTimeStamp,neEventLogIdentityTranslation } 
    STATUS      current
    DESCRIPTION   "tHEC Discard 15 Minute Threshold Exceeded"
    ::=  { trapMibPrefix 1161 }


alarmThres15MinExceededGfpTsuperblockDisc NOTIFICATION-TYPE 
    OBJECTS     { currentConditionSeverity,currentConditionAffect,neEventLogTimeStamp,neEventLogIdentityTranslation } 
    STATUS      current
    DESCRIPTION   "Discard SBlocks 15M Crossed"
    ::=  { trapMibPrefix 1162 }


alarmIntrusionRx NOTIFICATION-TYPE 
    OBJECTS     { currentConditionSeverity,currentConditionAffect,neEventLogTimeStamp,neEventLogIdentityTranslation } 
    STATUS      deprecated
    DESCRIPTION   "Intrusion on the Receiver Fiber based on GRADHT-AT keyword."
    ::=  { trapMibPrefix 1163 }


alarmIntrusionTx NOTIFICATION-TYPE 
    OBJECTS     { currentConditionSeverity,currentConditionAffect,neEventLogTimeStamp,neEventLogIdentityTranslation } 
    STATUS      deprecated
    DESCRIPTION   "Intrusion on the Receiver Fiber based on GRADHT-AT keyword."
    ::=  { trapMibPrefix 1164 }


alarmAutoShutdownLaserOffDueToHighTemp NOTIFICATION-TYPE 
    OBJECTS     { currentConditionSeverity,currentConditionAffect,neEventLogTimeStamp,neEventLogIdentityTranslation } 
    STATUS      current
    DESCRIPTION   "Facility autonomously shut down with Transmitter off due to temperature."
    ::=  { trapMibPrefix 1165 }


alarmAutoShutdownLaserOffDueToHighTxPwr NOTIFICATION-TYPE 
    OBJECTS     { currentConditionSeverity,currentConditionAffect,neEventLogTimeStamp,neEventLogIdentityTranslation } 
    STATUS      current
    DESCRIPTION   "Facility Autonomously Shut Down with Transmitter OFF because of excessiv optical Power Transmitted."
    ::=  { trapMibPrefix 1166 }


alarmLaserEndOfLife NOTIFICATION-TYPE 
    OBJECTS     { currentConditionSeverity,currentConditionAffect,neEventLogTimeStamp,neEventLogIdentityTranslation } 
    STATUS      current
    DESCRIPTION   "End Of Life [laser degrade]."
    ::=  { trapMibPrefix 1167 }


alarmLaserBiasCurrAbnormal NOTIFICATION-TYPE 
    OBJECTS     { currentConditionSeverity,currentConditionAffect,neEventLogTimeStamp,neEventLogIdentityTranslation } 
    STATUS      current
    DESCRIPTION   "Abnormally High Laser Bias Current Level under the current operating conditions."
    ::=  { trapMibPrefix 1168 }


alarmOpticalPowerTxLOS NOTIFICATION-TYPE 
    OBJECTS     { currentConditionSeverity,currentConditionAffect,neEventLogTimeStamp,neEventLogIdentityTranslation } 
    STATUS      current
    DESCRIPTION   "Optical Power Transmission Fault (Tx LOS)."
    ::=  { trapMibPrefix 1169 }


alarmMidstageFault NOTIFICATION-TYPE 
    OBJECTS     { currentConditionSeverity,currentConditionAffect,neEventLogTimeStamp,neEventLogIdentityTranslation } 
    STATUS      current
    DESCRIPTION   "Out of Service due to Midstage Fault."
    ::=  { trapMibPrefix 1170 }


alarmFarEndIpAddressUnknown NOTIFICATION-TYPE 
    OBJECTS     { currentConditionSeverity,currentConditionAffect,neEventLogTimeStamp,neEventLogIdentityTranslation } 
    STATUS      current
    DESCRIPTION   "Send by active facility. If an FEND IP Address is changed the corresponding NODE-IP cannot be determined by the OSCM"
    ::=  { trapMibPrefix 1171 }


alarmTopologyDataCalculationInProgress NOTIFICATION-TYPE 
    OBJECTS     { currentConditionSeverity,currentConditionAffect,neEventLogTimeStamp,neEventLogIdentityTranslation } 
    STATUS      current
    DESCRIPTION   "Calculation of topology in progress"
    ::=  { trapMibPrefix 1172 }


alarmNtpServer1Unreachable NOTIFICATION-TYPE 
    OBJECTS     { currentConditionSeverity,currentConditionAffect,neEventLogTimeStamp,neEventLogIdentityTranslation } 
    STATUS      current
    DESCRIPTION   "alarm will be raised if the configured NTP server is not reachable"
    ::=  { trapMibPrefix 1173 }


alarmNtpServer2Unreachable NOTIFICATION-TYPE 
    OBJECTS     { currentConditionSeverity,currentConditionAffect,neEventLogTimeStamp,neEventLogIdentityTranslation } 
    STATUS      current
    DESCRIPTION   "alarm will be raised if the configured NTP server is not reachable"
    ::=  { trapMibPrefix 1174 }


alarmNtpServer3Unreachable NOTIFICATION-TYPE 
    OBJECTS     { currentConditionSeverity,currentConditionAffect,neEventLogTimeStamp,neEventLogIdentityTranslation } 
    STATUS      current
    DESCRIPTION   "alarm will be raised if the configured NTP server is not reachable"
    ::=  { trapMibPrefix 1175 }


alarmAutoShutdownSendingAisOpu NOTIFICATION-TYPE 
    OBJECTS     { currentConditionSeverity,currentConditionAffect,neEventLogTimeStamp,neEventLogIdentityTranslation } 
    STATUS      current
    DESCRIPTION   "Auto Shutdown (OPU-AIS)"
    ::=  { trapMibPrefix 1176 }


alarmAlarmIndicationSignalOpu NOTIFICATION-TYPE 
    OBJECTS     { currentConditionSeverity,currentConditionAffect,neEventLogTimeStamp,neEventLogIdentityTranslation } 
    STATUS      current
    DESCRIPTION   "Alarm Indication Signal OPU Path Monitoring"
    ::=  { trapMibPrefix 1177 }


alarmAlarmIndicationSignalOduTcmC NOTIFICATION-TYPE 
    OBJECTS     { currentConditionSeverity,currentConditionAffect,neEventLogTimeStamp,neEventLogIdentityTranslation } 
    STATUS      current
    DESCRIPTION   "Alarm Indication Signal ODU Tandem Connection Monitoring Instance C"
    ::=  { trapMibPrefix 1178 }


alarmBackwardDefectIndicationOduTcmC NOTIFICATION-TYPE 
    OBJECTS     { currentConditionSeverity,currentConditionAffect,neEventLogTimeStamp,neEventLogIdentityTranslation } 
    STATUS      current
    DESCRIPTION   "ODU Tandem Connection Monitoring C Backward Defect Indication"
    ::=  { trapMibPrefix 1179 }


alarmLockedDefectOduTcmC NOTIFICATION-TYPE 
    OBJECTS     { currentConditionSeverity,currentConditionAffect,neEventLogTimeStamp,neEventLogIdentityTranslation } 
    STATUS      current
    DESCRIPTION   "Locked Defect ODU TCM Instance C"
    ::=  { trapMibPrefix 1180 }


alarmLossofTandemConnectionOduTcmC NOTIFICATION-TYPE 
    OBJECTS     { currentConditionSeverity,currentConditionAffect,neEventLogTimeStamp,neEventLogIdentityTranslation } 
    STATUS      current
    DESCRIPTION   "Loss of Tandem Connection ODU Tandem Connection Monitoring Instane C"
    ::=  { trapMibPrefix 1181 }


alarmOpenConnectionIndicationOduTcmC NOTIFICATION-TYPE 
    OBJECTS     { currentConditionSeverity,currentConditionAffect,neEventLogTimeStamp,neEventLogIdentityTranslation } 
    STATUS      current
    DESCRIPTION   "Open Connection Indication ODU Tandem Connection Monitoring C"
    ::=  { trapMibPrefix 1182 }


alarmSignalDegradeOduTcmC NOTIFICATION-TYPE 
    OBJECTS     { currentConditionSeverity,currentConditionAffect,neEventLogTimeStamp,neEventLogIdentityTranslation } 
    STATUS      current
    DESCRIPTION   "Signal Degrade ODU Tandem Connection Monitoring Instance C. Related to a configurable threshold"
    ::=  { trapMibPrefix 1183 }


alarmLoopbackError NOTIFICATION-TYPE 
    OBJECTS     { currentConditionSeverity,currentConditionAffect,neEventLogTimeStamp,neEventLogIdentityTranslation } 
    STATUS      current
    DESCRIPTION   "A loop in the PPP-IP path is detected"
    ::=  { trapMibPrefix 1184 }


alarmSectionTraceMismatch NOTIFICATION-TYPE 
    OBJECTS     { currentConditionSeverity,currentConditionAffect,neEventLogTimeStamp,neEventLogIdentityTranslation } 
    STATUS      current
    DESCRIPTION   "Section (SONET) / Regeneration Section (SDH) - Trace Identifier Mismatch"
    ::=  { trapMibPrefix 1185 }


alarmTraceIdentifierMismatchOtu NOTIFICATION-TYPE 
    OBJECTS     { currentConditionSeverity,currentConditionAffect,neEventLogTimeStamp,neEventLogIdentityTranslation } 
    STATUS      current
    DESCRIPTION   "OTU-TIM"
    ::=  { trapMibPrefix 1186 }


alarmTraceIdentifierMismatchOdu NOTIFICATION-TYPE 
    OBJECTS     { currentConditionSeverity,currentConditionAffect,neEventLogTimeStamp,neEventLogIdentityTranslation } 
    STATUS      current
    DESCRIPTION   "ODU-Trace Identifier Mismatch"
    ::=  { trapMibPrefix 1187 }


alarmTraceIdentifierMismatchOduTcmA NOTIFICATION-TYPE 
    OBJECTS     { currentConditionSeverity,currentConditionAffect,neEventLogTimeStamp,neEventLogIdentityTranslation } 
    STATUS      current
    DESCRIPTION   "Trace Identifier Mismatch of ODU Tandem Connection Monitoring Instance A"
    ::=  { trapMibPrefix 1188 }


alarmTraceIdentifierMismatchOduTcmC NOTIFICATION-TYPE 
    OBJECTS     { currentConditionSeverity,currentConditionAffect,neEventLogTimeStamp,neEventLogIdentityTranslation } 
    STATUS      current
    DESCRIPTION   "Trace Identifier Mismatch of ODU Tandem Connection Monitoring Instance C"
    ::=  { trapMibPrefix 1189 }


alarmTraceIdentifierMismatchOduTcmB NOTIFICATION-TYPE 
    OBJECTS     { currentConditionSeverity,currentConditionAffect,neEventLogTimeStamp,neEventLogIdentityTranslation } 
    STATUS      current
    DESCRIPTION   "Trace Identifier Mismatch of ODU Tandem Connection Monitoring Instance B"
    ::=  { trapMibPrefix 1190 }


alarmDatabaseMismatch NOTIFICATION-TYPE 
    OBJECTS     { currentConditionSeverity,currentConditionAffect,neEventLogTimeStamp,neEventLogIdentityTranslation } 
    STATUS      current
    DESCRIPTION   "compare DBACT__FAIL x.y.z in UBR note DBTYPE is retrievable immediately with RTRV-SYS, we do not currently supported a RTRV-COND-SYS"
    ::=  { trapMibPrefix 1191 }


alarmDatabaseNcuMismatch NOTIFICATION-TYPE 
    OBJECTS     { currentConditionSeverity,currentConditionAffect,neEventLogTimeStamp,neEventLogIdentityTranslation } 
    STATUS      current
    DESCRIPTION   "This parameter indicates a change of NCU Type (NCU<->NCU2E)"
    ::=  { trapMibPrefix 1192 }


alarmServerSignalFailureSectionRS NOTIFICATION-TYPE 
    OBJECTS     { currentConditionSeverity,currentConditionAffect,neEventLogTimeStamp,neEventLogIdentityTranslation } 
    STATUS      current
    DESCRIPTION   "Section (SONET) / Regeneration Section (SDH) - Server Signal Failure"
    ::=  { trapMibPrefix 1193 }


alarmFwpMismatchDownloadServiceAffecting NOTIFICATION-TYPE 
    OBJECTS     { currentConditionSeverity,currentConditionAffect,neEventLogTimeStamp,neEventLogIdentityTranslation } 
    STATUS      current
    DESCRIPTION   "Firmware Package Mismatch; download will be Service Affecting"
    ::=  { trapMibPrefix 1194 }


alarmFwpMismatchDownloadNotServiceAffecting NOTIFICATION-TYPE 
    OBJECTS     { currentConditionSeverity,currentConditionAffect,neEventLogTimeStamp,neEventLogIdentityTranslation } 
    STATUS      current
    DESCRIPTION   "Firmware Package Mismatch; download will be NOT Service Affecting"
    ::=  { trapMibPrefix 1195 }


alarmDatabaseVersionMismatch NOTIFICATION-TYPE 
    OBJECTS     { currentConditionSeverity,currentConditionAffect,neEventLogTimeStamp,neEventLogIdentityTranslation } 
    STATUS      current
    DESCRIPTION   "The current DB is newer than required, or not updateable"
    ::=  { trapMibPrefix 1196 }


alarmClientFailForwarding NOTIFICATION-TYPE 
    OBJECTS     { currentConditionSeverity,currentConditionAffect,neEventLogTimeStamp,neEventLogIdentityTranslation } 
    STATUS      current
    DESCRIPTION   "Forwarding of Client Failure"
    ::=  { trapMibPrefix 1197 }


alarmVirtualChannelAis NOTIFICATION-TYPE 
    OBJECTS     { currentConditionSeverity,currentConditionAffect,neEventLogTimeStamp,neEventLogIdentityTranslation } 
    STATUS      current
    DESCRIPTION   "Client Failure Far-end"
    ::=  { trapMibPrefix 1198 }


alarmServerSignalFailureVf NOTIFICATION-TYPE 
    OBJECTS     { currentConditionSeverity,currentConditionAffect,neEventLogTimeStamp,neEventLogIdentityTranslation } 
    STATUS      current
    DESCRIPTION   "Aggregate level failure"
    ::=  { trapMibPrefix 1199 }


alarmSignalFailureOnLink NOTIFICATION-TYPE 
    OBJECTS     { currentConditionSeverity,currentConditionAffect,neEventLogTimeStamp,neEventLogIdentityTranslation } 
    STATUS      current
    DESCRIPTION   "Signal Failure on Link"
    ::=  { trapMibPrefix 1200 }


alarmServerSignalFailureGfp NOTIFICATION-TYPE 
    OBJECTS     { currentConditionSeverity,currentConditionAffect,neEventLogTimeStamp,neEventLogIdentityTranslation } 
    STATUS      current
    DESCRIPTION   "GFP Server Signal Failure"
    ::=  { trapMibPrefix 1201 }


alarmServerSignalFailurePath NOTIFICATION-TYPE 
    OBJECTS     { currentConditionSeverity,currentConditionAffect,neEventLogTimeStamp,neEventLogIdentityTranslation } 
    STATUS      current
    DESCRIPTION   "SONET/SDH Path Server Signal Failure"
    ::=  { trapMibPrefix 1202 }


alarmGainTiltNotSettable NOTIFICATION-TYPE 
    OBJECTS     { currentConditionSeverity,currentConditionAffect,neEventLogTimeStamp,neEventLogIdentityTranslation } 
    STATUS      current
    DESCRIPTION   "The nominal tilt and gain values are not settable"
    ::=  { trapMibPrefix 1203 }


alarmTxPowerLimited NOTIFICATION-TYPE 
    OBJECTS     { currentConditionSeverity,currentConditionAffect,neEventLogTimeStamp,neEventLogIdentityTranslation } 
    STATUS      current
    DESCRIPTION   "The optical output power reached limit"
    ::=  { trapMibPrefix 1204 }


alarmEqualizationProgress NOTIFICATION-TYPE 
    OBJECTS     { currentConditionSeverity,currentConditionAffect,neEventLogTimeStamp,neEventLogIdentityTranslation } 
    STATUS      current
    DESCRIPTION   "Equalization and countdown in progress"
    ::=  { trapMibPrefix 1205 }


alarmUPortFailure NOTIFICATION-TYPE 
    OBJECTS     { currentConditionSeverity,currentConditionAffect,neEventLogTimeStamp,neEventLogIdentityTranslation } 
    STATUS      current
    DESCRIPTION   "Internal U Port Failure"
    ::=  { trapMibPrefix 1206 }


alarmAutoShutdownBlock NOTIFICATION-TYPE 
    OBJECTS     { currentConditionSeverity,currentConditionAffect,neEventLogTimeStamp,neEventLogIdentityTranslation } 
    STATUS      current
    DESCRIPTION   "Auto Shutdown Block"
    ::=  { trapMibPrefix 1207 }


alarmServerSignalFailTx NOTIFICATION-TYPE 
    OBJECTS     { currentConditionSeverity,currentConditionAffect,neEventLogTimeStamp,neEventLogIdentityTranslation } 
    STATUS      current
    DESCRIPTION   "Aggregate level failure"
    ::=  { trapMibPrefix 1208 }


alarmPayloadMismatch NOTIFICATION-TYPE 
    OBJECTS     { currentConditionSeverity,currentConditionAffect,neEventLogTimeStamp,neEventLogIdentityTranslation } 
    STATUS      current
    DESCRIPTION   "Payload Mismatch on Virtual Facility"
    ::=  { trapMibPrefix 1209 }


alarmVoaControlFail NOTIFICATION-TYPE 
    OBJECTS     { currentConditionSeverity,currentConditionAffect,neEventLogTimeStamp,neEventLogIdentityTranslation } 
    STATUS      current
    DESCRIPTION   "The power or attenuation control of OPCM failed"
    ::=  { trapMibPrefix 1210 }


alarmProvisioningLocked NOTIFICATION-TYPE 
    OBJECTS     { currentConditionSeverity,currentConditionAffect,neEventLogTimeStamp,neEventLogIdentityTranslation } 
    STATUS      current
    DESCRIPTION   "Provisioning locked"
    ::=  { trapMibPrefix 1211 }


alarmMansw NOTIFICATION-TYPE 
    OBJECTS     { currentConditionSeverity,currentConditionAffect,neEventLogTimeStamp,neEventLogIdentityTranslation } 
    STATUS      current
    DESCRIPTION   "This condition will only be shown on the working entity, meaning the MANSW has switched traffic from the working entity to the protection entity."
    ::=  { trapMibPrefix 1212 }


alarmWtrTimerRunning NOTIFICATION-TYPE 
    OBJECTS     { currentConditionSeverity,currentConditionAffect,neEventLogTimeStamp,neEventLogIdentityTranslation } 
    STATUS      current
    DESCRIPTION   "WTR timer is running"
    ::=  { trapMibPrefix 1213 }


alarmPcsSignalDegrade NOTIFICATION-TYPE 
    OBJECTS     { currentConditionSeverity,currentConditionAffect,neEventLogTimeStamp,neEventLogIdentityTranslation } 
    STATUS      current
    DESCRIPTION   "Pysical Coding Sublayer Signal Degrade alarm; related to a configurable threshold"
    ::=  { trapMibPrefix 1214 }


alarmThres15MinExceededSonetSectES NOTIFICATION-TYPE 
    OBJECTS     { currentConditionSeverity,currentConditionAffect,neEventLogTimeStamp,neEventLogIdentityTranslation } 
    STATUS      current
    DESCRIPTION   "Errored Seconds Section"
    ::=  { trapMibPrefix 1216 }


alarmThres15MinExceededSonetSectSES NOTIFICATION-TYPE 
    OBJECTS     { currentConditionSeverity,currentConditionAffect,neEventLogTimeStamp,neEventLogIdentityTranslation } 
    STATUS      current
    DESCRIPTION   "Severely Errored Seconds Section 15 Minute Threshold Exceeded"
    ::=  { trapMibPrefix 1217 }


alarmThres15MinExceededSonetSectSEFS NOTIFICATION-TYPE 
    OBJECTS     { currentConditionSeverity,currentConditionAffect,neEventLogTimeStamp,neEventLogIdentityTranslation } 
    STATUS      current
    DESCRIPTION   "Severely Errored Framing Seconds Section 15 Minute Threshold Exceeded"
    ::=  { trapMibPrefix 1218 }


alarmThres15MinExceededSonetSectCV NOTIFICATION-TYPE 
    OBJECTS     { currentConditionSeverity,currentConditionAffect,neEventLogTimeStamp,neEventLogIdentityTranslation } 
    STATUS      current
    DESCRIPTION   "Coding Violations Section"
    ::=  { trapMibPrefix 1219 }


alarmThres15MinExceededSonetLineES NOTIFICATION-TYPE 
    OBJECTS     { currentConditionSeverity,currentConditionAffect,neEventLogTimeStamp,neEventLogIdentityTranslation } 
    STATUS      current
    DESCRIPTION   "Errored Seconds Line"
    ::=  { trapMibPrefix 1220 }


alarmThres15MinExceededSonetLineSES NOTIFICATION-TYPE 
    OBJECTS     { currentConditionSeverity,currentConditionAffect,neEventLogTimeStamp,neEventLogIdentityTranslation } 
    STATUS      current
    DESCRIPTION   "Severely Errored Seconds Line 15 Minute Threshold Exceeded"
    ::=  { trapMibPrefix 1221 }


alarmThres15MinExceededSonetLineCV NOTIFICATION-TYPE 
    OBJECTS     { currentConditionSeverity,currentConditionAffect,neEventLogTimeStamp,neEventLogIdentityTranslation } 
    STATUS      current
    DESCRIPTION   "Coding Violations Line"
    ::=  { trapMibPrefix 1222 }


alarmThres15MinExceededSonetLineUAS NOTIFICATION-TYPE 
    OBJECTS     { currentConditionSeverity,currentConditionAffect,neEventLogTimeStamp,neEventLogIdentityTranslation } 
    STATUS      current
    DESCRIPTION   "Unavailable Seconds Line 15 Minute Threshold Exceeded"
    ::=  { trapMibPrefix 1223 }


alarmThres15MinExceededOduTcmAES NOTIFICATION-TYPE 
    OBJECTS     { currentConditionSeverity,currentConditionAffect,neEventLogTimeStamp,neEventLogIdentityTranslation } 
    STATUS      current
    DESCRIPTION   "Errored Seconds ODU Tandem Connection Monitoring"
    ::=  { trapMibPrefix 1224 }


alarmThres15MinExceededOduTcmASES NOTIFICATION-TYPE 
    OBJECTS     { currentConditionSeverity,currentConditionAffect,neEventLogTimeStamp,neEventLogIdentityTranslation } 
    STATUS      current
    DESCRIPTION   "Severely Errored Seconds ODU Tandem Connection Monitoring A (TCM_A) 15 Minute Threshold Exceeded"
    ::=  { trapMibPrefix 1225 }


alarmThres15MinExceededOduTcmAUAS NOTIFICATION-TYPE 
    OBJECTS     { currentConditionSeverity,currentConditionAffect,neEventLogTimeStamp,neEventLogIdentityTranslation } 
    STATUS      current
    DESCRIPTION   "Unavailable Seconds ODU Tandem Connection Monitoring A (TCM_A) 15 Minute Threshold Exceeded"
    ::=  { trapMibPrefix 1226 }


alarmThres15MinExceededOduTcmABbe NOTIFICATION-TYPE 
    OBJECTS     { currentConditionSeverity,currentConditionAffect,neEventLogTimeStamp,neEventLogIdentityTranslation } 
    STATUS      current
    DESCRIPTION   "Background Block Errors ODU Tandem Connection Monitoring"
    ::=  { trapMibPrefix 1227 }


alarmThres15MinExceededOduTcmBES NOTIFICATION-TYPE 
    OBJECTS     { currentConditionSeverity,currentConditionAffect,neEventLogTimeStamp,neEventLogIdentityTranslation } 
    STATUS      current
    DESCRIPTION   "Errored Seconds ODU Tandem Connection Monitoring"
    ::=  { trapMibPrefix 1228 }


alarmThres15MinExceededOduTcmBSES NOTIFICATION-TYPE 
    OBJECTS     { currentConditionSeverity,currentConditionAffect,neEventLogTimeStamp,neEventLogIdentityTranslation } 
    STATUS      current
    DESCRIPTION   "Severely Errored Seconds ODU Tandem Connection Monitoring B (TCM_B) 15 Minute Threshold Exceeded"
    ::=  { trapMibPrefix 1229 }


alarmThres15MinExceededOduTcmBUAS NOTIFICATION-TYPE 
    OBJECTS     { currentConditionSeverity,currentConditionAffect,neEventLogTimeStamp,neEventLogIdentityTranslation } 
    STATUS      current
    DESCRIPTION   "Unavailable Seconds ODU Tandem Connection Monitoring B (TCM_B) 15 Minute Threshold Exceeded"
    ::=  { trapMibPrefix 1230 }


alarmThres15MinExceededOduTcmBBbe NOTIFICATION-TYPE 
    OBJECTS     { currentConditionSeverity,currentConditionAffect,neEventLogTimeStamp,neEventLogIdentityTranslation } 
    STATUS      current
    DESCRIPTION   "Background Block Errors ODU Tandem Connection Monitoring"
    ::=  { trapMibPrefix 1231 }


alarmThres15MinExceededOduTcmCES NOTIFICATION-TYPE 
    OBJECTS     { currentConditionSeverity,currentConditionAffect,neEventLogTimeStamp,neEventLogIdentityTranslation } 
    STATUS      current
    DESCRIPTION   "Errored Seconds ODU Tandem Connection Monitoring"
    ::=  { trapMibPrefix 1232 }


alarmThres15MinExceededOduTcmCSES NOTIFICATION-TYPE 
    OBJECTS     { currentConditionSeverity,currentConditionAffect,neEventLogTimeStamp,neEventLogIdentityTranslation } 
    STATUS      current
    DESCRIPTION   "Severely Errored Seconds ODU Tandem Connection Monitoring C (TCM_C) 15 Minute Threshold Exceeded"
    ::=  { trapMibPrefix 1233 }


alarmThres15MinExceededOduTcmCUAS NOTIFICATION-TYPE 
    OBJECTS     { currentConditionSeverity,currentConditionAffect,neEventLogTimeStamp,neEventLogIdentityTranslation } 
    STATUS      current
    DESCRIPTION   "Unavailable Seconds ODU Tandem Connection Monitoring C (TCM_C) 15 Minute Threshold Exceeded"
    ::=  { trapMibPrefix 1234 }


alarmThres15MinExceededOduTcmCBbe NOTIFICATION-TYPE 
    OBJECTS     { currentConditionSeverity,currentConditionAffect,neEventLogTimeStamp,neEventLogIdentityTranslation } 
    STATUS      current
    DESCRIPTION   "Background Block Errors ODU Tandem Connection Monitoring"
    ::=  { trapMibPrefix 1235 }


alarmThres15MinExceededOtuES NOTIFICATION-TYPE 
    OBJECTS     { currentConditionSeverity,currentConditionAffect,neEventLogTimeStamp,neEventLogIdentityTranslation } 
    STATUS      current
    DESCRIPTION   "Errored Seconds OTU Section Monitoring"
    ::=  { trapMibPrefix 1236 }


alarmThres15MinExceededOtuSES NOTIFICATION-TYPE 
    OBJECTS     { currentConditionSeverity,currentConditionAffect,neEventLogTimeStamp,neEventLogIdentityTranslation } 
    STATUS      current
    DESCRIPTION   "Severely Errored Seconds OTU Section 15 Minute Threshold Exceeded"
    ::=  { trapMibPrefix 1237 }


alarmThres15MinExceededOtuUAS NOTIFICATION-TYPE 
    OBJECTS     { currentConditionSeverity,currentConditionAffect,neEventLogTimeStamp,neEventLogIdentityTranslation } 
    STATUS      current
    DESCRIPTION   "Unavailable Seconds OTU Section 15 Minute Threshold Exceeded"
    ::=  { trapMibPrefix 1238 }


alarmThres15MinExceededOtuBbe NOTIFICATION-TYPE 
    OBJECTS     { currentConditionSeverity,currentConditionAffect,neEventLogTimeStamp,neEventLogIdentityTranslation } 
    STATUS      current
    DESCRIPTION   "Background Block Errors OTU Section Monitoring"
    ::=  { trapMibPrefix 1239 }


alarmThres15MinExceededOduES NOTIFICATION-TYPE 
    OBJECTS     { currentConditionSeverity,currentConditionAffect,neEventLogTimeStamp,neEventLogIdentityTranslation } 
    STATUS      current
    DESCRIPTION   "Errored Seconds ODU Path Monitoring"
    ::=  { trapMibPrefix 1240 }


alarmThres15MinExceededOduSES NOTIFICATION-TYPE 
    OBJECTS     { currentConditionSeverity,currentConditionAffect,neEventLogTimeStamp,neEventLogIdentityTranslation } 
    STATUS      current
    DESCRIPTION   "Severely Errored Seconds ODU Path 15 Minute Threshold Exceeded"
    ::=  { trapMibPrefix 1241 }


alarmThres15MinExceededOduUAS NOTIFICATION-TYPE 
    OBJECTS     { currentConditionSeverity,currentConditionAffect,neEventLogTimeStamp,neEventLogIdentityTranslation } 
    STATUS      current
    DESCRIPTION   "Unavailable Seconds ODU Path 15 Minute Threshold Exceeded"
    ::=  { trapMibPrefix 1242 }


alarmThres15MinExceededOduBbe NOTIFICATION-TYPE 
    OBJECTS     { currentConditionSeverity,currentConditionAffect,neEventLogTimeStamp,neEventLogIdentityTranslation } 
    STATUS      current
    DESCRIPTION   "Background Block Errors ODU Section Monitoring"
    ::=  { trapMibPrefix 1243 }


alarmThresOptPowerCtrlFailureLow NOTIFICATION-TYPE 
    OBJECTS     { currentConditionSeverity,currentConditionAffect,neEventLogTimeStamp,neEventLogIdentityTranslation } 
    STATUS      current
    DESCRIPTION   "Optical Power Control Failure Low Threshold"
    ::=  { trapMibPrefix 1244 }


alarmThresOptPowerCtrlFailureHigh NOTIFICATION-TYPE 
    OBJECTS     { currentConditionSeverity,currentConditionAffect,neEventLogTimeStamp,neEventLogIdentityTranslation } 
    STATUS      current
    DESCRIPTION   "Optical Power Control Failure High Threshold"
    ::=  { trapMibPrefix 1245 }


alarmDcnServerSignalFailure NOTIFICATION-TYPE 
    OBJECTS     { currentConditionSeverity,currentConditionAffect,neEventLogTimeStamp,neEventLogIdentityTranslation } 
    STATUS      current
    DESCRIPTION   "DCN Server Signal Failure"
    ::=  { trapMibPrefix 1246 }


alarmMaxPowerConsEquipModulesToHigh NOTIFICATION-TYPE 
    OBJECTS     { currentConditionSeverity,currentConditionAffect,neEventLogTimeStamp,neEventLogIdentityTranslation } 
    STATUS      current
    DESCRIPTION   "The maximum power consumption of the installed equipment exceeds the capability of a single PSU in the shelf."
    ::=  { trapMibPrefix 1247 }


alarmMaxPowerConsProvModulesToHigh NOTIFICATION-TYPE 
    OBJECTS     { currentConditionSeverity,currentConditionAffect,neEventLogTimeStamp,neEventLogIdentityTranslation } 
    STATUS      current
    DESCRIPTION   "The maximum power consumption of all provisioned equipment exceeds the capability of a single PSU in the shelf."
    ::=  { trapMibPrefix 1248 }


alarmEquipmentMismatchAllow NOTIFICATION-TYPE 
    OBJECTS     { currentConditionSeverity,currentConditionAffect,neEventLogTimeStamp,neEventLogIdentityTranslation } 
    STATUS      current
    DESCRIPTION   "Equipment Mismatch Allow"
    ::=  { trapMibPrefix 1249 }


alarmOosPrePostSig NOTIFICATION-TYPE 
    OBJECTS     { currentConditionSeverity,currentConditionAffect,neEventLogTimeStamp,neEventLogIdentityTranslation } 
    STATUS      current
    DESCRIPTION   "Out of Service Pre/Post Signalling"
    ::=  { trapMibPrefix 1250 }


alarmOosPrePostSigInSetUpProcess NOTIFICATION-TYPE 
    OBJECTS     { currentConditionSeverity,currentConditionAffect,neEventLogTimeStamp,neEventLogIdentityTranslation } 
    STATUS      current
    DESCRIPTION   "While PPS in Set-Up Process; supersede OOSPPS"
    ::=  { trapMibPrefix 1251 }


alarmOosPrePostSigInTearDownProcess NOTIFICATION-TYPE 
    OBJECTS     { currentConditionSeverity,currentConditionAffect,neEventLogTimeStamp,neEventLogIdentityTranslation } 
    STATUS      current
    DESCRIPTION   "While PPS is in Tear-Down Process"
    ::=  { trapMibPrefix 1252 }


alarmCpTunnelModificationInProgess NOTIFICATION-TYPE 
    OBJECTS     { currentConditionSeverity,currentConditionAffect,neEventLogTimeStamp,neEventLogIdentityTranslation } 
    STATUS      current
    DESCRIPTION   "Modification in Progess"
    ::=  { trapMibPrefix 1253 }


alarmCapabilityLevelMismatch NOTIFICATION-TYPE 
    OBJECTS     { currentConditionSeverity,currentConditionAffect,neEventLogTimeStamp,neEventLogIdentityTranslation } 
    STATUS      current
    DESCRIPTION   "Capability level mismatch"
    ::=  { trapMibPrefix 1254 }


alarmOosPrePostSigEstablishFailed NOTIFICATION-TYPE 
    OBJECTS     { currentConditionSeverity,currentConditionAffect,neEventLogTimeStamp,neEventLogIdentityTranslation } 
    STATUS      current
    DESCRIPTION   "PPS after establishment fail"
    ::=  { trapMibPrefix 1255 }


alarmOosPrePostSigAfterPrecompFailed NOTIFICATION-TYPE 
    OBJECTS     { currentConditionSeverity,currentConditionAffect,neEventLogTimeStamp,neEventLogIdentityTranslation } 
    STATUS      current
    DESCRIPTION   "PPS after precomputed fail"
    ::=  { trapMibPrefix 1256 }


alarmCpTunnelEstablishFailed NOTIFICATION-TYPE 
    OBJECTS     { currentConditionSeverity,currentConditionAffect,neEventLogTimeStamp,neEventLogIdentityTranslation } 
    STATUS      current
    DESCRIPTION   "The Tunnel has Failed to Establish"
    ::=  { trapMibPrefix 1257 }


alarmCpTunnelPrecompFailed NOTIFICATION-TYPE 
    OBJECTS     { currentConditionSeverity,currentConditionAffect,neEventLogTimeStamp,neEventLogIdentityTranslation } 
    STATUS      current
    DESCRIPTION   "The Tunnel precomputing failed"
    ::=  { trapMibPrefix 1258 }


alarmLocalFault NOTIFICATION-TYPE 
    OBJECTS     { currentConditionSeverity,currentConditionAffect,neEventLogTimeStamp,neEventLogIdentityTranslation } 
    STATUS      current
    DESCRIPTION   "Local Fault Sequence ordered_set received by the local PHY"
    ::=  { trapMibPrefix 1259 }


alarmOscPwrTooHigh NOTIFICATION-TYPE 
    OBJECTS     { currentConditionSeverity,currentConditionAffect,neEventLogTimeStamp,neEventLogIdentityTranslation } 
    STATUS      current
    DESCRIPTION   "Optical Supervisory Channel Optical Power High Threshold Exceeded"
    ::=  { trapMibPrefix 1260 }


alarmOscPwrTooLow NOTIFICATION-TYPE 
    OBJECTS     { currentConditionSeverity,currentConditionAffect,neEventLogTimeStamp,neEventLogIdentityTranslation } 
    STATUS      current
    DESCRIPTION   "Optical Supervisory Channel Optical Power Low Threshold Exceeded"
    ::=  { trapMibPrefix 1261 }


alarmAseTableBuild NOTIFICATION-TYPE 
    OBJECTS     { currentConditionSeverity,currentConditionAffect,neEventLogTimeStamp,neEventLogIdentityTranslation } 
    STATUS      current
    DESCRIPTION   "Auto shutdown due to missing ASE table"
    ::=  { trapMibPrefix 1262 }


alarmAseTableNotAvailable NOTIFICATION-TYPE 
    OBJECTS     { currentConditionSeverity,currentConditionAffect,neEventLogTimeStamp,neEventLogIdentityTranslation } 
    STATUS      current
    DESCRIPTION   "ASE table not available or invalid"
    ::=  { trapMibPrefix 1263 }


alarmAutomaticPowerReduction NOTIFICATION-TYPE 
    OBJECTS     { currentConditionSeverity,currentConditionAffect,neEventLogTimeStamp,neEventLogIdentityTranslation } 
    STATUS      current
    DESCRIPTION   "The signal power exceeds the limit"
    ::=  { trapMibPrefix 1264 }


alarmHighBer NOTIFICATION-TYPE 
    OBJECTS     { currentConditionSeverity,currentConditionAffect,neEventLogTimeStamp,neEventLogIdentityTranslation } 
    STATUS      current
    DESCRIPTION   "More than 16 invalid 64B/66B sync headers within the current 125us period"
    ::=  { trapMibPrefix 1266 }


alarmPumpLaser1TempTooHigh NOTIFICATION-TYPE 
    OBJECTS     { currentConditionSeverity,currentConditionAffect,neEventLogTimeStamp,neEventLogIdentityTranslation } 
    STATUS      current
    DESCRIPTION   "TCA - Fixed high threshold of Laser 1 Temperature has been crossed."
    ::=  { trapMibPrefix 1267 }


alarmPumpLaser1TempTooLow NOTIFICATION-TYPE 
    OBJECTS     { currentConditionSeverity,currentConditionAffect,neEventLogTimeStamp,neEventLogIdentityTranslation } 
    STATUS      current
    DESCRIPTION   "TCA - Fixed low threshold of Laser 1 Temperature has been crossed."
    ::=  { trapMibPrefix 1268 }


alarmPumpLaser2TempTooHigh NOTIFICATION-TYPE 
    OBJECTS     { currentConditionSeverity,currentConditionAffect,neEventLogTimeStamp,neEventLogIdentityTranslation } 
    STATUS      current
    DESCRIPTION   "TCA - Fixed high threshold of Laser 2 Temperature has been crossed."
    ::=  { trapMibPrefix 1269 }


alarmPumpLaser2TempTooLow NOTIFICATION-TYPE 
    OBJECTS     { currentConditionSeverity,currentConditionAffect,neEventLogTimeStamp,neEventLogIdentityTranslation } 
    STATUS      current
    DESCRIPTION   "TCA - Fixed low threshold of Laser 2 Temperature has been crossed."
    ::=  { trapMibPrefix 1270 }


alarmOspfIpServerNotAvailable NOTIFICATION-TYPE 
    OBJECTS     { currentConditionSeverity,currentConditionAffect,neEventLogTimeStamp,neEventLogIdentityTranslation } 
    STATUS      current
    DESCRIPTION   "Failure of Entity on OSPFIP Server"
    ::=  { trapMibPrefix 1271 }


alarmLossOsc NOTIFICATION-TYPE 
    OBJECTS     { currentConditionSeverity,currentConditionAffect,neEventLogTimeStamp,neEventLogIdentityTranslation } 
    STATUS      current
    DESCRIPTION   "Loss Of OSC"
    ::=  { trapMibPrefix 1272 }


alarmBrPwrRxTooHigh NOTIFICATION-TYPE 
    OBJECTS     { currentConditionSeverity,currentConditionAffect,neEventLogTimeStamp,neEventLogIdentityTranslation } 
    STATUS      current
    DESCRIPTION   "Backreflection Rx too High"
    ::=  { trapMibPrefix 1273 }


alarmAseTableGenFailSignalinput NOTIFICATION-TYPE 
    OBJECTS     { currentConditionSeverity,currentConditionAffect,neEventLogTimeStamp,neEventLogIdentityTranslation } 
    STATUS      current
    DESCRIPTION   "ASE table generation failed because of detected input signal"
    ::=  { trapMibPrefix 1274 }


alarmAseTableGenFailOscMissing NOTIFICATION-TYPE 
    OBJECTS     { currentConditionSeverity,currentConditionAffect,neEventLogTimeStamp,neEventLogIdentityTranslation } 
    STATUS      current
    DESCRIPTION   "ASE table generation failed because OSC is missing"
    ::=  { trapMibPrefix 1275 }


alarmAseTableGenFailHighBackreflection NOTIFICATION-TYPE 
    OBJECTS     { currentConditionSeverity,currentConditionAffect,neEventLogTimeStamp,neEventLogIdentityTranslation } 
    STATUS      current
    DESCRIPTION   "ASE table generation failed because of too high backreflection"
    ::=  { trapMibPrefix 1276 }


alarmRamanPumpPwrTooHigh NOTIFICATION-TYPE 
    OBJECTS     { currentConditionSeverity,currentConditionAffect,neEventLogTimeStamp,neEventLogIdentityTranslation } 
    STATUS      current
    DESCRIPTION   "Pump Laser Power Fixed High Threshold Exceeded"
    ::=  { trapMibPrefix 1277 }


alarmRamanPumpPwrTooLow NOTIFICATION-TYPE 
    OBJECTS     { currentConditionSeverity,currentConditionAffect,neEventLogTimeStamp,neEventLogIdentityTranslation } 
    STATUS      current
    DESCRIPTION   "Pump Laser Power Fixed Low Threshold Exceeded"
    ::=  { trapMibPrefix 1278 }


alarmAutoPowerShutdown NOTIFICATION-TYPE 
    OBJECTS     { currentConditionSeverity,currentConditionAffect,neEventLogTimeStamp,neEventLogIdentityTranslation } 
    STATUS      current
    DESCRIPTION   "Automatic Power Shutdown"
    ::=  { trapMibPrefix 1279 }


alarmAseTableGenFailLow NOTIFICATION-TYPE 
    OBJECTS     { currentConditionSeverity,currentConditionAffect,neEventLogTimeStamp,neEventLogIdentityTranslation } 
    STATUS      current
    DESCRIPTION   "ASE table generation failed because of too low ASE level"
    ::=  { trapMibPrefix 1280 }


alarmAseLow NOTIFICATION-TYPE 
    OBJECTS     { currentConditionSeverity,currentConditionAffect,neEventLogTimeStamp,neEventLogIdentityTranslation } 
    STATUS      current
    DESCRIPTION   "Pump laser is not switched on because of too low ASE power"
    ::=  { trapMibPrefix 1281 }


alarmConfigurableOpticalOutputPowerTransmittedTooHigh NOTIFICATION-TYPE 
    OBJECTS     { currentConditionSeverity,currentConditionAffect,neEventLogTimeStamp,neEventLogIdentityTranslation } 
    STATUS      current
    DESCRIPTION   "Optical Power Transmit (output) High Threshold Exceeded"
    ::=  { trapMibPrefix 1282 }


alarmConfigurableOpticalOutputPowerTransmittedTooLow NOTIFICATION-TYPE 
    OBJECTS     { currentConditionSeverity,currentConditionAffect,neEventLogTimeStamp,neEventLogIdentityTranslation } 
    STATUS      current
    DESCRIPTION   "Optical Power Transmit (output) Low Threshold Exceeded"
    ::=  { trapMibPrefix 1283 }


alarmLosAttProgress NOTIFICATION-TYPE 
    OBJECTS     { currentConditionSeverity,currentConditionAffect,neEventLogTimeStamp,neEventLogIdentityTranslation } 
    STATUS      current
    DESCRIPTION   "Loss of Signal Attenuation finding in process"
    ::=  { trapMibPrefix 1284 }


alarmAseTableGenProgress NOTIFICATION-TYPE 
    OBJECTS     { currentConditionSeverity,currentConditionAffect,neEventLogTimeStamp,neEventLogIdentityTranslation } 
    STATUS      current
    DESCRIPTION   "ASE table is in the build process"
    ::=  { trapMibPrefix 1285 }


alarmSignalDegradeScn NOTIFICATION-TYPE 
    OBJECTS     { currentConditionSeverity,currentConditionAffect,neEventLogTimeStamp,neEventLogIdentityTranslation } 
    STATUS      current
    DESCRIPTION   "Sec/RS signal degrade alarm; related to a configurable threshold"
    ::=  { trapMibPrefix 1286 }


alarmDispertionTunningCondition NOTIFICATION-TYPE 
    OBJECTS     { currentConditionSeverity,currentConditionAffect,neEventLogTimeStamp,neEventLogIdentityTranslation } 
    STATUS      current
    DESCRIPTION   "Chromatic Dispersion Compensation In Progress"
    ::=  { trapMibPrefix 1287 }


alarmTurnupCondition NOTIFICATION-TYPE 
    OBJECTS     { currentConditionSeverity,currentConditionAffect,neEventLogTimeStamp,neEventLogIdentityTranslation } 
    STATUS      current
    DESCRIPTION   "Turnup Operation in progress"
    ::=  { trapMibPrefix 1288 }


alarmTurnupFailed NOTIFICATION-TYPE 
    OBJECTS     { currentConditionSeverity,currentConditionAffect,neEventLogTimeStamp,neEventLogIdentityTranslation } 
    STATUS      current
    DESCRIPTION   "Turnup Operation failed"
    ::=  { trapMibPrefix 1289 }


alarmFaultOnOpm NOTIFICATION-TYPE 
    OBJECTS     { currentConditionSeverity,currentConditionAffect,neEventLogTimeStamp,neEventLogIdentityTranslation } 
    STATUS      current
    DESCRIPTION   "Fault detected on OPM"
    ::=  { trapMibPrefix 1301 }


alarmOptSignalFailure NOTIFICATION-TYPE 
    OBJECTS     { currentConditionSeverity,currentConditionAffect,neEventLogTimeStamp,neEventLogIdentityTranslation } 
    STATUS      current
    DESCRIPTION   "Optical Power Transmit Signal Failure"
    ::=  { trapMibPrefix 1302 }


alarmOpmAbnormalCondition NOTIFICATION-TYPE 
    OBJECTS     { currentConditionSeverity,currentConditionAffect,neEventLogTimeStamp,neEventLogIdentityTranslation } 
    STATUS      current
    DESCRIPTION   "OPM condition is abnormal (degraded)"
    ::=  { trapMibPrefix 1303 }


alarmHwOprReachedHT NOTIFICATION-TYPE 
    OBJECTS     { currentConditionSeverity,currentConditionAffect,neEventLogTimeStamp,neEventLogIdentityTranslation } 
    STATUS      current
    DESCRIPTION   "HW OPR has reached a high thershold and could be damaged"
    ::=  { trapMibPrefix 1304 }


alarmDisabledChannelPowerTooHigh NOTIFICATION-TYPE 
    OBJECTS     { currentConditionSeverity,currentConditionAffect,neEventLogTimeStamp,neEventLogIdentityTranslation } 
    STATUS      current
    DESCRIPTION   "Optical power is not blocked when service is disabled (OPT > -25 dBm)."
    ::=  { trapMibPrefix 1305 }


alarmLossOfSignalCPort NOTIFICATION-TYPE 
    OBJECTS     { currentConditionSeverity,currentConditionAffect,neEventLogTimeStamp,neEventLogIdentityTranslation } 
    STATUS      current
    DESCRIPTION   "Loss of signal on C Port that corresponds to the network VCH via CRS"
    ::=  { trapMibPrefix 1306 }


alarmLossOfSignalNPort NOTIFICATION-TYPE 
    OBJECTS     { currentConditionSeverity,currentConditionAffect,neEventLogTimeStamp,neEventLogIdentityTranslation } 
    STATUS      current
    DESCRIPTION   "Internal N Port Failure"
    ::=  { trapMibPrefix 1307 }


alarmServerSignalFailureODU NOTIFICATION-TYPE 
    OBJECTS     { currentConditionSeverity,currentConditionAffect,neEventLogTimeStamp,neEventLogIdentityTranslation } 
    STATUS      current
    DESCRIPTION   "ODU Server Signal Failure"
    ::=  { trapMibPrefix 1308 }


alarmSignalFailureOPU NOTIFICATION-TYPE 
    OBJECTS     { currentConditionSeverity,currentConditionAffect,neEventLogTimeStamp,neEventLogIdentityTranslation } 
    STATUS      current
    DESCRIPTION   "This is a very severe signal degradation or loss"
    ::=  { trapMibPrefix 1309 }


alarmServerSignalFail NOTIFICATION-TYPE 
    OBJECTS     { currentConditionSeverity,currentConditionAffect,neEventLogTimeStamp,neEventLogIdentityTranslation } 
    STATUS      current
    DESCRIPTION   "All member ports signals have failed"
    ::=  { trapMibPrefix 1310 }


alarmServerSignalReduced NOTIFICATION-TYPE 
    OBJECTS     { currentConditionSeverity,currentConditionAffect,neEventLogTimeStamp,neEventLogIdentityTranslation } 
    STATUS      current
    DESCRIPTION   "One of the member ports signals has failed"
    ::=  { trapMibPrefix 1311 }


alarmDispersionCompensationTooLow NOTIFICATION-TYPE 
    OBJECTS     { currentConditionSeverity,currentConditionAffect,neEventLogTimeStamp,neEventLogIdentityTranslation } 
    STATUS      current
    DESCRIPTION   "Chromatic Dispersion Compensation too Low"
    ::=  { trapMibPrefix 1312 }


alarmDispersionCompensationTooHigh NOTIFICATION-TYPE 
    OBJECTS     { currentConditionSeverity,currentConditionAffect,neEventLogTimeStamp,neEventLogIdentityTranslation } 
    STATUS      current
    DESCRIPTION   "Chromatic Dispersion Compensation too High"
    ::=  { trapMibPrefix 1313 }


alarmFarEndCommFailure NOTIFICATION-TYPE 
    OBJECTS     { currentConditionSeverity,currentConditionAffect,neEventLogTimeStamp,neEventLogIdentityTranslation } 
    STATUS      current
    DESCRIPTION   "The connection to the Far End Optojack plug is dysfunctional"
    ::=  { trapMibPrefix 1315 }


alarmLinkAttenuationTooLow NOTIFICATION-TYPE 
    OBJECTS     { currentConditionSeverity,currentConditionAffect,neEventLogTimeStamp,neEventLogIdentityTranslation } 
    STATUS      current
    DESCRIPTION   "TCA - Link attenuation too low"
    ::=  { trapMibPrefix 1316 }


alarmLinkAttenuationTooHigh NOTIFICATION-TYPE 
    OBJECTS     { currentConditionSeverity,currentConditionAffect,neEventLogTimeStamp,neEventLogIdentityTranslation } 
    STATUS      current
    DESCRIPTION   "TCA - Link attenuation too high"
    ::=  { trapMibPrefix 1317 }


alarmEntityOutageIndication NOTIFICATION-TYPE 
    OBJECTS     { currentConditionSeverity,currentConditionAffect,neEventLogTimeStamp,neEventLogIdentityTranslation } 
    STATUS      current
    DESCRIPTION   "Current Path is down; TNL is outage due to its supporting CNX outage (remote as well as local)"
    ::=  { trapMibPrefix 1320 }


alarmFiberConnectionMissing NOTIFICATION-TYPE 
    OBJECTS     { currentConditionSeverity,currentConditionAffect,neEventLogTimeStamp,neEventLogIdentityTranslation } 
    STATUS      current
    DESCRIPTION   "Fiber Connection Missing"
    ::=  { trapMibPrefix 1321 }


alarmFarEndInformationMismatch NOTIFICATION-TYPE 
    OBJECTS     { currentConditionSeverity,currentConditionAffect,neEventLogTimeStamp,neEventLogIdentityTranslation } 
    STATUS      current
    DESCRIPTION   "Far End Information Mismatch"
    ::=  { trapMibPrefix 1322 }


alarmAutomaticPowerReductionForEyeSafety NOTIFICATION-TYPE 
    OBJECTS     { currentConditionSeverity,currentConditionAffect,neEventLogTimeStamp,neEventLogIdentityTranslation } 
    STATUS      current
    DESCRIPTION   "Output power is automatically reduced to eye safety limit"
    ::=  { trapMibPrefix 1325 }


alarmLossOfPilotSignal NOTIFICATION-TYPE 
    OBJECTS     { currentConditionSeverity,currentConditionAffect,neEventLogTimeStamp,neEventLogIdentityTranslation } 
    STATUS      current
    DESCRIPTION   "Loss of Pilot Signal"
    ::=  { trapMibPrefix 1326 }


alarmPumpLaser3TempTooHigh NOTIFICATION-TYPE 
    OBJECTS     { currentConditionSeverity,currentConditionAffect,neEventLogTimeStamp,neEventLogIdentityTranslation } 
    STATUS      current
    DESCRIPTION   "TCA - Fixed high threshold of Laser 3 Temperature has been crossed."
    ::=  { trapMibPrefix 1327 }


alarmPumpLaser3TempTooLow NOTIFICATION-TYPE 
    OBJECTS     { currentConditionSeverity,currentConditionAffect,neEventLogTimeStamp,neEventLogIdentityTranslation } 
    STATUS      current
    DESCRIPTION   "TCA - Fixed low threshold of Laser 3 Temperature has been crossed."
    ::=  { trapMibPrefix 1328 }


alarmPilotReceiveLevelHigh NOTIFICATION-TYPE 
    OBJECTS     { currentConditionSeverity,currentConditionAffect,neEventLogTimeStamp,neEventLogIdentityTranslation } 
    STATUS      current
    DESCRIPTION   "Pilot receive level is high"
    ::=  { trapMibPrefix 1329 }


alarmAutoShutdownStbyProtection NOTIFICATION-TYPE 
    OBJECTS     { currentConditionSeverity,currentConditionAffect,neEventLogTimeStamp,neEventLogIdentityTranslation } 
    STATUS      current
    DESCRIPTION   "Shut down of STBYH client LASER in protection configuration"
    ::=  { trapMibPrefix 1330 }


alarmDatabaseFailure NOTIFICATION-TYPE 
    OBJECTS     { currentConditionSeverity,currentConditionAffect,neEventLogTimeStamp,neEventLogIdentityTranslation } 
    STATUS      current
    DESCRIPTION   "Database Failure detect by Database Check Routine"
    ::=  { trapMibPrefix 1331 }


alarmLatencyTooHigh NOTIFICATION-TYPE 
    OBJECTS     { currentConditionSeverity,currentConditionAffect,neEventLogTimeStamp,neEventLogIdentityTranslation } 
    STATUS      current
    DESCRIPTION   "TCA -Round Trip Delay Too High"
    ::=  { trapMibPrefix 1335 }


alarmLatencyTooLow NOTIFICATION-TYPE 
    OBJECTS     { currentConditionSeverity,currentConditionAffect,neEventLogTimeStamp,neEventLogIdentityTranslation } 
    STATUS      current
    DESCRIPTION   "TCA -Round trip delay Too Low"
    ::=  { trapMibPrefix 1336 }


alarmThres15MinExceededFecBERCE NOTIFICATION-TYPE 
    OBJECTS     { currentConditionSeverity,currentConditionAffect,neEventLogTimeStamp,neEventLogIdentityTranslation } 
    STATUS      current
    DESCRIPTION   "Bit error rate before FEC 15 minutes high threshold crossed"
    ::=  { trapMibPrefix 1337 }


alarmAutoShutdownSendingLckOdu NOTIFICATION-TYPE 
    OBJECTS     { currentConditionSeverity,currentConditionAffect,neEventLogTimeStamp,neEventLogIdentityTranslation } 
    STATUS      current
    DESCRIPTION   "Auto Shutdown (ODU-LCK)"
    ::=  { trapMibPrefix 1338 }


alarmNtpNotInSync NOTIFICATION-TYPE 
    OBJECTS     { ntpSrvCurrentConditionSeverity,
                  ntpSrvCurrentConditionAffect,
                  neEventLogTimeStamp,
                  neEventLogIdentityTranslation 
                } 
    STATUS      current
    DESCRIPTION   "NTP not Synchronized"
    ::=  { trapMibPrefix 1339 }


alarmEncryptionModuleTamperDetected NOTIFICATION-TYPE 
    OBJECTS     { currentConditionSeverity,currentConditionAffect,neEventLogTimeStamp,neEventLogIdentityTranslation } 
    STATUS      current
    DESCRIPTION   "Tamper event on Encryption module"
    ::=  { trapMibPrefix 1340 }


alarmEncryptionModuleCryPasswdMissing NOTIFICATION-TYPE 
    OBJECTS     { currentConditionSeverity,currentConditionAffect,neEventLogTimeStamp,neEventLogIdentityTranslation } 
    STATUS      current
    DESCRIPTION   "Crypto Officer password missing"
    ::=  { trapMibPrefix 1341 }


alarmEncryptionModuleCryPasswdError NOTIFICATION-TYPE 
    OBJECTS     { currentConditionSeverity,currentConditionAffect,neEventLogTimeStamp,neEventLogIdentityTranslation } 
    STATUS      current
    DESCRIPTION   "3 invalid CRYPW entered; The Module refuses input of CRYPW for 10 minutes"
    ::=  { trapMibPrefix 1342 }


alarmEncryptionModuleFwpUpdateEnabled NOTIFICATION-TYPE 
    OBJECTS     { currentConditionSeverity,currentConditionAffect,neEventLogTimeStamp,neEventLogIdentityTranslation } 
    STATUS      current
    DESCRIPTION   "FWP upgrade is allowed"
    ::=  { trapMibPrefix 1343 }


alarmEncryptionModuleSelfTestStarted NOTIFICATION-TYPE 
    OBJECTS     { currentConditionSeverity,currentConditionAffect,neEventLogTimeStamp,neEventLogIdentityTranslation } 
    STATUS      current
    DESCRIPTION   "Encryption selftest running"
    ::=  { trapMibPrefix 1344 }


alarmEncryptionModuleSelfTestFail NOTIFICATION-TYPE 
    OBJECTS     { currentConditionSeverity,currentConditionAffect,neEventLogTimeStamp,neEventLogIdentityTranslation } 
    STATUS      current
    DESCRIPTION   "Noncritical selftest failed"
    ::=  { trapMibPrefix 1345 }


alarmEncryptionModuleSelfTestFailCritical NOTIFICATION-TYPE 
    OBJECTS     { currentConditionSeverity,currentConditionAffect,neEventLogTimeStamp,neEventLogIdentityTranslation } 
    STATUS      current
    DESCRIPTION   "Encrytion critical selftest failed"
    ::=  { trapMibPrefix 1346 }


alarmEncryptionPortAuthPasswdMissing NOTIFICATION-TYPE 
    OBJECTS     { currentConditionSeverity,currentConditionAffect,neEventLogTimeStamp,neEventLogIdentityTranslation } 
    STATUS      current
    DESCRIPTION   "Authentication password missing"
    ::=  { trapMibPrefix 1350 }


alarmEncryptionPortMaxKeyExchgFailuresReachedIs NOTIFICATION-TYPE 
    OBJECTS     { currentConditionSeverity,currentConditionAffect,neEventLogTimeStamp,neEventLogIdentityTranslation } 
    STATUS      current
    DESCRIPTION   "Maximum Key exchange failure count reached"
    ::=  { trapMibPrefix 1351 }


alarmEncryptionPortMaxKeyExchgFailuresReachedOos NOTIFICATION-TYPE 
    OBJECTS     { currentConditionSeverity,currentConditionAffect,neEventLogTimeStamp,neEventLogIdentityTranslation } 
    STATUS      current
    DESCRIPTION   "Session Key missing"
    ::=  { trapMibPrefix 1352 }


alarmEncryptionPortEncryptionSwitchedOff NOTIFICATION-TYPE 
    OBJECTS     { currentConditionSeverity,currentConditionAffect,neEventLogTimeStamp,neEventLogIdentityTranslation } 
    STATUS      current
    DESCRIPTION   "Encryption switched off"
    ::=  { trapMibPrefix 1353 }


alarmEncryptionPortKeyExchangedForced NOTIFICATION-TYPE 
    OBJECTS     { currentConditionSeverity,currentConditionAffect,neEventLogTimeStamp,neEventLogIdentityTranslation } 
    STATUS      current
    DESCRIPTION   "Encryption Key exchanged forced"
    ::=  { trapMibPrefix 1354 }


alarmEncryptionPortEncryptionSwitchOffEnabled NOTIFICATION-TYPE 
    OBJECTS     { currentConditionSeverity,currentConditionAffect,neEventLogTimeStamp,neEventLogIdentityTranslation } 
    STATUS      current
    DESCRIPTION   "User enabled switching encryption off"
    ::=  { trapMibPrefix 1355 }


alarmEncryptionPortKeyInitExchgMissed NOTIFICATION-TYPE 
    OBJECTS     { currentConditionSeverity,currentConditionAffect,neEventLogTimeStamp,neEventLogIdentityTranslation } 
    STATUS      current
    DESCRIPTION   "The initial successful key exchange has not be completed"
    ::=  { trapMibPrefix 1356 }


alarmRoundTripDelayTooHigh NOTIFICATION-TYPE 
    OBJECTS     { currentConditionSeverity,currentConditionAffect,neEventLogTimeStamp,neEventLogIdentityTranslation } 
    STATUS      current
    DESCRIPTION   "Round Trip Delay High Threshold Exceeded"
    ::=  { trapMibPrefix 1380 }


alarmRoundTripDelayTooLow NOTIFICATION-TYPE 
    OBJECTS     { currentConditionSeverity,currentConditionAffect,neEventLogTimeStamp,neEventLogIdentityTranslation } 
    STATUS      current
    DESCRIPTION   "Round Trip Delay Low Threshold Exceeded"
    ::=  { trapMibPrefix 1381 }


alarmNtpForSchedEqlzRequired NOTIFICATION-TYPE 
    OBJECTS     { currentConditionSeverity,currentConditionAffect,neEventLogTimeStamp,neEventLogIdentityTranslation } 
    STATUS      current
    DESCRIPTION   "Scheduled Equalization requires NTP to be enabled"
    ::=  { trapMibPrefix 1386 }


alarmAirDustFilterClogged NOTIFICATION-TYPE 
    OBJECTS     { currentConditionSeverity,currentConditionAffect,neEventLogTimeStamp,neEventLogIdentityTranslation } 
    STATUS      current
    DESCRIPTION   "Air dust filter clogged"
    ::=  { trapMibPrefix 1385 }


alarmOscOpticalPowerControlFailHigh NOTIFICATION-TYPE 
    OBJECTS     { currentConditionSeverity,currentConditionAffect,neEventLogTimeStamp,neEventLogIdentityTranslation } 
    STATUS      current
    DESCRIPTION   "OSC Optical Power Control Failure High Threshold"
    ::=  { trapMibPrefix 1387 }


alarmOscOpticalPowerControlFailLow NOTIFICATION-TYPE 
    OBJECTS     { currentConditionSeverity,currentConditionAffect,neEventLogTimeStamp,neEventLogIdentityTranslation } 
    STATUS      current
    DESCRIPTION   "OSC Optical Power Control Failure Low Threshold"
    ::=  { trapMibPrefix 1388 }


alarmAmplifierAbnormal NOTIFICATION-TYPE 
    OBJECTS     { currentConditionSeverity,currentConditionAffect,neEventLogTimeStamp,neEventLogIdentityTranslation } 
    STATUS      current
    DESCRIPTION   "Output of amplifier is abnormal"
    ::=  { trapMibPrefix 1389 }


alarmAseTableGenFailPilot NOTIFICATION-TYPE 
    OBJECTS     { currentConditionSeverity,currentConditionAffect,neEventLogTimeStamp,neEventLogIdentityTranslation } 
    STATUS      current
    DESCRIPTION   "ASE table generation failed because PILOT is missing"
    ::=  { trapMibPrefix 1390 }


alarmPumpLaser4TempTooHigh NOTIFICATION-TYPE 
    OBJECTS     { currentConditionSeverity,currentConditionAffect,neEventLogTimeStamp,neEventLogIdentityTranslation } 
    STATUS      current
    DESCRIPTION   "TCA - Fixed high threshold of Laser 4 Temperature has been crossed."
    ::=  { trapMibPrefix 1391 }


alarmPumpLaser4TempTooLow NOTIFICATION-TYPE 
    OBJECTS     { currentConditionSeverity,currentConditionAffect,neEventLogTimeStamp,neEventLogIdentityTranslation } 
    STATUS      current
    DESCRIPTION   "TCA - Fixed low threshold of Laser 4 Temperature has been crossed."
    ::=  { trapMibPrefix 1392 }


alarmFwdAseTableFailPilot NOTIFICATION-TYPE 
    OBJECTS     { currentConditionSeverity,currentConditionAffect,neEventLogTimeStamp,neEventLogIdentityTranslation } 
    STATUS      current
    DESCRIPTION   "Force of BWD Raman pilot for FWD ASE Table Build Failed"
    ::=  { trapMibPrefix 1393 }


alarmFwdAseTableOnPilot NOTIFICATION-TYPE 
    OBJECTS     { currentConditionSeverity,currentConditionAffect,neEventLogTimeStamp,neEventLogIdentityTranslation } 
    STATUS      current
    DESCRIPTION   "Force the BWD Raman Pilot on to allow building of FWD Raman ASE Table"
    ::=  { trapMibPrefix 1394 }


alarmInputVoltageFailurePort1 NOTIFICATION-TYPE 
    OBJECTS     { currentConditionSeverity,currentConditionAffect,neEventLogTimeStamp,neEventLogIdentityTranslation } 
    STATUS      current
    DESCRIPTION   "Input Voltage Failed to power input 1 or A"
    ::=  { trapMibPrefix 1395 }


alarmInputVoltageFailurePort2 NOTIFICATION-TYPE 
    OBJECTS     { currentConditionSeverity,currentConditionAffect,neEventLogTimeStamp,neEventLogIdentityTranslation } 
    STATUS      current
    DESCRIPTION   "Input Voltage Failed to Power input 2 or B"
    ::=  { trapMibPrefix 1396 }


alarmXfpDecisionThresSetFailed NOTIFICATION-TYPE 
    OBJECTS     { currentConditionSeverity,currentConditionAffect,neEventLogTimeStamp,neEventLogIdentityTranslation } 
    STATUS      current
    DESCRIPTION   "Decision threshold setting failed"
    ::=  { trapMibPrefix 1397 }


alarmNtpSrvOosDsbld NOTIFICATION-TYPE
    OBJECTS     { ntpSrvCurrentConditionSeverity,
                  ntpSrvCurrentConditionAffect,
                  neEventLogTimeStamp,
                  neEventLogIdentityTranslation }
    STATUS      current
    DESCRIPTION "The NTP server is in Out Of Service - Disabled state."
	::=  { trapMibPrefix 1398 }
	

alarmThres15MinExceededPhysConvSE NOTIFICATION-TYPE 
    OBJECTS     { currentConditionSeverity,currentConditionAffect,neEventLogTimeStamp,neEventLogIdentityTranslation } 
    STATUS      current
    DESCRIPTION   "Sync Header Errors Physical Coding Layer 15 Minute Threshold Exceeded"
    ::=  { trapMibPrefix 1399 }


alarmThres15MinExceededPhysConvESTX NOTIFICATION-TYPE 
    OBJECTS     { currentConditionSeverity,currentConditionAffect,neEventLogTimeStamp,neEventLogIdentityTranslation } 
    STATUS      current
    DESCRIPTION   "Tx Errored Seconds Physical Coding Layer"
    ::=  { trapMibPrefix 1400 }


alarmThres15MinExceededPhysConvCVTX NOTIFICATION-TYPE 
    OBJECTS     { currentConditionSeverity,currentConditionAffect,neEventLogTimeStamp,neEventLogIdentityTranslation } 
    STATUS      current
    DESCRIPTION   "Tx Coding Violations Physical Coding Layer"
    ::=  { trapMibPrefix 1401 }


alarmThres15MinExceededPhysConvSETX NOTIFICATION-TYPE 
    OBJECTS     { currentConditionSeverity,currentConditionAffect,neEventLogTimeStamp,neEventLogIdentityTranslation } 
    STATUS      current
    DESCRIPTION   "Tx Sync Header Errors Physical Coding Layer 15 Minute Threshold Exceeded"
    ::=  { trapMibPrefix 1402 }


alarmPrbsRcvActivated NOTIFICATION-TYPE 
    OBJECTS     { currentConditionSeverity,currentConditionAffect,neEventLogTimeStamp,neEventLogIdentityTranslation } 
    STATUS      current
    DESCRIPTION   "PRBS Receive Activated"
    ::=  { trapMibPrefix 1403 }


alarmPrbsTrmtActivated NOTIFICATION-TYPE 
    OBJECTS     { currentConditionSeverity,currentConditionAffect,neEventLogTimeStamp,neEventLogIdentityTranslation } 
    STATUS      current
    DESCRIPTION   "PRBS Transmit Activated"
    ::=  { trapMibPrefix 1404 }


alarmPrbsLossOfSeqSynch NOTIFICATION-TYPE 
    OBJECTS     { currentConditionSeverity,currentConditionAffect,neEventLogTimeStamp,neEventLogIdentityTranslation } 
    STATUS      current
    DESCRIPTION   "Loss of PRBS Pattern"
    ::=  { trapMibPrefix 1405 }


alarmOpuClientSignalFail NOTIFICATION-TYPE 
    OBJECTS     { currentConditionSeverity,currentConditionAffect,neEventLogTimeStamp,neEventLogIdentityTranslation } 
    STATUS      current
    DESCRIPTION   "OPU Client Signal Fail"
    ::=  { trapMibPrefix 1406 }


alarmLossOfTestSeqSynchOpu NOTIFICATION-TYPE 
    OBJECTS     { currentConditionSeverity,currentConditionAffect,neEventLogTimeStamp,neEventLogIdentityTranslation } 
    STATUS      current
    DESCRIPTION   "Loss of test Sequence Synchronization at OPU layer"
    ::=  { trapMibPrefix 1407 }


alarmAutoShutdownOpuClientSignalFail NOTIFICATION-TYPE 
    OBJECTS     { currentConditionSeverity,currentConditionAffect,neEventLogTimeStamp,neEventLogIdentityTranslation } 
    STATUS      current
    DESCRIPTION   "Automatic Shutdown - Client Signal Fail transmit (LKDO-CSF)"
    ::=  { trapMibPrefix 1408 }


alarmLocalOscTemperatureTooLow NOTIFICATION-TYPE 
    OBJECTS     { currentConditionSeverity,currentConditionAffect,neEventLogTimeStamp,neEventLogIdentityTranslation } 
    STATUS      current
    DESCRIPTION   "Rx Laser used for Local Oscillator Temperature Low"
    ::=  { trapMibPrefix 1409 }


alarmLocalOscTemperatureTooHigh NOTIFICATION-TYPE 
    OBJECTS     { currentConditionSeverity,currentConditionAffect,neEventLogTimeStamp,neEventLogIdentityTranslation } 
    STATUS      current
    DESCRIPTION   "Rx Laser used for Local Oscillator Temperature High"
    ::=  { trapMibPrefix 1410 }


alarmDifferentialGroupDelayTooHigh NOTIFICATION-TYPE 
    OBJECTS     { currentConditionSeverity,currentConditionAffect,neEventLogTimeStamp,neEventLogIdentityTranslation } 
    STATUS      current
    DESCRIPTION   "Differential Group Delay too High"
    ::=  { trapMibPrefix 1412 }


alarmChromaticDispersionTooLow NOTIFICATION-TYPE 
    OBJECTS     { currentConditionSeverity,currentConditionAffect,neEventLogTimeStamp,neEventLogIdentityTranslation } 
    STATUS      current
    DESCRIPTION   "Chromatic Dispersion too Low"
    ::=  { trapMibPrefix 1413 }


alarmChromaticDispersionTooHigh NOTIFICATION-TYPE 
    OBJECTS     { currentConditionSeverity,currentConditionAffect,neEventLogTimeStamp,neEventLogIdentityTranslation } 
    STATUS      current
    DESCRIPTION   "Chromatic Dispersion too High"
    ::=  { trapMibPrefix 1414 }


alarmSignalToNoiseRatioTooLow NOTIFICATION-TYPE 
    OBJECTS     { currentConditionSeverity,currentConditionAffect,neEventLogTimeStamp,neEventLogIdentityTranslation } 
    STATUS      current
    DESCRIPTION   "Signal-to-Noise Ratio Low Threshold Exceeded"
    ::=  { trapMibPrefix 1415 }


alarmLocalOscLevelAbnormal NOTIFICATION-TYPE 
    OBJECTS     { currentConditionSeverity,currentConditionAffect,neEventLogTimeStamp,neEventLogIdentityTranslation } 
    STATUS      current
    DESCRIPTION   "Rx Laser Current Level Abnormal (used for Local Oscillator)"
    ::=  { trapMibPrefix 1416 }


alarmCarrierFreqOffsetTooLow NOTIFICATION-TYPE 
    OBJECTS     { currentConditionSeverity,currentConditionAffect,neEventLogTimeStamp,neEventLogIdentityTranslation } 
    STATUS      current
    DESCRIPTION   "Carrier Frequency Offset too Low"
    ::=  { trapMibPrefix 1417 }


alarmCarrierFreqOffsetTooHigh NOTIFICATION-TYPE 
    OBJECTS     { currentConditionSeverity,currentConditionAffect,neEventLogTimeStamp,neEventLogIdentityTranslation } 
    STATUS      current
    DESCRIPTION   "Carrier Frequency Offset too High"
    ::=  { trapMibPrefix 1418 }


alarmLossOfLane NOTIFICATION-TYPE 
    OBJECTS     { currentConditionSeverity,currentConditionAffect,neEventLogTimeStamp,neEventLogIdentityTranslation } 
    STATUS      current
    DESCRIPTION   "Loss of Lane Alignment"
    ::=  { trapMibPrefix 1419 }


alarmServerSignalFailureODUcrs NOTIFICATION-TYPE 
    OBJECTS     { currentConditionSeverity,currentConditionAffect,neEventLogTimeStamp,neEventLogIdentityTranslation } 
    STATUS      current
    DESCRIPTION   "SSF between entities across the ODU cross connect"
    ::=  { trapMibPrefix 1420 }


alarmAutoShutdownSendingOciOdu NOTIFICATION-TYPE 
    OBJECTS     { currentConditionSeverity,currentConditionAffect,neEventLogTimeStamp,neEventLogIdentityTranslation } 
    STATUS      current
    DESCRIPTION   "Auto Shutdown (ODU-OCI)"
    ::=  { trapMibPrefix 1421 }


alarmOduTribMsiMismatch NOTIFICATION-TYPE 
    OBJECTS     { currentConditionSeverity,currentConditionAffect,neEventLogTimeStamp,neEventLogIdentityTranslation } 
    STATUS      current
    DESCRIPTION   "Tributary Port no and ODTU type do not match in provisioned time slots"
    ::=  { trapMibPrefix 1422 }


alarmChannelMismatch NOTIFICATION-TYPE 
    OBJECTS     { currentConditionSeverity,currentConditionAffect,neEventLogTimeStamp,neEventLogIdentityTranslation } 
    STATUS      current
    DESCRIPTION   "Channel provisioning incompatible with associated port configuration"
    ::=  { trapMibPrefix 1423 }


alarmEqlzAdjust NOTIFICATION-TYPE 
    STATUS      current
    DESCRIPTION   "Channel power adjustment is in progress"
    ::=  { trapMibPrefix 1424 }


alarmHwDegrade NOTIFICATION-TYPE 
    STATUS      current
    DESCRIPTION   "HW operation is degraded by a HW fault, but traffic is unaffected."
    ::=  { trapMibPrefix 1425 }


alarmHwInitializing NOTIFICATION-TYPE 
    STATUS      current
    DESCRIPTION   "Hardware is Initializing"
    ::=  { trapMibPrefix 1426 }


alarmAmpFailure NOTIFICATION-TYPE 
    STATUS      current
    DESCRIPTION   "SGEO-AMP is raised at a dependent entity due to an AMP auto shutdown condition at the associated supporting entity."
    ::=  { trapMibPrefix 1427 }


alarmAutoAmpShutdown NOTIFICATION-TYPE 
    STATUS      current
    DESCRIPTION   "Amplifier Auto Shutdown"
    ::=  { trapMibPrefix 1428 }


alarmFiberConnLos NOTIFICATION-TYPE 
    STATUS      current
    DESCRIPTION   "Fiber Connection Loss of Signal"
    ::=  { trapMibPrefix 1429 }


alarmFiberConnOptFault NOTIFICATION-TYPE 
    STATUS      current
    DESCRIPTION   "Fiber connection transmit optical power failure."
    ::=  { trapMibPrefix 1430 }


alarmFiberConnInvalid NOTIFICATION-TYPE 
    STATUS      current
    DESCRIPTION   "The fiber connection is in violation of the fiber connection rules."
    ::=  { trapMibPrefix 1431 }


alarmFiberConnMismatch NOTIFICATION-TYPE 
    STATUS      current
    DESCRIPTION   "The fiber connection does not match the existing fiber-map in database."
    ::=  { trapMibPrefix 1432 }


alarmFiberConnCommError NOTIFICATION-TYPE 
    STATUS      current
    DESCRIPTION   "Fiber Connection Communications Fault"
    ::=  { trapMibPrefix 1433 }


alarmFiberConnProtocolFailure NOTIFICATION-TYPE 
    STATUS      current
    DESCRIPTION   "Fiber Connection Protocol Fault"
    ::=  { trapMibPrefix 1434 }


alarmFiberConnDataFailure NOTIFICATION-TYPE 
    STATUS      current
    DESCRIPTION   "Fiber Connection Data Fault"
    ::=  { trapMibPrefix 1435 }


alarmFiberAttenuationHigh NOTIFICATION-TYPE 
    STATUS      current
    DESCRIPTION   "Fiber Connection Attenuation High"
    ::=  { trapMibPrefix 1436 }


alarmFiberConnInvalidTx NOTIFICATION-TYPE 
    STATUS      current
    DESCRIPTION   "The fiber connection is in violation of the fiber connection rules."
    ::=  { trapMibPrefix 1437 }


alarmFiberConnMismatchTx NOTIFICATION-TYPE 
    STATUS      current
    DESCRIPTION   "The fiber connection does not match the existing fiber-map in database."
    ::=  { trapMibPrefix 1438 }


alarmFiberAttenuationHighTx NOTIFICATION-TYPE 
    STATUS      current
    DESCRIPTION   "Fiber Connection Attenuation High Tx"
    ::=  { trapMibPrefix 1439 }


alarmSwitchToDuplexInhibited NOTIFICATION-TYPE 
    OBJECTS     { currentConditionSeverity,currentConditionAffect,neEventLogTimeStamp,neEventLogIdentityTranslation } 
    STATUS      current
    DESCRIPTION   "Switch-Over to Partner Controller inhibited"
    ::=  { trapMibPrefix 1440 }


alarmMeaSwRevision NOTIFICATION-TYPE 
    OBJECTS     { currentConditionSeverity,currentConditionAffect,neEventLogTimeStamp,neEventLogIdentityTranslation } 
    STATUS      current
    DESCRIPTION   "Mismatch of SW Revision"
    ::=  { trapMibPrefix 1441 }


alarmDbReplicationIncompleted NOTIFICATION-TYPE 
    OBJECTS     { currentConditionSeverity,currentConditionAffect,neEventLogTimeStamp,neEventLogIdentityTranslation } 
    STATUS      current
    DESCRIPTION   "DB Replication Incomplete"
    ::=  { trapMibPrefix 1442 }


alarmBackupNotResponding NOTIFICATION-TYPE 
    OBJECTS     { currentConditionSeverity,currentConditionAffect,neEventLogTimeStamp,neEventLogIdentityTranslation } 
    STATUS      current
    DESCRIPTION   "Not Responding"
    ::=  { trapMibPrefix 1443 }


alarmBackupForcedToHalt NOTIFICATION-TYPE 
    OBJECTS     { currentConditionSeverity,currentConditionAffect,neEventLogTimeStamp,neEventLogIdentityTranslation } 
    STATUS      current
    DESCRIPTION   "Forced Halt"
    ::=  { trapMibPrefix 1444 }


alarmDuplexLinkFailure NOTIFICATION-TYPE 
    OBJECTS     { currentConditionSeverity,currentConditionAffect,neEventLogTimeStamp,neEventLogIdentityTranslation } 
    STATUS      current
    DESCRIPTION   "Controller Protection Link Failure"
    ::=  { trapMibPrefix 1445 }


alarmProvPayloadMismatch NOTIFICATION-TYPE 
    OBJECTS     { currentConditionSeverity,currentConditionAffect,neEventLogTimeStamp,neEventLogIdentityTranslation } 
    STATUS      current
    DESCRIPTION   "Provisioning payload mismatch alarm"
    ::=  { trapMibPrefix 1446 }


alarmAutoShutdownOpuFlxCSF NOTIFICATION-TYPE 
    OBJECTS     { currentConditionSeverity,currentConditionAffect,neEventLogTimeStamp,neEventLogIdentityTranslation } 
    STATUS      current
    DESCRIPTION   "Automatic Shutdown - Client Signal Fail transmit (LKDO-CSF)"
    ::=  { trapMibPrefix 1447 }


alarmLogicalLanesSkewTooHigh NOTIFICATION-TYPE 
    OBJECTS     { currentConditionSeverity,currentConditionAffect,neEventLogTimeStamp,neEventLogIdentityTranslation } 
    STATUS      current
    DESCRIPTION   "Skew between the farthest apart lanes High Threshold Exceeded"
    ::=  { trapMibPrefix 1448 }


alarmFiberAttenuationCond NOTIFICATION-TYPE 
    STATUS      current
    DESCRIPTION   "Fiber Connection High Fiber Attenuation Condition"
    ::=  { trapMibPrefix 1449 }


alarmLaserOnDelay NOTIFICATION-TYPE 
    OBJECTS     { currentConditionSeverity,currentConditionAffect,neEventLogTimeStamp,neEventLogIdentityTranslation } 
    STATUS      current
    DESCRIPTION   "Laser in process of turning on"
    ::=  { trapMibPrefix 1450 }


alarmAutoShutdownTxRxLasersDueToHighTemp NOTIFICATION-TYPE 
    OBJECTS     { currentConditionSeverity,currentConditionAffect,neEventLogTimeStamp,neEventLogIdentityTranslation } 
    STATUS      current
    DESCRIPTION   "Facility autonomously shut down with Transmitter and Receiver off due to temperature."
    ::=  { trapMibPrefix 1451 }


alarmAutoShutdownAmpAps NOTIFICATION-TYPE 
    OBJECTS     { currentConditionSeverity,currentConditionAffect,neEventLogTimeStamp,neEventLogIdentityTranslation } 
    STATUS      current
    DESCRIPTION   "Auto Shutdown on Network Tx fiber due to LOS on Network Rx fiber (AMP-APS enabled)"
    ::=  { trapMibPrefix 1459 }


alarmTunnelAbnormal NOTIFICATION-TYPE 
    OBJECTS     { currentConditionSeverity,currentConditionAffect,neEventLogTimeStamp,neEventLogIdentityTranslation } 
    STATUS      current
    DESCRIPTION   "Tunnel is allowed to perform all of its provisioned functions, but at a degraded level."
    ::=  { trapMibPrefix 1460 }



transientThres1DayExceededPhysConvES NOTIFICATION-TYPE 
    OBJECTS     { entityIndex,neEventLogTimeStamp,neEventLogIdentityTranslation } 
    STATUS      current
    DESCRIPTION   "Errored Seconds Physical Coding Layer"
    ::=  { trapMibPrefix 3001 }


transientThres1DayExceededPhysConvCV NOTIFICATION-TYPE 
    OBJECTS     { entityIndex,neEventLogTimeStamp,neEventLogIdentityTranslation } 
    STATUS      current
    DESCRIPTION   "Coding Violations Physical Coding Layer"
    ::=  { trapMibPrefix 3002 }


transientThres1DayExceededPhysConvDE NOTIFICATION-TYPE 
    OBJECTS     { entityIndex,neEventLogTimeStamp,neEventLogIdentityTranslation } 
    STATUS      current
    DESCRIPTION   "Disparity Errors Physical Coding Layer"
    ::=  { trapMibPrefix 3003 }


transientThres1DayExceededPhysConvCVDE NOTIFICATION-TYPE 
    OBJECTS     { entityIndex,neEventLogTimeStamp,neEventLogIdentityTranslation } 
    STATUS      current
    DESCRIPTION   "Coding Violations And Disparity Errors Physical Coding Layer"
    ::=  { trapMibPrefix 3004 }


transientMin15RecordsAvailable NOTIFICATION-TYPE 
    OBJECTS     { entityIndex,neEventLogTimeStamp,neEventLogIdentityTranslation } 
    STATUS      current
    DESCRIPTION   "Performance Monitoring Server has collected all 15-MIN records."
    ::=  { trapMibPrefix 3005 }


transientDay1RecordsAvailable NOTIFICATION-TYPE 
    OBJECTS     { entityIndex,neEventLogTimeStamp,neEventLogIdentityTranslation } 
    STATUS      current
    DESCRIPTION   "Performance Monitoring Server has collected all 1-DAY records."
    ::=  { trapMibPrefix 3006 }


transientWeek1RecordsAvailable NOTIFICATION-TYPE 
    OBJECTS     { entityIndex,neEventLogTimeStamp,neEventLogIdentityTranslation } 
    STATUS      current
    DESCRIPTION   "Performance Monitoring Server has collected all 1-WEEK records."
    ::=  { trapMibPrefix 3007 }


transientNeColdStart NOTIFICATION-TYPE 
    OBJECTS     { entityIndex,neEventLogTimeStamp,neEventLogIdentityTranslation } 
    STATUS      current
    DESCRIPTION   "Cold start"
    ::=  { trapMibPrefix 3008 }


transientWorkingSwitchedtoProtection NOTIFICATION-TYPE 
    OBJECTS     { entityIndex,neEventLogTimeStamp,neEventLogIdentityTranslation } 
    STATUS      current
    DESCRIPTION   "Working Traffic (ACT) switched from WKG facility to PROTN facility automatically, sent by WKG."
    ::=  { trapMibPrefix 3009 }


transientWorkingSwitchedBacktoWorking NOTIFICATION-TYPE 
    OBJECTS     { entityIndex,neEventLogTimeStamp,neEventLogIdentityTranslation } 
    STATUS      current
    DESCRIPTION   "Working Traffic (ACT) switched back to Working facility from Protection facility automatically: sent by PROTN."
    ::=  { trapMibPrefix 3010 }


transientManualWorkingSwitchedtoProtection NOTIFICATION-TYPE 
    OBJECTS     { entityIndex,neEventLogTimeStamp,neEventLogIdentityTranslation } 
    STATUS      current
    DESCRIPTION   "Working Traffic (ACT) switched from Working facility to Protection facility manually: sent by WKG."
    ::=  { trapMibPrefix 3011 }


transientManualWorkingSwitchedBacktoWorking NOTIFICATION-TYPE 
    OBJECTS     { entityIndex,neEventLogTimeStamp,neEventLogIdentityTranslation } 
    STATUS      current
    DESCRIPTION   "Working Traffic (ACT) switched back to WKG facility from PROTN facility manually: sent by PROTN."
    ::=  { trapMibPrefix 3012 }


transientForcedWorkingSwitchedBacktoWorking NOTIFICATION-TYPE 
    OBJECTS     { entityIndex,neEventLogTimeStamp,neEventLogIdentityTranslation } 
    STATUS      current
    DESCRIPTION   "Forced Working Switched Back to Working"
    ::=  { trapMibPrefix 3013 }


transientForcedWorkingSwitchedBacktoProtection NOTIFICATION-TYPE 
    OBJECTS     { entityIndex,neEventLogTimeStamp,neEventLogIdentityTranslation } 
    STATUS      current
    DESCRIPTION   "Forced Working Switched Back to Protection"
    ::=  { trapMibPrefix 3014 }


transientThres1DayExceededBytesTx NOTIFICATION-TYPE 
    OBJECTS     { entityIndex,neEventLogTimeStamp,neEventLogIdentityTranslation } 
    STATUS      deprecated
    DESCRIPTION   "Byte Tx Exceeded Day Threshold"
    ::=  { trapMibPrefix 3015 }


transientThres1DayExceededFecCE NOTIFICATION-TYPE 
    OBJECTS     { entityIndex,neEventLogTimeStamp,neEventLogIdentityTranslation } 
    STATUS      current
    DESCRIPTION   "FEC Corrected Errors Exceeded Day Threshold"
    ::=  { trapMibPrefix 3016 }


transientThres1DayExceededFecUBE NOTIFICATION-TYPE 
    OBJECTS     { entityIndex,neEventLogTimeStamp,neEventLogIdentityTranslation } 
    STATUS      current
    DESCRIPTION   "FEC Uncorrected Block Error 1 Day Threshold Exceeded"
    ::=  { trapMibPrefix 3017 }


transientThres1DayExceededFecES NOTIFICATION-TYPE 
    OBJECTS     { entityIndex,neEventLogTimeStamp,neEventLogIdentityTranslation } 
    STATUS      current
    DESCRIPTION   "Errored Seconds FEC OTU Monitoring"
    ::=  { trapMibPrefix 3018 }


transientThres1DayExceededFecSES NOTIFICATION-TYPE 
    OBJECTS     { entityIndex,neEventLogTimeStamp,neEventLogIdentityTranslation } 
    STATUS      current
    DESCRIPTION   "Severely Errored Seconds FEC 1 Day Threshold Exceeded"
    ::=  { trapMibPrefix 3019 }


transientThres1DayExceededMuxES NOTIFICATION-TYPE 
    OBJECTS     { entityIndex,neEventLogTimeStamp,neEventLogIdentityTranslation } 
    STATUS      current
    DESCRIPTION   "Multiplex Error Second High Threshold 1 Day crossed"
    ::=  { trapMibPrefix 3020 }


transientThres1DayExceededMuxSES NOTIFICATION-TYPE 
    OBJECTS     { entityIndex,neEventLogTimeStamp,neEventLogIdentityTranslation } 
    STATUS      current
    DESCRIPTION   "Severely Errored Second Mux 1 Day Threshold Exceeded"
    ::=  { trapMibPrefix 3021 }


transientTopologyDataInvalid NOTIFICATION-TYPE 
    OBJECTS     { entityIndex,neEventLogTimeStamp,neEventLogIdentityTranslation } 
    STATUS      current
    DESCRIPTION   "Topology Detection Data invalid"
    ::=  { trapMibPrefix 3022 }


transientCopyFileFailNotExist NOTIFICATION-TYPE 
    OBJECTS     { entityIndex,neEventLogTimeStamp,neEventLogIdentityTranslation } 
    STATUS      current
    DESCRIPTION   "Copy File: File Does Not Exist"
    ::=  { trapMibPrefix 3023 }


transientCopyFileConnectionFail NOTIFICATION-TYPE 
    OBJECTS     { entityIndex,neEventLogTimeStamp,neEventLogIdentityTranslation } 
    STATUS      current
    DESCRIPTION   "Copy File: File Transfer Connect Fail, Server not reachable."
    ::=  { trapMibPrefix 3024 }


transientCopyFileLoginFail NOTIFICATION-TYPE 
    OBJECTS     { entityIndex,neEventLogTimeStamp,neEventLogIdentityTranslation } 
    STATUS      current
    DESCRIPTION   "Copy File: Server Login Fail"
    ::=  { trapMibPrefix 3025 }


transientCopyFileSpaceFail NOTIFICATION-TYPE 
    OBJECTS     { entityIndex,neEventLogTimeStamp,neEventLogIdentityTranslation } 
    STATUS      current
    DESCRIPTION   "Copy File: Insufficient Space for File"
    ::=  { trapMibPrefix 3026 }


transientCopyFileProtocolFail NOTIFICATION-TYPE 
    OBJECTS     { entityIndex,neEventLogTimeStamp,neEventLogIdentityTranslation } 
    STATUS      current
    DESCRIPTION   "Copy File: File Transfer Protocol Fail"
    ::=  { trapMibPrefix 3027 }


transientCopyFileAccessDenied NOTIFICATION-TYPE 
    OBJECTS     { entityIndex,neEventLogTimeStamp,neEventLogIdentityTranslation } 
    STATUS      current
    DESCRIPTION   "Copy File: File Access Denied"
    ::=  { trapMibPrefix 3028 }


transientCopyFileChecksumFail NOTIFICATION-TYPE 
    OBJECTS     { entityIndex,neEventLogTimeStamp,neEventLogIdentityTranslation } 
    STATUS      current
    DESCRIPTION   "Copy File: File Checksum Fail"
    ::=  { trapMibPrefix 3029 }


transientCopyFileTransferStart NOTIFICATION-TYPE 
    OBJECTS     { entityIndex,neEventLogTimeStamp,neEventLogIdentityTranslation } 
    STATUS      current
    DESCRIPTION   "Copy File: 00.0% Complete"
    ::=  { trapMibPrefix 3030 }


transientCopyFileTransferInProgress NOTIFICATION-TYPE 
    OBJECTS     { entityIndex,neEventLogTimeStamp,neEventLogIdentityTranslation } 
    STATUS      current
    DESCRIPTION   "Copy File Partial"
    ::=  { trapMibPrefix 3031 }


transientCopyFileTransferComplete NOTIFICATION-TYPE 
    OBJECTS     { entityIndex,neEventLogTimeStamp,neEventLogIdentityTranslation } 
    STATUS      current
    DESCRIPTION   "Copy File: 100 % Complete"
    ::=  { trapMibPrefix 3032 }


transientLocalCopyMemFail NOTIFICATION-TYPE 
    OBJECTS     { entityIndex,neEventLogTimeStamp,neEventLogIdentityTranslation } 
    STATUS      current
    DESCRIPTION   "Local copy file failed"
    ::=  { trapMibPrefix 3033 }


transientLocalCopyFileStarted NOTIFICATION-TYPE 
    OBJECTS     { entityIndex,neEventLogTimeStamp,neEventLogIdentityTranslation } 
    STATUS      current
    DESCRIPTION   "Local copy file started"
    ::=  { trapMibPrefix 3034 }


transientLocalCopyMemComplted NOTIFICATION-TYPE 
    OBJECTS     { entityIndex,neEventLogTimeStamp,neEventLogIdentityTranslation } 
    STATUS      current
    DESCRIPTION   "Local copy file completed"
    ::=  { trapMibPrefix 3035 }


transientSoftwareActivationFail NOTIFICATION-TYPE 
    OBJECTS     { entityIndex,neEventLogTimeStamp,neEventLogIdentityTranslation } 
    STATUS      current
    DESCRIPTION   "Software Activation /Reversion Failed."
    ::=  { trapMibPrefix 3037 }


transientDatabaseActivationFail NOTIFICATION-TYPE 
    OBJECTS     { entityIndex,neEventLogTimeStamp,neEventLogIdentityTranslation } 
    STATUS      current
    DESCRIPTION   "DBS Activation / Restoration Failed."
    ::=  { trapMibPrefix 3038 }


transientDatabaseActivation NOTIFICATION-TYPE 
    OBJECTS     { entityIndex,neEventLogTimeStamp,neEventLogIdentityTranslation } 
    STATUS      current
    DESCRIPTION   "DBS Activation /Restoration starts immediately."
    ::=  { trapMibPrefix 3039 }


transientBootUpFailed NOTIFICATION-TYPE 
    OBJECTS     { entityIndex,neEventLogTimeStamp,neEventLogIdentityTranslation } 
    STATUS      current
    DESCRIPTION   "Boot up failed"
    ::=  { trapMibPrefix 3040 }


transientBootUpCompleted NOTIFICATION-TYPE 
    OBJECTS     { entityIndex,neEventLogTimeStamp,neEventLogIdentityTranslation } 
    STATUS      current
    DESCRIPTION   "Boot up completed"
    ::=  { trapMibPrefix 3041 }


transientBootUpStarted NOTIFICATION-TYPE 
    OBJECTS     { entityIndex,neEventLogTimeStamp,neEventLogIdentityTranslation } 
    STATUS      current
    DESCRIPTION   "Boot up started"
    ::=  { trapMibPrefix 3042 }


transientIntrusionRx NOTIFICATION-TYPE 
    OBJECTS     { entityIndex,neEventLogTimeStamp,neEventLogIdentityTranslation } 
    STATUS      current
    DESCRIPTION   "Intrusion on the Receiver Fiber based on GRADHT-AT keyword."
    ::=  { trapMibPrefix 3043 }


transientIntrusionTx NOTIFICATION-TYPE 
    OBJECTS     { entityIndex,neEventLogTimeStamp,neEventLogIdentityTranslation } 
    STATUS      current
    DESCRIPTION   "Intrusion on the Transmitter Fiber based on GRADHT-AT keyword."
    ::=  { trapMibPrefix 3044 }


transientDatabaseMismatch NOTIFICATION-TYPE 
    OBJECTS     { entityIndex,neEventLogTimeStamp,neEventLogIdentityTranslation } 
    STATUS      deprecated
    DESCRIPTION   "compare DBACT__FAIL x.y.z in UBR note DBTYPE is retrievable
         immediately with RTRV-SYS, we do not currently supported a RTRV-COND-SYS"
    ::=  { trapMibPrefix 3045 }


transientSwResetReload NOTIFICATION-TYPE 
    OBJECTS     { entityIndex,neEventLogTimeStamp,neEventLogIdentityTranslation } 
    STATUS      current
    DESCRIPTION   "System Restart-RELOAD"
    ::=  { trapMibPrefix 3046 }


transientInstallFwpCompleted NOTIFICATION-TYPE 
    OBJECTS     { entityIndex,neEventLogTimeStamp,neEventLogIdentityTranslation } 
    STATUS      current
    DESCRIPTION   "Installation of FWP completed"
    ::=  { trapMibPrefix 3047 }


transientCopyFileSshHostKeyFail NOTIFICATION-TYPE 
    OBJECTS     { entityIndex,neEventLogTimeStamp,neEventLogIdentityTranslation } 
    STATUS      current
    DESCRIPTION   "Copy File: Invalid ssh host key"
    ::=  { trapMibPrefix 3048 }


transientCopyFileNoHostKeyFail NOTIFICATION-TYPE 
    OBJECTS     { entityIndex,neEventLogTimeStamp,neEventLogIdentityTranslation } 
    STATUS      current
    DESCRIPTION   "Copy File: The authentication of the remote host cannot be established"
    ::=  { trapMibPrefix 3049 }


transientHardwareResetInputTIF NOTIFICATION-TYPE 
    OBJECTS     { entityIndex,neEventLogTimeStamp,neEventLogIdentityTranslation } 
    STATUS      current
    DESCRIPTION   "Telemetry interface alarm reset by hardware switch"
    ::=  { trapMibPrefix 3050 }


transientThres1DayExceededSonetSectES NOTIFICATION-TYPE 
    OBJECTS     { entityIndex,neEventLogTimeStamp,neEventLogIdentityTranslation } 
    STATUS      current
    DESCRIPTION   "This is a very severe degradation BER This is a very severe degradation BER Errored Seconds>Errored Seconds Section>= 10**-3 Section= 10**-3"
    ::=  { trapMibPrefix 3051 }


transientThres1DayExceededSonetSectSES NOTIFICATION-TYPE 
    OBJECTS     { entityIndex,neEventLogTimeStamp,neEventLogIdentityTranslation } 
    STATUS      current
    DESCRIPTION   "Severely Errored Seconds Section 1 Day Threshold Exceeded"
    ::=  { trapMibPrefix 3052 }


transientThres1DayExceededSonetSectSEFS NOTIFICATION-TYPE 
    OBJECTS     { entityIndex,neEventLogTimeStamp,neEventLogIdentityTranslation } 
    STATUS      current
    DESCRIPTION   "Severely Errored Framing Seconds Section 1 Day Threshold Exceeded"
    ::=  { trapMibPrefix 3053 }


transientThres1DayExceededSonetSectCV NOTIFICATION-TYPE 
    OBJECTS     { entityIndex,neEventLogTimeStamp,neEventLogIdentityTranslation } 
    STATUS      current
    DESCRIPTION   "Coding Violations Section"
    ::=  { trapMibPrefix 3054 }


transientThres1DayExceededSonetLineES NOTIFICATION-TYPE 
    OBJECTS     { entityIndex,neEventLogTimeStamp,neEventLogIdentityTranslation } 
    STATUS      current
    DESCRIPTION   "Errored Seconds Line"
    ::=  { trapMibPrefix 3055 }


transientThres1DayExceededSonetLineSES NOTIFICATION-TYPE 
    OBJECTS     { entityIndex,neEventLogTimeStamp,neEventLogIdentityTranslation } 
    STATUS      current
    DESCRIPTION   "Severely Errored Seconds Line 1 Day Threshold Exceeded"
    ::=  { trapMibPrefix 3056 }


transientThres1DayExceededSonetLineCV NOTIFICATION-TYPE 
    OBJECTS     { entityIndex,neEventLogTimeStamp,neEventLogIdentityTranslation } 
    STATUS      current
    DESCRIPTION   "Coding Violations Line"
    ::=  { trapMibPrefix 3057 }


transientThres1DayExceededSonetLineUAS NOTIFICATION-TYPE 
    OBJECTS     { entityIndex,neEventLogTimeStamp,neEventLogIdentityTranslation } 
    STATUS      current
    DESCRIPTION   "Unavailable Seconds Line 1 Day Threshold Exceeded"
    ::=  { trapMibPrefix 3058 }


transientThres1DayExceededOduTcmAES NOTIFICATION-TYPE 
    OBJECTS     { entityIndex,neEventLogTimeStamp,neEventLogIdentityTranslation } 
    STATUS      current
    DESCRIPTION   "Errored Seconds ODU Tandem Connection Monitoring"
    ::=  { trapMibPrefix 3059 }


transientThres1DayExceededOduTcmASES NOTIFICATION-TYPE 
    OBJECTS     { entityIndex,neEventLogTimeStamp,neEventLogIdentityTranslation } 
    STATUS      current
    DESCRIPTION   "Severely Errored Seconds ODU Tandem Connection Monitoring A (TCM_A) 1 Day Threshold Exceeded"
    ::=  { trapMibPrefix 3060 }


transientThres1DayExceededOduTcmAUAS NOTIFICATION-TYPE 
    OBJECTS     { entityIndex,neEventLogTimeStamp,neEventLogIdentityTranslation } 
    STATUS      current
    DESCRIPTION   "Unavailable Seconds ODU Tandem Connection Monitoring A (TCM_A) 1 Day Threshold Exceeded"
    ::=  { trapMibPrefix 3061 }


transientThres1DayExceededOduTcmABbe NOTIFICATION-TYPE 
    OBJECTS     { entityIndex,neEventLogTimeStamp,neEventLogIdentityTranslation } 
    STATUS      current
    DESCRIPTION   "Background Block Errors ODU Tandem Connection Monitoring"
    ::=  { trapMibPrefix 3062 }


transientThres1DayExceededOduTcmBES NOTIFICATION-TYPE 
    OBJECTS     { entityIndex,neEventLogTimeStamp,neEventLogIdentityTranslation } 
    STATUS      current
    DESCRIPTION   "Errored Seconds ODU Tandem Connection Monitoring"
    ::=  { trapMibPrefix 3063 }


transientThres1DayExceededOduTcmBSES NOTIFICATION-TYPE 
    OBJECTS     { entityIndex,neEventLogTimeStamp,neEventLogIdentityTranslation } 
    STATUS      current
    DESCRIPTION   "Severely Errored Seconds ODU Tandem Connection Monitoring B (TCM_B) 1 Day Threshold Exceeded"
    ::=  { trapMibPrefix 3064 }


transientThres1DayExceededOduTcmBUAS NOTIFICATION-TYPE 
    OBJECTS     { entityIndex,neEventLogTimeStamp,neEventLogIdentityTranslation } 
    STATUS      current
    DESCRIPTION   "Unavailable Seconds ODU Tandem Connection Monitoring B (TCM_B) 1 Day Threshold Exceeded"
    ::=  { trapMibPrefix 3065 }


transientThres1DayExceededOduTcmBBbe NOTIFICATION-TYPE 
    OBJECTS     { entityIndex,neEventLogTimeStamp,neEventLogIdentityTranslation } 
    STATUS      current
    DESCRIPTION   "Background Block Errors ODU Tandem Connection Monitoring"
    ::=  { trapMibPrefix 3066 }


transientThres1DayExceededOduTcmCES NOTIFICATION-TYPE 
    OBJECTS     { entityIndex,neEventLogTimeStamp,neEventLogIdentityTranslation } 
    STATUS      current
    DESCRIPTION   "Errored Seconds ODU Tandem Connection Monitoring"
    ::=  { trapMibPrefix 3067 }


transientThres1DayExceededOduTcmCSES NOTIFICATION-TYPE 
    OBJECTS     { entityIndex,neEventLogTimeStamp,neEventLogIdentityTranslation } 
    STATUS      current
    DESCRIPTION   "Severely Errored Seconds ODU Tandem Connection Monitoring C (TCM_C) 1 Day Threshold Exceeded"
    ::=  { trapMibPrefix 3068 }


transientThres1DayExceededOduTcmCUAS NOTIFICATION-TYPE 
    OBJECTS     { entityIndex,neEventLogTimeStamp,neEventLogIdentityTranslation } 
    STATUS      current
    DESCRIPTION   "Unavailable Seconds ODU Tandem Connection Monitoring C (TCM_C) 1 Day Threshold Exceeded"
    ::=  { trapMibPrefix 3069 }


transientThres1DayExceededOduTcmCBbe NOTIFICATION-TYPE 
    OBJECTS     { entityIndex,neEventLogTimeStamp,neEventLogIdentityTranslation } 
    STATUS      current
    DESCRIPTION   "Background Block Errors ODU Tandem Connection Monitoring"
    ::=  { trapMibPrefix 3070 }


transientThres1DayExceededOtuES NOTIFICATION-TYPE 
    OBJECTS     { entityIndex,neEventLogTimeStamp,neEventLogIdentityTranslation } 
    STATUS      current
    DESCRIPTION   "Errored Seconds OTU Section Monitoring"
    ::=  { trapMibPrefix 3071 }


transientThres1DayExceededOtuSES NOTIFICATION-TYPE 
    OBJECTS     { entityIndex,neEventLogTimeStamp,neEventLogIdentityTranslation } 
    STATUS      current
    DESCRIPTION   "Severely Errored Seconds OTU Section 1 Day Threshold Exceeded"
    ::=  { trapMibPrefix 3072 }


transientThres1DayExceededOtuUAS NOTIFICATION-TYPE 
    OBJECTS     { entityIndex,neEventLogTimeStamp,neEventLogIdentityTranslation } 
    STATUS      current
    DESCRIPTION   "Unavailable Seconds OTU Section 1 Day Threshold Exceeded"
    ::=  { trapMibPrefix 3073 }


transientThres1DayExceededOtuBbe NOTIFICATION-TYPE 
    OBJECTS     { entityIndex,neEventLogTimeStamp,neEventLogIdentityTranslation } 
    STATUS      current
    DESCRIPTION   "Background Block Errors OTU Section Monitoring"
    ::=  { trapMibPrefix 3074 }


transientThres1DayExceededOduES NOTIFICATION-TYPE 
    OBJECTS     { entityIndex,neEventLogTimeStamp,neEventLogIdentityTranslation } 
    STATUS      current
    DESCRIPTION   "Errored Seconds ODU Path Monitoring"
    ::=  { trapMibPrefix 3075 }


transientThres1DayExceededOduSES NOTIFICATION-TYPE 
    OBJECTS     { entityIndex,neEventLogTimeStamp,neEventLogIdentityTranslation } 
    STATUS      current
    DESCRIPTION   "Severely Errored Seconds ODU Path 1 Day Threshold Exceeded"
    ::=  { trapMibPrefix 3076 }


transientThres1DayExceededOduUAS NOTIFICATION-TYPE 
    OBJECTS     { entityIndex,neEventLogTimeStamp,neEventLogIdentityTranslation } 
    STATUS      current
    DESCRIPTION   "Unavailable Seconds ODU Path 1 Day Threshold Exceeded"
    ::=  { trapMibPrefix 3077 }


transientThres1DayExceededOduBbe NOTIFICATION-TYPE 
    OBJECTS     { entityIndex,neEventLogTimeStamp,neEventLogIdentityTranslation } 
    STATUS      current
    DESCRIPTION   "Background Block Errors ODU Section Monitoring"
    ::=  { trapMibPrefix 3078 }


transientCpConnectionEstablishmentStart NOTIFICATION-TYPE 
    OBJECTS     { entityIndex,neEventLogTimeStamp,neEventLogIdentityTranslation } 
    STATUS      current
    DESCRIPTION   "Start of Connection Establisment"
    ::=  { trapMibPrefix 3080 }


transientCpConnectionEstablishmentFail NOTIFICATION-TYPE 
    OBJECTS     { entityIndex,neEventLogTimeStamp,neEventLogIdentityTranslation } 
    STATUS      current
    DESCRIPTION   "Failure of Connection Establisment"
    ::=  { trapMibPrefix 3081 }


transientCpConnectionEstablishmentCompleted NOTIFICATION-TYPE 
    OBJECTS     { entityIndex,neEventLogTimeStamp,neEventLogIdentityTranslation } 
    STATUS      current
    DESCRIPTION   "Completion of Connection Establisment"
    ::=  { trapMibPrefix 3082 }


transientCpConnectionModificationStart NOTIFICATION-TYPE 
    OBJECTS     { entityIndex,neEventLogTimeStamp,neEventLogIdentityTranslation } 
    STATUS      current
    DESCRIPTION   "Start of Connection Modification"
    ::=  { trapMibPrefix 3083 }


transientCpConnectionModificationFail NOTIFICATION-TYPE 
    OBJECTS     { entityIndex,neEventLogTimeStamp,neEventLogIdentityTranslation } 
    STATUS      current
    DESCRIPTION   "Failure of Connection Modification"
    ::=  { trapMibPrefix 3084 }


transientCpConnectionModificationCompleted NOTIFICATION-TYPE 
    OBJECTS     { entityIndex,neEventLogTimeStamp,neEventLogIdentityTranslation } 
    STATUS      current
    DESCRIPTION   "Completion of Connection Modification"
    ::=  { trapMibPrefix 3085 }


transientAlarmProfileActivation NOTIFICATION-TYPE 
    OBJECTS     { entityIndex,neEventLogTimeStamp,neEventLogIdentityTranslation } 
    STATUS      current
    DESCRIPTION   "Alarm Profile Activation"
    ::=  { trapMibPrefix 3086 }


transientAlarmProfileActivationFail NOTIFICATION-TYPE 
    OBJECTS     { entityIndex,neEventLogTimeStamp,neEventLogIdentityTranslation } 
    STATUS      current
    DESCRIPTION   "Alarm Profile Activation Failed."
    ::=  { trapMibPrefix 3087 }


transientCpConnectionEstablishmentAborted NOTIFICATION-TYPE 
    OBJECTS     { entityIndex,neEventLogTimeStamp,neEventLogIdentityTranslation } 
    STATUS      current
    DESCRIPTION   "Connection Establisment Aborted"
    ::=  { trapMibPrefix 3088 }


transientEqlzStart NOTIFICATION-TYPE 
    OBJECTS     { entityIndex,neEventLogTimeStamp,neEventLogIdentityTranslation } 
    STATUS      current
    DESCRIPTION   "Start of Connection Equalization"
    ::=  { trapMibPrefix 3089 }


transientEqlzFailed NOTIFICATION-TYPE 
    OBJECTS     { entityIndex,neEventLogTimeStamp,neEventLogIdentityTranslation } 
    STATUS      current
    DESCRIPTION   "Failure of Connection Equalization"
    ::=  { trapMibPrefix 3090 }


transientEqlzCompleted NOTIFICATION-TYPE 
    OBJECTS     { entityIndex,neEventLogTimeStamp,neEventLogIdentityTranslation } 
    STATUS      current
    DESCRIPTION   "Completion of Connection Equalization"
    ::=  { trapMibPrefix 3091 }


transientEqlzRequestDenied NOTIFICATION-TYPE 
    OBJECTS     { entityIndex,neEventLogTimeStamp,neEventLogIdentityTranslation } 
    STATUS      current
    DESCRIPTION   "Equalization request denied (could not be performed) by enity"
    ::=  { trapMibPrefix 3100 }


transientEqlzNotRequired NOTIFICATION-TYPE 
    OBJECTS     { entityIndex,neEventLogTimeStamp,neEventLogIdentityTranslation } 
    STATUS      current
    DESCRIPTION   "Equalization Null - Not Required - channel(s) are currently equalized"
    ::=  { trapMibPrefix 3101 }


transientEqlzProcessPassed NOTIFICATION-TYPE 
    OBJECTS     { entityIndex,neEventLogTimeStamp,neEventLogIdentityTranslation } 
    STATUS      current
    DESCRIPTION   "Equalization Operation completed sucessfully"
    ::=  { trapMibPrefix 3102 }


transientEqlzProcessWait NOTIFICATION-TYPE 
    OBJECTS     { entityIndex,neEventLogTimeStamp,neEventLogIdentityTranslation } 
    STATUS      current
    DESCRIPTION   "Eqalization is in progress, User must wait then request equalization"
    ::=  { trapMibPrefix 3103 }


transientDispersionCompFailed NOTIFICATION-TYPE 
    OBJECTS     { entityIndex,neEventLogTimeStamp,neEventLogIdentityTranslation } 
    STATUS      current
    DESCRIPTION   "Optimization of Chromatic Dispersion Compensation Fail"
    ::=  { trapMibPrefix 3110 }


transientAlpSettingStarted NOTIFICATION-TYPE 
    OBJECTS     { entityIndex,neEventLogTimeStamp,neEventLogIdentityTranslation } 
    STATUS      current
    DESCRIPTION   "Setting of alarm severities to Alarm Profile values started"
    ::=  { trapMibPrefix 3111 }


transientAlpSettingFinished NOTIFICATION-TYPE 
    OBJECTS     { entityIndex,neEventLogTimeStamp,neEventLogIdentityTranslation } 
    STATUS      current
    DESCRIPTION   "Setting of alarm severities to Alarm Profile values completed"
    ::=  { trapMibPrefix 3112 }


transientFarEndDyingGasp NOTIFICATION-TYPE 
    OBJECTS     { entityIndex,neEventLogTimeStamp,neEventLogIdentityTranslation } 
    STATUS      current
    DESCRIPTION   "signal received from far end upon far end power loss"
    ::=  { trapMibPrefix 3113 }


transientLocalCopyMemFailDenied NOTIFICATION-TYPE 
    OBJECTS     { entityIndex,neEventLogTimeStamp,neEventLogIdentityTranslation } 
    STATUS      current
    DESCRIPTION   "Local copy file fail - denied"
    ::=  { trapMibPrefix 3114 }


transientLocalCopyMemFailCrcErr NOTIFICATION-TYPE 
    OBJECTS     { entityIndex,neEventLogTimeStamp,neEventLogIdentityTranslation } 
    STATUS      current
    DESCRIPTION   "Local copy file fail - CRC error"
    ::=  { trapMibPrefix 3115 }


transientAlarmProfileFactoryDefaultActivation NOTIFICATION-TYPE 
    OBJECTS     { entityIndex,neEventLogTimeStamp,neEventLogIdentityTranslation } 
    STATUS      current
    DESCRIPTION   "Alarm Profile Factory Default Activation."
    ::=  { trapMibPrefix 3116 }


transientLocalCopyMemFailVersionMismatch NOTIFICATION-TYPE 
    OBJECTS     { entityIndex,neEventLogTimeStamp,neEventLogIdentityTranslation } 
    STATUS      current
    DESCRIPTION   "Copy Memory Failed Mismatch"
    ::=  { trapMibPrefix 3120 }


transientLocalCopyMemFailWrongState NOTIFICATION-TYPE 
    OBJECTS     { entityIndex,neEventLogTimeStamp,neEventLogIdentityTranslation } 
    STATUS      current
    DESCRIPTION   "Incorrect Standby State"
    ::=  { trapMibPrefix 3121 }


transientLocalCopyMemFailDamagedConfFile NOTIFICATION-TYPE 
    OBJECTS     { entityIndex,neEventLogTimeStamp,neEventLogIdentityTranslation } 
    STATUS      current
    DESCRIPTION   "Invalid Configuration File"
    ::=  { trapMibPrefix 3122 }


transientLocalCopyMemFailFsckFailed NOTIFICATION-TYPE 
    OBJECTS     { entityIndex,neEventLogTimeStamp,neEventLogIdentityTranslation } 
    STATUS      current
    DESCRIPTION   "File system check fail"
    ::=  { trapMibPrefix 3123 }


transientLocalCopyMemFailNotExist NOTIFICATION-TYPE 
    OBJECTS     { entityIndex,neEventLogTimeStamp,neEventLogIdentityTranslation } 
    STATUS      current
    DESCRIPTION   "Local File does not exist"
    ::=  { trapMibPrefix 3124 }


transientLocalCopyMemFailExist NOTIFICATION-TYPE 
    OBJECTS     { entityIndex,neEventLogTimeStamp,neEventLogIdentityTranslation } 
    STATUS      current
    DESCRIPTION   "Local File Exist"
    ::=  { trapMibPrefix 3125 }


transientLocalCopyMemFailDisallowed NOTIFICATION-TYPE 
    OBJECTS     { entityIndex,neEventLogTimeStamp,neEventLogIdentityTranslation } 
    STATUS      current
    DESCRIPTION   "Vendor Profile Exist"
    ::=  { trapMibPrefix 3126 }


transientLocalCopyMemFailLimitReached NOTIFICATION-TYPE 
    OBJECTS     { entityIndex,neEventLogTimeStamp,neEventLogIdentityTranslation } 
    STATUS      current
    DESCRIPTION   "Exceeded ECI User Profile Maximum Limit of 20 profiles"
    ::=  { trapMibPrefix 3127 }


transientLocalCopyMemFailGeneration NOTIFICATION-TYPE 
    OBJECTS     { entityIndex,neEventLogTimeStamp,neEventLogIdentityTranslation } 
    STATUS      current
    DESCRIPTION   "Consistent backup generation fail"
    ::=  { trapMibPrefix 3140 }


transientCopyFileFailDisabledProtocol NOTIFICATION-TYPE 
    OBJECTS     { entityIndex,neEventLogTimeStamp,neEventLogIdentityTranslation } 
    STATUS      current
    DESCRIPTION   "Selected file transfer protocol disabled."
    ::=  { trapMibPrefix 3141 }


transientAutomaticBackupReport NOTIFICATION-TYPE 
    OBJECTS     { entityIndex,neEventLogTimeStamp,neEventLogIdentityTranslation } 
    STATUS      current
    DESCRIPTION   "Automatic Data Base Backup Report"
    ::=  { trapMibPrefix 3142 }


transientRestorationStart NOTIFICATION-TYPE 
    OBJECTS     { entityIndex,neEventLogTimeStamp,neEventLogIdentityTranslation } 
    STATUS      current
    DESCRIPTION   "Start of Connection Restoration"
    ::=  { trapMibPrefix 3160 }


transientRestorationFailed NOTIFICATION-TYPE 
    OBJECTS     { entityIndex,neEventLogTimeStamp,neEventLogIdentityTranslation } 
    STATUS      current
    DESCRIPTION   "Failure of Connection Restoration"
    ::=  { trapMibPrefix 3161 }


transientRestorationCompleted NOTIFICATION-TYPE 
    OBJECTS     { entityIndex,neEventLogTimeStamp,neEventLogIdentityTranslation } 
    STATUS      current
    DESCRIPTION   "Completion of Connection Restoration"
    ::=  { trapMibPrefix 3162 }


transientFarEndChanged NOTIFICATION-TYPE 
    OBJECTS     { entityIndex,neEventLogTimeStamp,neEventLogIdentityTranslation } 
    STATUS      current
    DESCRIPTION   "Neighbor Discovery Dectected a Far End Change"
    ::=  { trapMibPrefix 3163 }


transientBootUpRejected NOTIFICATION-TYPE 
    OBJECTS     { entityIndex,neEventLogTimeStamp,neEventLogIdentityTranslation } 
    STATUS      current
    DESCRIPTION   "Boot up rejected"
    ::=  { trapMibPrefix 3170 }


transientThres1DayExceededFecBERCE NOTIFICATION-TYPE 
    OBJECTS     { entityIndex,neEventLogTimeStamp,neEventLogIdentityTranslation } 
    STATUS      current
    DESCRIPTION   "Bit error rate before FEC 1day high threshold crossed"
    ::=  { trapMibPrefix 3175 }


transientPreComputationReady NOTIFICATION-TYPE 
    OBJECTS     { entityIndex,neEventLogTimeStamp,neEventLogIdentityTranslation } 
    STATUS      current
    DESCRIPTION   "Pre-Computation finished. Result either successful or failed."
    ::=  { trapMibPrefix 3180 }


transientNeTimeChanged NOTIFICATION-TYPE 
    STATUS      current
    DESCRIPTION   "Time Change"
    ::=  { trapMibPrefix 3181 }


transientNtpSrvTestSuccessed NOTIFICATION-TYPE 
    OBJECTS     { entityIndex,neEventLogTimeStamp,neEventLogIdentityTranslation } 
    STATUS      current
    DESCRIPTION   "NTPTEST-SUCCESS"
    ::=  { trapMibPrefix 3182 }


transientNtpSrvTestFailed NOTIFICATION-TYPE 
    OBJECTS     { entityIndex,neEventLogTimeStamp,neEventLogIdentityTranslation } 
    STATUS      current
    DESCRIPTION   "NTPTEST-FAIL"
    ::=  { trapMibPrefix 3183 }


transientNtpSrvSyncStarted NOTIFICATION-TYPE 
    OBJECTS     { entityIndex,neEventLogTimeStamp,neEventLogIdentityTranslation } 
    STATUS      current
    DESCRIPTION   "NTP-START"
    ::=  { trapMibPrefix 3184 }


transientNtpSrvSyncFailed NOTIFICATION-TYPE 
    OBJECTS     { entityIndex,neEventLogTimeStamp,neEventLogIdentityTranslation } 
    STATUS      current
    DESCRIPTION   "NTP-FAIL"
    ::=  { trapMibPrefix 3185 }


transientNtpSrvSyncEnded NOTIFICATION-TYPE 
    OBJECTS     { entityIndex,neEventLogTimeStamp,neEventLogIdentityTranslation } 
    STATUS      current
    DESCRIPTION   "NTP-END"
    ::=  { trapMibPrefix 3186 }


transientPmSnapshotStarted NOTIFICATION-TYPE 
    OBJECTS     { entityIndex,neEventLogTimeStamp,neEventLogIdentityTranslation } 
    STATUS      current
    DESCRIPTION   "Reference value save start"
    ::=  { trapMibPrefix 3187 }


transientPmSnapshotEnded NOTIFICATION-TYPE 
    OBJECTS     { entityIndex,neEventLogTimeStamp,neEventLogIdentityTranslation } 
    STATUS      current
    DESCRIPTION   "Reference value save end"
    ::=  { trapMibPrefix 3188 }


transientNtpSrvSyncChanged NOTIFICATION-TYPE 
    OBJECTS     { ntpServerSyncStatus, neEventLogTimeStamp, neEventLogIdentityTranslation }
    STATUS      current
    DESCRIPTION   "NTP Synchronization Change (current Status in Varbind)"
    ::=  { trapMibPrefix 3189 }


transientThres1DayExceededPhysConvSE NOTIFICATION-TYPE 
    OBJECTS     { entityIndex,neEventLogTimeStamp,neEventLogIdentityTranslation } 
    STATUS      current
    DESCRIPTION   "Sync Header Errors Physical Coding Layer 1 Day Threshold Exceeded"
    ::=  { trapMibPrefix 3190 }


transientThres1DayExceededPhysConvESTX NOTIFICATION-TYPE 
    OBJECTS     { entityIndex,neEventLogTimeStamp,neEventLogIdentityTranslation } 
    STATUS      current
    DESCRIPTION   "Tx Errored Seconds Physical Coding Layer"
    ::=  { trapMibPrefix 3191 }


transientThres1DayExceededPhysConvCVTX NOTIFICATION-TYPE 
    OBJECTS     { entityIndex,neEventLogTimeStamp,neEventLogIdentityTranslation } 
    STATUS      current
    DESCRIPTION   "Tx Coding Violations Physical Coding Layer"
    ::=  { trapMibPrefix 3192 }


transientThres1DayExceededPhysConvSETX NOTIFICATION-TYPE 
    OBJECTS     { entityIndex,neEventLogTimeStamp,neEventLogIdentityTranslation } 
    STATUS      current
    DESCRIPTION   "Tx Sync Header Errors Physical Coding Layer 1 Day Threshold Exceeded"
    ::=  { trapMibPrefix 3193 }


transientCryptoRtf NOTIFICATION-TYPE 
    OBJECTS     { entityIndex,neEventLogTimeStamp,neEventLogIdentityTranslation } 
    STATUS      current
    DESCRIPTION   "Encryption settings reset to factory defaults"
    ::=  { trapMibPrefix 3194 }


transientCryptoFwpRevChanged NOTIFICATION-TYPE 
    OBJECTS     { entityIndex,neEventLogTimeStamp,neEventLogIdentityTranslation } 
    STATUS      current
    DESCRIPTION   "FWP upgrade revision number is changed"
    ::=  { trapMibPrefix 3195 }


transientCryptoPasswdChanged NOTIFICATION-TYPE 
    OBJECTS     { entityIndex,neEventLogTimeStamp,neEventLogIdentityTranslation } 
    STATUS      current
    DESCRIPTION   "Crypto Officer Password Changed"
    ::=  { trapMibPrefix 3196 }


transientCryptoFwpUpdate NOTIFICATION-TYPE 
    OBJECTS     { entityIndex,neEventLogTimeStamp,neEventLogIdentityTranslation } 
    STATUS      current
    DESCRIPTION   "A new FWP is installed"
    ::=  { trapMibPrefix 3197 }


transientCryptoKeyExchgFailCondClr NOTIFICATION-TYPE 
    OBJECTS     { entityIndex,neEventLogTimeStamp,neEventLogIdentityTranslation } 
    STATUS      current
    DESCRIPTION   "Key exchange fail counter reset"
    ::=  { trapMibPrefix 3198 }


transientCryptoAuthPasswdChanged NOTIFICATION-TYPE 
    OBJECTS     { entityIndex,neEventLogTimeStamp,neEventLogIdentityTranslation } 
    STATUS      current
    DESCRIPTION   "Change of Authentication Password"
    ::=  { trapMibPrefix 3199 }


transientCryptoSessKeyLifetimeChanged NOTIFICATION-TYPE 
    OBJECTS     { entityIndex,neEventLogTimeStamp,neEventLogIdentityTranslation } 
    STATUS      current
    DESCRIPTION   "Change of session key lifetime"
    ::=  { trapMibPrefix 3200 }


transientCryptoAuthPasswdInvalid NOTIFICATION-TYPE 
    OBJECTS     { entityIndex,neEventLogTimeStamp,neEventLogIdentityTranslation } 
    STATUS      current
    DESCRIPTION   "A wrong Authentication password was sent with the command"
    ::=  { trapMibPrefix 3201 }


transientEncryptionPortSingleKeyExchgFailed NOTIFICATION-TYPE 
    OBJECTS     { entityIndex,neEventLogTimeStamp,neEventLogIdentityTranslation } 
    STATUS      current
    DESCRIPTION   "At least one Key exchange failed"
    ::=  { trapMibPrefix 3202 }


transientWaitToRevert NOTIFICATION-TYPE 
    OBJECTS     { entityIndex,neEventLogTimeStamp,neEventLogIdentityTranslation } 
    STATUS      current
    DESCRIPTION   "Wait to revert time started for an auto-revertive tunnel"
    ::=  { trapMibPrefix 3203 }


transientReversionStarted NOTIFICATION-TYPE 
    OBJECTS     { entityIndex,neEventLogTimeStamp,neEventLogIdentityTranslation } 
    STATUS      current
    DESCRIPTION   "Manual Start of Reversion back to the nomial connection"
    ::=  { trapMibPrefix 3204 }


transientReversionFailed NOTIFICATION-TYPE 
    OBJECTS     { entityIndex,neEventLogTimeStamp,neEventLogIdentityTranslation } 
    STATUS      current
    DESCRIPTION   "Reversion back to the nominal connection failed"
    ::=  { trapMibPrefix 3205 }


transientReversionCompleted NOTIFICATION-TYPE 
    OBJECTS     { entityIndex,neEventLogTimeStamp,neEventLogIdentityTranslation } 
    STATUS      current
    DESCRIPTION   "Reversion to the nominal connection completed"
    ::=  { trapMibPrefix 3206 }


transientFiberConnStatChange NOTIFICATION-TYPE 
    STATUS      current
    DESCRIPTION   "Fiber Connection Status Change"
    ::=  { trapMibPrefix 3207 }


transientProtSwToDuplexStart NOTIFICATION-TYPE 
    OBJECTS     { entityIndex,neEventLogTimeStamp,neEventLogIdentityTranslation } 
    STATUS      current
    DESCRIPTION   "Switch to Partner Controller started"
    ::=  { trapMibPrefix 3210 }


transientProtSwToDuplexCompl NOTIFICATION-TYPE 
    STATUS      current
    DESCRIPTION   "Switch to Partner Controller complete"
    ::=  { trapMibPrefix 3211 }


transientProtSwToDuplexFail NOTIFICATION-TYPE 
    OBJECTS     { entityIndex,neEventLogTimeStamp,neEventLogIdentityTranslation } 
    STATUS      current
    DESCRIPTION   "Switch to Partner Controller failed"
    ::=  { trapMibPrefix 3212 }


transientForcedReboot NOTIFICATION-TYPE 
    OBJECTS     { entityIndex,neEventLogTimeStamp,neEventLogIdentityTranslation } 
    STATUS      current
    DESCRIPTION   "Forced Reboot"
    ::=  { trapMibPrefix 3220 }


transientReversionReady NOTIFICATION-TYPE 
    OBJECTS     { entityIndex,neEventLogTimeStamp,neEventLogIdentityTranslation } 
    STATUS      current
    DESCRIPTION   "Nominal path is ready for reversion"
    ::=  { trapMibPrefix 3221 }


transientReversionNotReady NOTIFICATION-TYPE 
    OBJECTS     { entityIndex,neEventLogTimeStamp,neEventLogIdentityTranslation } 
    STATUS      current
    DESCRIPTION   "Nominal path is not ready for reversion"
    ::=  { trapMibPrefix 3222 }


transientReversionBlocked NOTIFICATION-TYPE 
    OBJECTS     { entityIndex,neEventLogTimeStamp,neEventLogIdentityTranslation } 
    STATUS      current
    DESCRIPTION   "Reversion Blocked"
    ::=  { trapMibPrefix 3223 }


transientReversionUnknown NOTIFICATION-TYPE 
    OBJECTS     { entityIndex,neEventLogTimeStamp,neEventLogIdentityTranslation } 
    STATUS      current
    DESCRIPTION   "No information on readiness to revert. CP will not be able to notice failed link repair and hence will NEVER provide information on reversion state."
    ::=  { trapMibPrefix 3224 }


transientPaFileStart NOTIFICATION-TYPE 
    OBJECTS     { entityIndex,neEventLogTimeStamp,neEventLogIdentityTranslation } 
    STATUS      current
    DESCRIPTION   "Path Analyzer File-Start"
    ::=  { trapMibPrefix 3225 }


transientPaFileCompleted NOTIFICATION-TYPE 
    OBJECTS     { entityIndex,neEventLogTimeStamp,neEventLogIdentityTranslation } 
    STATUS      current
    DESCRIPTION   "Path Analyzer File-Done"
    ::=  { trapMibPrefix 3226 }


transientPaFileFailed NOTIFICATION-TYPE 
    OBJECTS     { entityIndex,neEventLogTimeStamp,neEventLogIdentityTranslation } 
    STATUS      current
    DESCRIPTION   "Path Analyzer-File-Fail"
    ::=  { trapMibPrefix 3227 }


entityStateTable OBJECT-TYPE
    SYNTAX      SEQUENCE OF EntityStateEntry
    MAX-ACCESS  not-accessible
    STATUS      current
    DESCRIPTION   ""
    ::=  { commonConfigAndStatus 1 }

entityStateEntry OBJECT-TYPE
    SYNTAX      EntityStateEntry
    MAX-ACCESS  not-accessible
    STATUS      current
    DESCRIPTION   ""
    INDEX       {
                  entityIndex
                }
    ::=  { entityStateTable 1 }

EntityStateEntry ::=  SEQUENCE
  { entityStateAdmin FspR7AdminState,
    entityStateOper FspR7OperState,
    entityStateSecondaryStates FspR7EntitySecondaryStates }

entityStateAdmin OBJECT-TYPE
    SYNTAX      FspR7AdminState
    MAX-ACCESS  read-write
    STATUS      current
    DESCRIPTION   "The Adminstrative State will be displayed in the GUI with full name values;
         it will be differently displayed in TL1 SYNTAX according to TL1 display rules.
         The transaction into the UAS state requires a special destroy/delete function."
    ::=  { entityStateEntry 1 }

entityStateOper OBJECT-TYPE
    SYNTAX      FspR7OperState
    MAX-ACCESS  read-only
    STATUS      current
    DESCRIPTION   "The Operational State will be displayed on the GUI with full name values;
         it will be differently displayed in TL1 SYNTAX according to TL1 display rules"
    ::=  { entityStateEntry 2 }

entityStateSecondaryStates OBJECT-TYPE
    SYNTAX      FspR7EntitySecondaryStates
    MAX-ACCESS  read-only
    STATUS      current
    DESCRIPTION   "Secondary states of an entity."
    ::=  { entityStateEntry 3 }

entityStateCapTable OBJECT-TYPE
    SYNTAX      SEQUENCE OF EntityStateCapEntry
    MAX-ACCESS  not-accessible
    STATUS      current
    DESCRIPTION   ""
    ::=  { commonConfigAndStatus 2 }

entityStateCapEntry OBJECT-TYPE
    SYNTAX      EntityStateCapEntry
    MAX-ACCESS  not-accessible
    STATUS      current
    DESCRIPTION   ""
    INDEX       {
                  entityIndex
                }
    ::=  { entityStateCapTable 1 }

EntityStateCapEntry ::=  SEQUENCE
  { entityStateCapAdmin FspR7AdminStateCaps }

entityStateCapAdmin OBJECT-TYPE
    SYNTAX      FspR7AdminStateCaps
    MAX-ACCESS  read-only
    STATUS      current
    DESCRIPTION   "This object contains capabilities for entityStateAdmin object."
    ::=  { entityStateCapEntry 1 }

controlPlaneWdmEntityStateTable OBJECT-TYPE
    SYNTAX      SEQUENCE OF ControlPlaneWdmEntityStateEntry
    MAX-ACCESS  not-accessible
    STATUS      current
    DESCRIPTION   ""
    ::=  { commonConfigAndStatus 3 }

controlPlaneWdmEntityStateEntry OBJECT-TYPE
    SYNTAX      ControlPlaneWdmEntityStateEntry
    MAX-ACCESS  not-accessible
    STATUS      current
    DESCRIPTION   ""
    INDEX       {
                  controlPlaneWdmEntityIndex
                }
    ::=  { controlPlaneWdmEntityStateTable 1 }

ControlPlaneWdmEntityStateEntry ::=  SEQUENCE
  { controlPlaneWdmEntityStateAdmin FspR7AdminState,
    controlPlaneWdmEntityStateOper FspR7OperState,
    controlPlaneWdmEntityStateSecondaryStates FspR7EntitySecondaryStates }

controlPlaneWdmEntityStateAdmin OBJECT-TYPE
    SYNTAX      FspR7AdminState
    MAX-ACCESS  read-write
    STATUS      current
    DESCRIPTION   "The Adminstrative State will be displayed in the GUI with full name values;
         it will be differently displayed in TL1 SYNTAX according to TL1 display rules.
         The transaction into the UAS state requires a special destroy/delete function."
    ::=  { controlPlaneWdmEntityStateEntry 1 }

controlPlaneWdmEntityStateOper OBJECT-TYPE
    SYNTAX      FspR7OperState
    MAX-ACCESS  read-only
    STATUS      current
    DESCRIPTION   "The Operational State will be displayed on the GUI with full name values;
         it will be differently displayed in TL1 SYNTAX according to TL1 display rules"
    ::=  { controlPlaneWdmEntityStateEntry 2 }

controlPlaneWdmEntityStateSecondaryStates OBJECT-TYPE
    SYNTAX      FspR7EntitySecondaryStates
    MAX-ACCESS  read-only
    STATUS      current
    DESCRIPTION   "Secondary states of an entity."
    ::=  { controlPlaneWdmEntityStateEntry 3 }

controlPlaneEntityStateCapTable OBJECT-TYPE
    SYNTAX      SEQUENCE OF ControlPlaneEntityStateCapEntry
    MAX-ACCESS  not-accessible
    STATUS      current
    DESCRIPTION   ""
    ::=  { commonConfigAndStatus 4 }

controlPlaneEntityStateCapEntry OBJECT-TYPE
    SYNTAX      ControlPlaneEntityStateCapEntry
    MAX-ACCESS  not-accessible
    STATUS      current
    DESCRIPTION   ""
    INDEX       {
                  controlPlaneWdmEntityIndex
                }
    ::=  { controlPlaneEntityStateCapTable 1 }

ControlPlaneEntityStateCapEntry ::=  SEQUENCE
  { controlPlaneEntityStateCapAdmin FspR7AdminStateCaps }

controlPlaneEntityStateCapAdmin OBJECT-TYPE
    SYNTAX      FspR7AdminStateCaps
    MAX-ACCESS  read-only
    STATUS      current
    DESCRIPTION   "This object contains capabilities for entityStateAdmin object."
    ::=  { controlPlaneEntityStateCapEntry 1 }

dependenciesTable OBJECT-TYPE
    SYNTAX      SEQUENCE OF DependenciesEntry
    MAX-ACCESS  not-accessible
    STATUS      current
    DESCRIPTION   ""
    ::=  { commonConfigAndStatus 5 }

dependenciesEntry OBJECT-TYPE
    SYNTAX      DependenciesEntry
    MAX-ACCESS  not-accessible
    STATUS      current
    DESCRIPTION   ""
    INDEX       {
                  entityIndex,
                  dependenciesIndex
                }
    ::=  { dependenciesTable 1 }

DependenciesEntry ::=  SEQUENCE
  { dependenciesIndex Unsigned32,
    dependenciesAid SnmpAdminString }

dependenciesIndex OBJECT-TYPE
    SYNTAX      Unsigned32
    MAX-ACCESS  not-accessible
    STATUS      current
    DESCRIPTION   "Number of sequence"
    ::=  { dependenciesEntry 1 }

dependenciesAid OBJECT-TYPE
    SYNTAX      SnmpAdminString
    MAX-ACCESS  read-only
    STATUS      current
    DESCRIPTION
        "Name" 
    ::=  { dependenciesEntry 2 }

controlPlaneEthEntityStateTable OBJECT-TYPE
    SYNTAX      SEQUENCE OF ControlPlaneEthEntityStateEntry
    MAX-ACCESS  not-accessible
    STATUS      current
    DESCRIPTION   ""
    ::=  { commonConfigAndStatus 6 }

controlPlaneEthEntityStateEntry OBJECT-TYPE
    SYNTAX      ControlPlaneEthEntityStateEntry
    MAX-ACCESS  not-accessible
    STATUS      current
    DESCRIPTION   ""
    INDEX       {
                  controlPlaneEthEntityIndex
                }
    ::=  { controlPlaneEthEntityStateTable 1 }

ControlPlaneEthEntityStateEntry ::=  SEQUENCE
  { controlPlaneEthEntityStateAdmin FspR7AdminState,
    controlPlaneEthEntityStateOper FspR7OperState,
    controlPlaneEthEntityStateSecondaryStates FspR7EntitySecondaryStates }

controlPlaneEthEntityStateAdmin OBJECT-TYPE
    SYNTAX      FspR7AdminState
    MAX-ACCESS  read-write
    STATUS      current
    DESCRIPTION   "The Adminstrative State will be displayed in the GUI with full name values;
         it will be differently displayed in TL1 SYNTAX according to TL1 display rules.
         The transaction into the UAS state requires a special destroy/delete function."
    ::=  { controlPlaneEthEntityStateEntry 1 }

controlPlaneEthEntityStateOper OBJECT-TYPE
    SYNTAX      FspR7OperState
    MAX-ACCESS  read-only
    STATUS      current
    DESCRIPTION   "The Operational State will be displayed on the GUI with full name values;
         it will be differently displayed in TL1 SYNTAX according to TL1 display rules"
    ::=  { controlPlaneEthEntityStateEntry 2 }

controlPlaneEthEntityStateSecondaryStates OBJECT-TYPE
    SYNTAX      FspR7EntitySecondaryStates
    MAX-ACCESS  read-only
    STATUS      current
    DESCRIPTION   "Secondary states of an entity."
    ::=  { controlPlaneEthEntityStateEntry 3 }

controlPlaneEthEntityStateCapTable OBJECT-TYPE
    SYNTAX      SEQUENCE OF ControlPlaneEthEntityStateCapEntry
    MAX-ACCESS  not-accessible
    STATUS      current
    DESCRIPTION   ""
    ::=  { commonConfigAndStatus 7 }

controlPlaneEthEntityStateCapEntry OBJECT-TYPE
    SYNTAX      ControlPlaneEthEntityStateCapEntry
    MAX-ACCESS  not-accessible
    STATUS      current
    DESCRIPTION   ""
    INDEX       {
                  controlPlaneEthEntityIndex
                }
    ::=  { controlPlaneEthEntityStateCapTable 1 }

ControlPlaneEthEntityStateCapEntry ::=  SEQUENCE
  { controlPlaneEthEntityStateCapAdmin FspR7AdminStateCaps }

controlPlaneEthEntityStateCapAdmin OBJECT-TYPE
    SYNTAX      FspR7AdminStateCaps
    MAX-ACCESS  read-only
    STATUS      current
    DESCRIPTION   "This object contains capabilities for entityStateAdmin object."
    ::=  { controlPlaneEthEntityStateCapEntry 1 }

controlPlaneOtnEntityStateTable OBJECT-TYPE
    SYNTAX      SEQUENCE OF ControlPlaneOtnEntityStateEntry
    MAX-ACCESS  not-accessible
    STATUS      current
    DESCRIPTION   ""
    ::=  { commonConfigAndStatus 8 }

controlPlaneOtnEntityStateEntry OBJECT-TYPE
    SYNTAX      ControlPlaneOtnEntityStateEntry
    MAX-ACCESS  not-accessible
    STATUS      current
    DESCRIPTION   ""
    INDEX       {
                  controlPlaneOtnEntityIndex
                }
    ::=  { controlPlaneOtnEntityStateTable 1 }

ControlPlaneOtnEntityStateEntry ::=  SEQUENCE
  { controlPlaneOtnEntityStateAdmin FspR7AdminState,
    controlPlaneOtnEntityStateOper FspR7OperState,
    controlPlaneOtnEntityStateSecondaryStates FspR7EntitySecondaryStates }

controlPlaneOtnEntityStateAdmin OBJECT-TYPE
    SYNTAX      FspR7AdminState
    MAX-ACCESS  read-write
    STATUS      current
    DESCRIPTION   "The Adminstrative State will be displayed in the GUI with full name values;
         it will be differently displayed in TL1 SYNTAX according to TL1 display rules.
         The transaction into the UAS state requires a special destroy/delete function."
    ::=  { controlPlaneOtnEntityStateEntry 1 }

controlPlaneOtnEntityStateOper OBJECT-TYPE
    SYNTAX      FspR7OperState
    MAX-ACCESS  read-only
    STATUS      current
    DESCRIPTION   "The Operational State will be displayed on the GUI with full name values;
         it will be differently displayed in TL1 SYNTAX according to TL1 display rules"
    ::=  { controlPlaneOtnEntityStateEntry 2 }

controlPlaneOtnEntityStateSecondaryStates OBJECT-TYPE
    SYNTAX      FspR7EntitySecondaryStates
    MAX-ACCESS  read-only
    STATUS      current
    DESCRIPTION   "Secondary states of an entity."
    ::=  { controlPlaneOtnEntityStateEntry 3 }

controlPlaneOtnEntityStateCapTable OBJECT-TYPE
    SYNTAX      SEQUENCE OF ControlPlaneOtnEntityStateCapEntry
    MAX-ACCESS  not-accessible
    STATUS      current
    DESCRIPTION   ""
    ::=  { commonConfigAndStatus 9 }

controlPlaneOtnEntityStateCapEntry OBJECT-TYPE
    SYNTAX      ControlPlaneOtnEntityStateCapEntry
    MAX-ACCESS  not-accessible
    STATUS      current
    DESCRIPTION   ""
    INDEX       {
                  controlPlaneOtnEntityIndex
                }
    ::=  { controlPlaneOtnEntityStateCapTable 1 }

ControlPlaneOtnEntityStateCapEntry ::=  SEQUENCE
  { controlPlaneOtnEntityStateCapAdmin FspR7AdminStateCaps }

controlPlaneOtnEntityStateCapAdmin OBJECT-TYPE
    SYNTAX      FspR7AdminStateCaps
    MAX-ACCESS  read-only
    STATUS      current
    DESCRIPTION   "This object contains capabilities for entityStateAdmin object."
    ::=  { controlPlaneOtnEntityStateCapEntry 1 }

ptpEntityStateTable OBJECT-TYPE
    SYNTAX      SEQUENCE OF PtpEntityStateEntry
    MAX-ACCESS  not-accessible
    STATUS      current
    DESCRIPTION   ""
    ::=  { commonConfigAndStatus 10 }

ptpEntityStateEntry OBJECT-TYPE
    SYNTAX      PtpEntityStateEntry
    MAX-ACCESS  not-accessible
    STATUS      current
    DESCRIPTION   ""
    INDEX       {
                  ptpEntityIndex
                }
    ::=  { ptpEntityStateTable 1 }

PtpEntityStateEntry ::=  SEQUENCE
  { ptpEntityStateAdmin FspR7AdminState,
    ptpEntityStateOper FspR7OperState,
    ptpEntityStateSecondaryStates FspR7EntitySecondaryStates }

ptpEntityStateAdmin OBJECT-TYPE
    SYNTAX      FspR7AdminState
    MAX-ACCESS  read-write
    STATUS      current
    DESCRIPTION   "The Adminstrative State will be displayed in the GUI with full name values;
         it will be differently displayed in TL1 SYNTAX according to TL1 display rules.
         The transaction into the UAS state requires a special destroy/delete function."
    ::=  { ptpEntityStateEntry 1 }

ptpEntityStateOper OBJECT-TYPE
    SYNTAX      FspR7OperState
    MAX-ACCESS  read-only
    STATUS      current
    DESCRIPTION   "The Operational State will be displayed on the GUI with full name values;
         it will be differently displayed in TL1 SYNTAX according to TL1 display rules"
    ::=  { ptpEntityStateEntry 2 }

ptpEntityStateSecondaryStates OBJECT-TYPE
    SYNTAX      FspR7EntitySecondaryStates
    MAX-ACCESS  read-only
    STATUS      current
    DESCRIPTION   "Secondary states of an entity."
    ::=  { ptpEntityStateEntry 3 }

ptpEntityStateCapTable OBJECT-TYPE
    SYNTAX      SEQUENCE OF PtpEntityStateCapEntry
    MAX-ACCESS  not-accessible
    STATUS      current
    DESCRIPTION   ""
    ::=  { commonConfigAndStatus 11 }

ptpEntityStateCapEntry OBJECT-TYPE
    SYNTAX      PtpEntityStateCapEntry
    MAX-ACCESS  not-accessible
    STATUS      current
    DESCRIPTION   ""
    INDEX       {
                  ptpEntityIndex
                }
    ::=  { ptpEntityStateCapTable 1 }

PtpEntityStateCapEntry ::=  SEQUENCE
  { ptpEntityStateCapAdmin FspR7AdminStateCaps }

ptpEntityStateCapAdmin OBJECT-TYPE
    SYNTAX      FspR7AdminStateCaps
    MAX-ACCESS  read-only
    STATUS      current
    DESCRIPTION   "This object contains capabilities for entityStateAdmin object."
    ::=  { ptpEntityStateCapEntry 1 }

childrenTable OBJECT-TYPE
    SYNTAX      SEQUENCE OF ChildrenEntry
    MAX-ACCESS  not-accessible
    STATUS      current
    DESCRIPTION   "Table for all existing addresses. Gives the Row Pointer to the
         subtending entity in the containment."
    ::=  { commonConfigAndStatus 12 }

childrenEntry OBJECT-TYPE
    SYNTAX      ChildrenEntry
    MAX-ACCESS  not-accessible
    STATUS      current
    DESCRIPTION   ""
    INDEX       {
                  entityIndex,
                  childrenId
                }
    ::=  { childrenTable 1 }

ChildrenEntry ::=  SEQUENCE
  { childrenId Unsigned32,
    childrenRowPointer RowPointer }

childrenId OBJECT-TYPE
    SYNTAX      Unsigned32
    MAX-ACCESS  not-accessible
    STATUS      current
    DESCRIPTION   "Order Index"
    ::=  { childrenEntry 1 }

childrenRowPointer OBJECT-TYPE
    SYNTAX      RowPointer
    MAX-ACCESS  read-only
    STATUS      current
    DESCRIPTION
        "" 
    ::=  { childrenEntry 2 }

moduleDiagnosticsTable OBJECT-TYPE
    SYNTAX      SEQUENCE OF ModuleDiagnosticsEntry
    MAX-ACCESS  not-accessible
    STATUS      current
    DESCRIPTION   "The ModuleDiagnostics table. This table extends the entries
         in the inventoryTable for the FspR7 modules."
    ::=  { equipmentConfigAndStatus 1 }

moduleDiagnosticsEntry OBJECT-TYPE
    SYNTAX      ModuleDiagnosticsEntry
    MAX-ACCESS  not-accessible
    STATUS      current
    DESCRIPTION   "An entry in the ModuleDiagnostics table. Each entry in this table represents
         a field replacable module in a shelf, which is inserted into or removed from a container (slot)."
    INDEX       {
                  entityIndex
                }
    ::=  { moduleDiagnosticsTable 1 }

ModuleDiagnosticsEntry ::=  SEQUENCE
  { moduleDiagnosticsTemp Integer32,
    moduleDiagnosticsUpperTempThres Integer32,
    moduleDiagnosticsLowerTempThres Integer32,
    moduleDiagnosticsCapabilityLevel FspR7CapInventory,
    moduleDiagnosticsCurrentLowThres Unsigned32,
    moduleDiagnosticsCurrentHighThres Unsigned32,
    moduleDiagnosticsDescription SnmpAdminString,
    moduleDiagnosticsInventoryDescription SnmpAdminString }

moduleDiagnosticsTemp OBJECT-TYPE
    SYNTAX      Integer32 
    UNITS       "0.1 degree Celsius"
    MAX-ACCESS  read-only
    STATUS      current
    DESCRIPTION   "Actual temperature on the module."
    ::=  { moduleDiagnosticsEntry 1 }

moduleDiagnosticsUpperTempThres OBJECT-TYPE
    SYNTAX      Integer32 
    UNITS       "0.1 degree Celsius"
    MAX-ACCESS  read-only
    STATUS      current
    DESCRIPTION   "Upper temperature threshold for threshold crossing alarm.
         Temperatures above this value will cause a Notification."
    ::=  { moduleDiagnosticsEntry 2 }

moduleDiagnosticsLowerTempThres OBJECT-TYPE
    SYNTAX      Integer32 
    UNITS       "0.1 degree Celsius"
    MAX-ACCESS  read-only
    STATUS      current
    DESCRIPTION   "Lower temperature threshold for threshold crossing alarm.
         Temperatures below this value will cause a Notification."
    ::=  { moduleDiagnosticsEntry 3 }

moduleDiagnosticsCapabilityLevel OBJECT-TYPE
    SYNTAX      FspR7CapInventory
    MAX-ACCESS  read-only
    STATUS      current
    DESCRIPTION
        "Capability level reported by HW" 
    ::=  { moduleDiagnosticsEntry 4 }

moduleDiagnosticsCurrentLowThres OBJECT-TYPE
    SYNTAX      Unsigned32 
    UNITS       "0.001 A"
    MAX-ACCESS  read-only
    STATUS      current
    DESCRIPTION   "Lower current threshold for threshold crossing alarm.
         Current below this value will cause a Notification."
    ::=  { moduleDiagnosticsEntry 5 }

moduleDiagnosticsCurrentHighThres OBJECT-TYPE
    SYNTAX      Unsigned32 
    UNITS       "0.001 A"
    MAX-ACCESS  read-only
    STATUS      current
    DESCRIPTION   "Higher current threshold for threshold crossing alarm.
         Current below this value will cause a Notification."
    ::=  { moduleDiagnosticsEntry 6 }

moduleDiagnosticsDescription OBJECT-TYPE
    SYNTAX      SnmpAdminString
    MAX-ACCESS  read-only
    STATUS      current
    DESCRIPTION   ""
    ::=  { moduleDiagnosticsEntry 7 }

moduleDiagnosticsInventoryDescription OBJECT-TYPE
    SYNTAX      SnmpAdminString
    MAX-ACCESS  read-only
    STATUS      current
    DESCRIPTION   ""
    ::=  { moduleDiagnosticsEntry 8 }

currentDiagnosticsTable OBJECT-TYPE
    SYNTAX      SEQUENCE OF CurrentDiagnosticsEntry
    MAX-ACCESS  not-accessible
    STATUS      current
    DESCRIPTION   "The currentDiagnostics table. This table extends the entries
         in the inventoryTable for the FspR7 modules."
    ::=  { equipmentConfigAndStatus 2 }

currentDiagnosticsEntry OBJECT-TYPE
    SYNTAX      CurrentDiagnosticsEntry
    MAX-ACCESS  not-accessible
    STATUS      current
    DESCRIPTION   "An entry in the currentDiagnostics table."
    INDEX       {
                  entityIndex
                }
    ::=  { currentDiagnosticsTable 1 }

CurrentDiagnosticsEntry ::=  SEQUENCE
  { currentDiagnosticsAmpere Unsigned32,
    currentDiagnosticsUpperThres Unsigned32,
    currentDiagnosticsPsuOutputPower FspR7PsuOutputPower }

currentDiagnosticsAmpere OBJECT-TYPE
    SYNTAX      Unsigned32 
    UNITS       "0.001 A"
    MAX-ACCESS  read-only
    STATUS      current
    DESCRIPTION   "Instantaneous current measured."
    ::=  { currentDiagnosticsEntry 1 }

currentDiagnosticsUpperThres OBJECT-TYPE
    SYNTAX      Unsigned32 
    UNITS       "0.001 A"
    MAX-ACCESS  read-only
    STATUS      current
    DESCRIPTION   "Upper current threshold for threshold crossing condition.
         Currents above this value will cause a Notification"
    ::=  { currentDiagnosticsEntry 2 }

currentDiagnosticsPsuOutputPower OBJECT-TYPE
    SYNTAX      FspR7PsuOutputPower
    MAX-ACCESS  read-only
    STATUS      current
    DESCRIPTION
        "Maximum PSU Output Power" 
    ::=  { currentDiagnosticsEntry 3 }

moduleConfigTable OBJECT-TYPE
    SYNTAX      SEQUENCE OF ModuleConfigEntry
    MAX-ACCESS  not-accessible
    STATUS      current
    DESCRIPTION   "The ModuleConfig table. This table extends the entries in the
         inventoryTable for the FspR7 modules."
    ::=  { equipmentConfigAndStatus 3 }

moduleConfigEntry OBJECT-TYPE
    SYNTAX      ModuleConfigEntry
    MAX-ACCESS  not-accessible
    STATUS      current
    DESCRIPTION   "An entry in the ModuleConfig table. Each entry in this table represents a
         field replacable module in a shelf, which is inserted into or removed from a container (slot)."
    INDEX       {
                  entityIndex
                }
    ::=  { moduleConfigTable 1 }

ModuleConfigEntry ::=  SEQUENCE
  { moduleConfigAlias SnmpAdminString,
    moduleConfigCapabilityLevelProvision FspR7CapInventory,
    moduleConfigOutputReset FspR7TifOutputReset,
    moduleConfigScrambling FspR7Scrambling,
    moduleConfigLagSysPrio Unsigned32,
    moduleConfigEqlzAdmin FspR7EqlzAdminState,
    moduleConfigInitiateEqualization FspR7InitEqualization,
    moduleConfigCac FspR7L2CacEnable,
    moduleConfigFiberDetect FspR7FiberDetect }

moduleConfigAlias OBJECT-TYPE
    SYNTAX      SnmpAdminString
    MAX-ACCESS  read-write
    STATUS      current
    DESCRIPTION   "A string, configurable by the operator, containing
         a symbolic name for the module."
    ::=  { moduleConfigEntry 1 }

moduleConfigCapabilityLevelProvision OBJECT-TYPE
    SYNTAX      FspR7CapInventory
    MAX-ACCESS  read-write
    STATUS      current
    DESCRIPTION
        "Capability level provisioned" 
    ::=  { moduleConfigEntry 2 }

moduleConfigOutputReset OBJECT-TYPE
    SYNTAX      FspR7TifOutputReset
    MAX-ACCESS  read-write
    STATUS      current
    DESCRIPTION
        "Has the same function as the HW switch at the UTM board" 
    ::=  { moduleConfigEntry 3 }

moduleConfigScrambling OBJECT-TYPE
    SYNTAX      FspR7Scrambling
    MAX-ACCESS  read-write
    STATUS      current
    DESCRIPTION   "Virtual Fac. Scrambling"
    ::=  { moduleConfigEntry 4 }

moduleConfigLagSysPrio OBJECT-TYPE
    SYNTAX      Unsigned32 (0..65535 | 4294967295)
    MAX-ACCESS  read-write
    STATUS      current
    DESCRIPTION
        "Link Aggregation Group Actor System Priority Part of LAG ID" 
    ::=  { moduleConfigEntry 5 }

moduleConfigEqlzAdmin OBJECT-TYPE
    SYNTAX      FspR7EqlzAdminState
    MAX-ACCESS  read-write
    STATUS      current
    DESCRIPTION
        "Scheduled Equalization Administration" 
    ::=  { moduleConfigEntry 6 }

moduleConfigInitiateEqualization OBJECT-TYPE
    SYNTAX      FspR7InitEqualization
    MAX-ACCESS  read-write
    STATUS      current
    DESCRIPTION
        "Initiate Equalization" 
    ::=  { moduleConfigEntry 7 }

moduleConfigCac OBJECT-TYPE
    SYNTAX      FspR7L2CacEnable
    MAX-ACCESS  read-write
    STATUS      current
    DESCRIPTION
        "Enable of CAC" 
    ::=  { moduleConfigEntry 8 }

moduleConfigFiberDetect OBJECT-TYPE
    SYNTAX      FspR7FiberDetect
    MAX-ACCESS  read-write
    STATUS      current
    DESCRIPTION
        "Fiber Detect" 
    ::=  { moduleConfigEntry 9 }

moduleDataTable OBJECT-TYPE
    SYNTAX      SEQUENCE OF ModuleDataEntry
    MAX-ACCESS  not-accessible
    STATUS      current
    DESCRIPTION   ""
    ::=  { equipmentConfigAndStatus 4 }

moduleDataEntry OBJECT-TYPE
    SYNTAX      ModuleDataEntry
    MAX-ACCESS  not-accessible
    STATUS      current
    DESCRIPTION   ""
    INDEX       {
                  entityIndex
                }
    ::=  { moduleDataTable 1 }

ModuleDataEntry ::=  SEQUENCE
  { moduleDataDeploymentScenario FspR7DeploymentScenario,
    moduleDataHeight Unsigned32,
    moduleDataWidth Unsigned32,
    moduleDataNetworkPorts Unsigned32,
    moduleDataClientPorts Unsigned32,
    moduleDataStages FspR7Stages,
    moduleDataConnectionLocation Unsigned32,
    moduleDataInternalPorts Unsigned32,
    moduleDataInternalPlugs FspR7EquipmentTypeCaps,
    moduleDataInternalPlugRates FspR7PlugDataRateCaps,
    moduleDataChannel FspR7ChannelIdentifierCaps,
    moduleDataUpgradePorts Unsigned32,
    moduleDataSerialPorts Unsigned32,
    moduleDataEccPorts Unsigned32,
    moduleDataMaxPowerConsumption Unsigned32,
    moduleDataScuRing FspR7ScuRing,
    moduleDataNetworkPlugs FspR7EquipmentTypeCaps,
    moduleDataMidstagePorts Unsigned32,
    moduleDataMode FspR7TransmissionMode,
    moduleDataRoadmNumber FspR7RoadmNumber,
    moduleDataChannelsNumber FspR7NumberOfChannels,
    moduleDataChannelSpacing FspR7ChannelSpacing,
    moduleDataTransmitChannel FspR7ChannelIdentifier,
    moduleDataCategory FspR7Category,
    moduleDataFanPorts Unsigned32,
    moduleDataLanPorts Unsigned32,
    moduleDataMapping FspR7Mapping,
    moduleDataBand FspR7OpticalBand,
    moduleDataChannelsProvision FspR7NumberOfChannels,
    moduleDataType FspR7EquipmentType,
    moduleDataTerminationType FspR7EquipmentType,
    moduleDataFiberDetectStatus FspR7FDStatusCaps,
    moduleDataInternalPlugsReach FspR7OpticalInterfaceReachCaps,
    moduleDataSpeqAlsConf FspR7EnableDisable,
    moduleDataTrafficDirection FspR7TrafficDirection,
    moduleDataOscUsage FspR7OscUsage }

moduleDataDeploymentScenario OBJECT-TYPE
    SYNTAX      FspR7DeploymentScenario
    MAX-ACCESS  read-only
    STATUS      current
    DESCRIPTION
        "Describes how the card is applied related to a network scenario" 
    ::=  { moduleDataEntry 1 }

moduleDataHeight OBJECT-TYPE
    SYNTAX      Unsigned32 
    UNITS       "0.1 HU"
    MAX-ACCESS  read-only
    STATUS      current
    DESCRIPTION
        "Module Height" 
    ::=  { moduleDataEntry 2 }

moduleDataWidth OBJECT-TYPE
    SYNTAX      Unsigned32 
    UNITS       "0.1 HP"
    MAX-ACCESS  read-only
    STATUS      current
    DESCRIPTION
        "Module Width" 
    ::=  { moduleDataEntry 3 }

moduleDataNetworkPorts OBJECT-TYPE
    SYNTAX      Unsigned32
    MAX-ACCESS  read-only
    STATUS      current
    DESCRIPTION
        "Number of Network Ports" 
    ::=  { moduleDataEntry 4 }

moduleDataClientPorts OBJECT-TYPE
    SYNTAX      Unsigned32 (0..128 | 4294967295)
    MAX-ACCESS  read-only
    STATUS      current
    DESCRIPTION
        "Number of Client Ports" 
    ::=  { moduleDataEntry 5 }

moduleDataStages OBJECT-TYPE
    SYNTAX      FspR7Stages
    MAX-ACCESS  read-only
    STATUS      current
    DESCRIPTION
        "Number of Stages" 
    ::=  { moduleDataEntry 6 }

moduleDataConnectionLocation OBJECT-TYPE
    SYNTAX      Unsigned32
    MAX-ACCESS  read-only
    STATUS      current
    DESCRIPTION
        "Defines the Location of the connector of a module in numbers from left to ricght (view is from the front)" 
    ::=  { moduleDataEntry 7 }

moduleDataInternalPorts OBJECT-TYPE
    SYNTAX      Unsigned32
    MAX-ACCESS  read-only
    STATUS      current
    DESCRIPTION
        "Number of Internal Ports" 
    ::=  { moduleDataEntry 8 }

moduleDataInternalPlugs OBJECT-TYPE
    SYNTAX      FspR7EquipmentTypeCaps
    MAX-ACCESS  read-only
    STATUS      current
    DESCRIPTION
        "Internal Plugs Required" 
    ::=  { moduleDataEntry 9 }

moduleDataInternalPlugRates OBJECT-TYPE
    SYNTAX      FspR7PlugDataRateCaps
    MAX-ACCESS  read-only
    STATUS      current
    DESCRIPTION
        "List of Provisionable Internal Plug Rates Supported" 
    ::=  { moduleDataEntry 10 }

moduleDataChannel OBJECT-TYPE
    SYNTAX      FspR7ChannelIdentifierCaps
    MAX-ACCESS  read-only
    STATUS      current
    DESCRIPTION
        "Possible internal channel" 
    ::=  { moduleDataEntry 11 }

moduleDataUpgradePorts OBJECT-TYPE
    SYNTAX      Unsigned32
    MAX-ACCESS  read-only
    STATUS      current
    DESCRIPTION
        "Number of Upgrade Ports" 
    ::=  { moduleDataEntry 12 }

moduleDataSerialPorts OBJECT-TYPE
    SYNTAX      Unsigned32 (0..2 | 4294967295)
    MAX-ACCESS  read-only
    STATUS      current
    DESCRIPTION
        "Number of Serial Ports" 
    ::=  { moduleDataEntry 13 }

moduleDataEccPorts OBJECT-TYPE
    SYNTAX      Unsigned32 (0..50 | 4294967295)
    MAX-ACCESS  read-only
    STATUS      current
    DESCRIPTION
        "Number of PPP over ECC Ports" 
    ::=  { moduleDataEntry 14 }

moduleDataMaxPowerConsumption OBJECT-TYPE
    SYNTAX      Unsigned32 
    UNITS       "0.1 W"
    MAX-ACCESS  read-only
    STATUS      current
    DESCRIPTION
        "Maximum Power Consumption of the device" 
    ::=  { moduleDataEntry 15 }

moduleDataScuRing OBJECT-TYPE
    SYNTAX      FspR7ScuRing
    MAX-ACCESS  read-only
    STATUS      current
    DESCRIPTION
        "SCU Interconnection" 
    ::=  { moduleDataEntry 16 }

moduleDataNetworkPlugs OBJECT-TYPE
    SYNTAX      FspR7EquipmentTypeCaps
    MAX-ACCESS  read-only
    STATUS      current
    DESCRIPTION
        "Network Plugs Required" 
    ::=  { moduleDataEntry 17 }

moduleDataMidstagePorts OBJECT-TYPE
    SYNTAX      Unsigned32
    MAX-ACCESS  read-only
    STATUS      current
    DESCRIPTION
        "Number of Midstage Ports" 
    ::=  { moduleDataEntry 18 }

moduleDataMode OBJECT-TYPE
    SYNTAX      FspR7TransmissionMode
    MAX-ACCESS  read-only
    STATUS      current
    DESCRIPTION   "The transmission mode of the module."
    ::=  { moduleDataEntry 19 }

moduleDataRoadmNumber OBJECT-TYPE
    SYNTAX      FspR7RoadmNumber
    MAX-ACCESS  read-only
    STATUS      current
    DESCRIPTION
        "Number for ROADM module typically associated with a Network Fiber or Degree" 
    ::=  { moduleDataEntry 20 }

moduleDataChannelsNumber OBJECT-TYPE
    SYNTAX      FspR7NumberOfChannels
    MAX-ACCESS  read-only
    STATUS      current
    DESCRIPTION   "Number of channels supported by an entity"
    ::=  { moduleDataEntry 21 }

moduleDataChannelSpacing OBJECT-TYPE
    SYNTAX      FspR7ChannelSpacing
    MAX-ACCESS  read-only
    STATUS      current
    DESCRIPTION
        "ITU Grid channel spacing" 
    ::=  { moduleDataEntry 22 }

moduleDataTransmitChannel OBJECT-TYPE
    SYNTAX      FspR7ChannelIdentifier
    MAX-ACCESS  read-only
    STATUS      current
    DESCRIPTION
        "Channel" 
    ::=  { moduleDataEntry 23 }

moduleDataCategory OBJECT-TYPE
    SYNTAX      FspR7Category
    MAX-ACCESS  read-only
    STATUS      current
    DESCRIPTION
        "Used For Internal Purposes (and possibly for pre-selection in GUI)" 
    ::=  { moduleDataEntry 24 }

moduleDataFanPorts OBJECT-TYPE
    SYNTAX      Unsigned32 (0..3 | 4294967295)
    MAX-ACCESS  read-only
    STATUS      current
    DESCRIPTION
        "Number of Fan Plug ins" 
    ::=  { moduleDataEntry 25 }

moduleDataLanPorts OBJECT-TYPE
    SYNTAX      Unsigned32 (0..20 | 4294967295)
    MAX-ACCESS  read-only
    STATUS      current
    DESCRIPTION
        "Number of LAN Ports" 
    ::=  { moduleDataEntry 26 }

moduleDataMapping OBJECT-TYPE
    SYNTAX      FspR7Mapping
    MAX-ACCESS  read-only
    STATUS      current
    DESCRIPTION
        "Type of mapping; transparent or framing" 
    ::=  { moduleDataEntry 27 }

moduleDataBand OBJECT-TYPE
    SYNTAX      FspR7OpticalBand
    MAX-ACCESS  read-only
    STATUS      current
    DESCRIPTION
        "Band Provision. Reference to BAND__INVENTORY." 
    ::=  { moduleDataEntry 28 }

moduleDataChannelsProvision OBJECT-TYPE
    SYNTAX      FspR7NumberOfChannels
    MAX-ACCESS  read-only
    STATUS      current
    DESCRIPTION
        "Number of channels supported by an entity" 
    ::=  { moduleDataEntry 29 }

moduleDataType OBJECT-TYPE
    SYNTAX      FspR7EquipmentType
    MAX-ACCESS  read-only
    STATUS      current
    DESCRIPTION   "The TYPE of Module."
    ::=  { moduleDataEntry 30 }

moduleDataTerminationType OBJECT-TYPE
    SYNTAX      FspR7EquipmentType
    MAX-ACCESS  read-only
    STATUS      current
    DESCRIPTION
        "Type of Physical Termination" 
    ::=  { moduleDataEntry 31 }

moduleDataFiberDetectStatus OBJECT-TYPE
    SYNTAX      FspR7FDStatusCaps
    MAX-ACCESS  read-only
    STATUS      current
    DESCRIPTION
        "Fiber Detect Status" 
    ::=  { moduleDataEntry 32 }

moduleDataInternalPlugsReach OBJECT-TYPE
    SYNTAX      FspR7OpticalInterfaceReachCaps
    MAX-ACCESS  read-only
    STATUS      current
    DESCRIPTION   "Reach of Internal Plugs"
    ::=  { moduleDataEntry 33 }

moduleDataSpeqAlsConf OBJECT-TYPE
    SYNTAX      FspR7EnableDisable
    MAX-ACCESS  read-only
    STATUS      current
    DESCRIPTION   "Enables EDFA amplifiers to provision their LOS behavior as 'ALS enabled' or 'ALS disabled'."
    ::=  { moduleDataEntry 35 }

moduleDataTrafficDirection OBJECT-TYPE
    SYNTAX      FspR7TrafficDirection
    MAX-ACCESS  read-only
    STATUS      current
    DESCRIPTION
        "Traffic Direction" 
    ::=  { moduleDataEntry 36 }

moduleDataOscUsage OBJECT-TYPE
    SYNTAX      FspR7OscUsage
    MAX-ACCESS  read-only
    STATUS      current
    DESCRIPTION
        "Select if and how the OSC is to be used on an amplifier" 
    ::=  { moduleDataEntry 37 }

wdmChannelModuleInventoryTable OBJECT-TYPE
    SYNTAX      SEQUENCE OF WdmChannelModuleInventoryEntry
    MAX-ACCESS  not-accessible
    STATUS      current
    DESCRIPTION   "The WdmChannelModuleInventory table. This table extends the entries in
         the inventoryTable for the FspR7 wdmChannelModules."
    ::=  { equipmentConfigAndStatus 5 }

wdmChannelModuleInventoryEntry OBJECT-TYPE
    SYNTAX      WdmChannelModuleInventoryEntry
    MAX-ACCESS  not-accessible
    STATUS      current
    DESCRIPTION   "An entry in the WdmChannelModuleInventory table. Each entry in this
         table represents a field replacable wdmChannelModule in a shelf,
         which is inserted into or removed from a container (slot)."
    INDEX       {
                  entityIndex
                }
    ::=  { wdmChannelModuleInventoryTable 1 }

WdmChannelModuleInventoryEntry ::=  SEQUENCE
  { wdmChannelModuleInventoryChannelId FspR7ChannelIdentifier,
    wdmChannelModuleInventoryReach FspR7OpticalInterfaceReach }

wdmChannelModuleInventoryChannelId OBJECT-TYPE
    SYNTAX      FspR7ChannelIdentifier
    MAX-ACCESS  read-only
    STATUS      current
    DESCRIPTION   "The WDM channel identifier of the wdmChannelModule."
    ::=  { wdmChannelModuleInventoryEntry 1 }

wdmChannelModuleInventoryReach OBJECT-TYPE
    SYNTAX      FspR7OpticalInterfaceReach
    MAX-ACCESS  read-only
    STATUS      current
    DESCRIPTION   "The optical reach of the wdmChannelModule."
    ::=  { wdmChannelModuleInventoryEntry 2 }

wdmChannelModuleDataTable OBJECT-TYPE
    SYNTAX      SEQUENCE OF WdmChannelModuleDataEntry
    MAX-ACCESS  not-accessible
    STATUS      current
    DESCRIPTION   "The WdmChannelModuleData table. This table extends the entries
         in the inventoryTable for the FspR7 wdmChannelModules."
    ::=  { equipmentConfigAndStatus 6 }

wdmChannelModuleDataEntry OBJECT-TYPE
    SYNTAX      WdmChannelModuleDataEntry
    MAX-ACCESS  not-accessible
    STATUS      current
    DESCRIPTION   "An entry in the WdmChannelModuleData table. Each entry in this table
         represents a field replacable wdmChannelModule in a shelf, which is
         inserted into or removed from a container (slot)."
    INDEX       {
                  entityIndex
                }
    ::=  { wdmChannelModuleDataTable 1 }

WdmChannelModuleDataEntry ::=  SEQUENCE
  { wdmChannelModuleDataSuppClientPlugRates FspR7PlugDataRateCaps,
    wdmChannelModuleDataSuppNetworkPlugRates FspR7PlugDataRateCaps,
    wdmChannelModuleDataSuppClientPlugTypes FspR7EquipmentTypeCaps,
    wdmChannelModuleDataSuppNetworkPlugTypes FspR7EquipmentTypeCaps }

wdmChannelModuleDataSuppClientPlugRates OBJECT-TYPE
    SYNTAX      FspR7PlugDataRateCaps
    MAX-ACCESS  read-only
    STATUS      current
    DESCRIPTION   "The supported client plug rates of the wdmChannelModule."
    ::=  { wdmChannelModuleDataEntry 1 }

wdmChannelModuleDataSuppNetworkPlugRates OBJECT-TYPE
    SYNTAX      FspR7PlugDataRateCaps
    MAX-ACCESS  read-only
    STATUS      current
    DESCRIPTION   "The supported network plug rates of the wdmChannelModule."
    ::=  { wdmChannelModuleDataEntry 2 }

wdmChannelModuleDataSuppClientPlugTypes OBJECT-TYPE
    SYNTAX      FspR7EquipmentTypeCaps
    MAX-ACCESS  read-only
    STATUS      current
    DESCRIPTION   "The supported client plug types of the wdmChannelModule."
    ::=  { wdmChannelModuleDataEntry 3 }

wdmChannelModuleDataSuppNetworkPlugTypes OBJECT-TYPE
    SYNTAX      FspR7EquipmentTypeCaps
    MAX-ACCESS  read-only
    STATUS      current
    DESCRIPTION   "The supported network plug types of the wdmChannelModule."
    ::=  { wdmChannelModuleDataEntry 4 }

plugInventoryTable OBJECT-TYPE
    SYNTAX      SEQUENCE OF PlugInventoryEntry
    MAX-ACCESS  not-accessible
    STATUS      current
    DESCRIPTION   "The PlugInventory table. This table extends the entries
         in the inventoryTable for the FspR7 plugs (SFP/XFP). The data in this table
         only applies to equipped plugs."
    ::=  { equipmentConfigAndStatus 7 }

plugInventoryEntry OBJECT-TYPE
    SYNTAX      PlugInventoryEntry
    MAX-ACCESS  not-accessible
    STATUS      current
    DESCRIPTION   "An entry in the PlugInventory table. Each entry in this table represents
         a field replacable plug in a card, which is inserted into or removed from
         a container (slot)."
    INDEX       {
                  entityIndex
                }
    ::=  { plugInventoryTable 1 }

PlugInventoryEntry ::=  SEQUENCE
  { plugInventoryMaxDataRate FspR7PlugDataRate,
    plugInventoryChannelId FspR7ChannelIdentifier,
    plugInventoryReach FspR7OpticalInterfaceReach }

plugInventoryMaxDataRate OBJECT-TYPE
    SYNTAX      FspR7PlugDataRate
    MAX-ACCESS  read-only
    STATUS      current
    DESCRIPTION   "The maximal supported data rate of the plug."
    ::=  { plugInventoryEntry 1 }

plugInventoryChannelId OBJECT-TYPE
    SYNTAX      FspR7ChannelIdentifier
    MAX-ACCESS  read-only
    STATUS      current
    DESCRIPTION   "The supported optical channel of the plug."
    ::=  { plugInventoryEntry 2 }

plugInventoryReach OBJECT-TYPE
    SYNTAX      FspR7OpticalInterfaceReach
    MAX-ACCESS  read-only
    STATUS      current
    DESCRIPTION   "The supported optical reach of the plug."
    ::=  { plugInventoryEntry 3 }

plugDataTable OBJECT-TYPE
    SYNTAX      SEQUENCE OF PlugDataEntry
    MAX-ACCESS  not-accessible
    STATUS      current
    DESCRIPTION   "The plugData table. This table extends the entries
         in the entityTable for the FspR7 plugs (SFP/XFP)."
    ::=  { equipmentConfigAndStatus 8 }

plugDataEntry OBJECT-TYPE
    SYNTAX      PlugDataEntry
    MAX-ACCESS  not-accessible
    STATUS      current
    DESCRIPTION   "An entry in the plugData table. Each entry in this table represents
         a field replacable plug in a card, which may be inserted into or
         removed from a container (slot)."
    INDEX       {
                  entityIndex
                }
    ::=  { plugDataTable 1 }

PlugDataEntry ::=  SEQUENCE
  { plugDataConnectorType FspR7ConnectorType,
    plugDataFiberType FspR7OpticalFiberType,
    plugDataLoopbackAttenuation Unsigned32,
    plugDataMaxPowerConsumption Unsigned32,
    plugDataGenericPorts Unsigned32 }

plugDataConnectorType OBJECT-TYPE
    SYNTAX      FspR7ConnectorType
    MAX-ACCESS  read-only
    STATUS      current
    DESCRIPTION   "The type of external connector on a plug (eg. SC, LC, RJ45, etc)."
    ::=  { plugDataEntry 1 }

plugDataFiberType OBJECT-TYPE
    SYNTAX      FspR7OpticalFiberType
    MAX-ACCESS  read-only
    STATUS      current
    DESCRIPTION   "The fiber type of this plug."
    ::=  { plugDataEntry 2 }

plugDataLoopbackAttenuation OBJECT-TYPE
    SYNTAX      Unsigned32 (10..300 | 4294967295) 
    UNITS       "0.1 dB"
    MAX-ACCESS  read-only
    STATUS      current
    DESCRIPTION   "Loop back attenuation of the plug"
    ::=  { plugDataEntry 3 }

plugDataMaxPowerConsumption OBJECT-TYPE
    SYNTAX      Unsigned32 
    UNITS       "0.1 W"
    MAX-ACCESS  read-only
    STATUS      current
    DESCRIPTION
        "Maximum Power Consumption of the device" 
    ::=  { plugDataEntry 4 }

plugDataGenericPorts OBJECT-TYPE
    SYNTAX      Unsigned32 (0..40 | 4294967295)
    MAX-ACCESS  read-only
    STATUS      current
    DESCRIPTION
        "Number of Generic Ports" 
    ::=  { plugDataEntry 5 }

apsConfigTable OBJECT-TYPE
    SYNTAX      SEQUENCE OF ApsConfigEntry
    MAX-ACCESS  not-accessible
    STATUS      current
    DESCRIPTION   "This table contains attributes related to the automatic protection
         switching (APS) functionality."
    ::=  { equipmentConfigAndStatus 9 }

apsConfigEntry OBJECT-TYPE
    SYNTAX      ApsConfigEntry
    MAX-ACCESS  not-accessible
    STATUS      current
    DESCRIPTION   "An entry in the APS configuration table. There is one entry in this
         table for each protection group."
    INDEX       {
                  entityIndex
                }
    ::=  { apsConfigTable 1 }

ApsConfigEntry ::=  SEQUENCE
  { apsConfigSDswitching EnableState,
    apsConfigHoldOffTime ApsHoldoffTime,
    apsConfigWaitToRestore Unsigned32 }

apsConfigSDswitching OBJECT-TYPE
    SYNTAX      EnableState
    MAX-ACCESS  read-write
    STATUS      current
    DESCRIPTION   "This state controls whether the switch criteria for the
         APS group will include the SignalDegrade alarm."
    ::=  { apsConfigEntry 1 }

apsConfigHoldOffTime OBJECT-TYPE
    SYNTAX      ApsHoldoffTime
    MAX-ACCESS  read-write
    STATUS      current
    DESCRIPTION   "This value controls the switch delay (0 to 90 seconds in
         100ms steps) for the protection group. Changing the hold-off
         time when the timer is active will not affect the active
         timer. The change will take effect the next time the timer
         is active."
    ::=  { apsConfigEntry 2 }

apsConfigWaitToRestore OBJECT-TYPE
    SYNTAX      Unsigned32 (5..12 | 4294967295) 
    UNITS       "min"
    MAX-ACCESS  read-write
    STATUS      current
    DESCRIPTION
        "Wait to Restore Timer value" 
    ::=  { apsConfigEntry 3 }

apsProtGroupStatusTable OBJECT-TYPE
    SYNTAX      SEQUENCE OF ApsProtGroupStatusEntry
    MAX-ACCESS  not-accessible
    STATUS      current
    DESCRIPTION   "This table contains status information related to the automatic protection
         switching (APS) functionality."
    ::=  { equipmentConfigAndStatus 10 }

apsProtGroupStatusEntry OBJECT-TYPE
    SYNTAX      ApsProtGroupStatusEntry
    MAX-ACCESS  not-accessible
    STATUS      current
    DESCRIPTION   "An entry in the APS status table. There is one entry in this table
         for each protection group."
    INDEX       {
                  entityIndex
                }
    ::=  { apsProtGroupStatusTable 1 }

ApsProtGroupStatusEntry ::=  SEQUENCE
  { apsProtGroupStatusApsType ApsType,
    apsProtGroupStatusDirection ApsDirection,
    apsProtGroupStatusRevertiveMode ApsRevertMode,
    apsProtGroupStatusProtectionMech ProtectionMech,
    apsProtGroupStatusWorkingIndex EntityIndex,
    apsProtGroupStatusProtectionIndex EntityIndex,
    apsProtGroupStatusProtectionType FspR7ProtectionType }

apsProtGroupStatusApsType OBJECT-TYPE
    SYNTAX      ApsType
    MAX-ACCESS  read-only
    STATUS      current
    DESCRIPTION   "The type of APS implemented in this protection group."
    ::=  { apsProtGroupStatusEntry 1 }

apsProtGroupStatusDirection OBJECT-TYPE
    SYNTAX      ApsDirection
    MAX-ACCESS  read-only
    STATUS      current
    DESCRIPTION   "Indicates whether the APS function is 'unidirectional' (single-ended)
         or 'bidirectional' (dual-ended)."
    ::=  { apsProtGroupStatusEntry 2 }

apsProtGroupStatusRevertiveMode OBJECT-TYPE
    SYNTAX      ApsRevertMode
    MAX-ACCESS  read-only
    STATUS      current
    DESCRIPTION   "Indicates if revertive switching is enable dor disabled."
    ::=  { apsProtGroupStatusEntry 3 }

apsProtGroupStatusProtectionMech OBJECT-TYPE
    SYNTAX      ProtectionMech
    MAX-ACCESS  read-only
    STATUS      current
    DESCRIPTION   "The protection type of this protection group."
    ::=  { apsProtGroupStatusEntry 4 }

apsProtGroupStatusWorkingIndex OBJECT-TYPE
    SYNTAX      EntityIndex
    MAX-ACCESS  read-only
    STATUS      current
    DESCRIPTION   "The entityIndex of the working section in the APS group."
    ::=  { apsProtGroupStatusEntry 5 }

apsProtGroupStatusProtectionIndex OBJECT-TYPE
    SYNTAX      EntityIndex
    MAX-ACCESS  read-only
    STATUS      current
    DESCRIPTION   "The entityIndex of the protection section. The protection section will
         become the active section when an APS switch occurs (ie, as a result of a failure on
         the working section)."
    ::=  { apsProtGroupStatusEntry 6 }

apsProtGroupStatusProtectionType OBJECT-TYPE
    SYNTAX      FspR7ProtectionType
    MAX-ACCESS  read-only
    STATUS      current
    DESCRIPTION
        "" 
    ::=  { apsProtGroupStatusEntry 7 }

apsProtFacilityConfigTable OBJECT-TYPE
    SYNTAX      SEQUENCE OF ApsProtFacilityConfigEntry
    MAX-ACCESS  not-accessible
    STATUS      current
    DESCRIPTION   "This table contains attributes related to the automatic protection
         switching (APS) functionality on a facility involved in a protection group."
    ::=  { equipmentConfigAndStatus 11 }

apsProtFacilityConfigEntry OBJECT-TYPE
    SYNTAX      ApsProtFacilityConfigEntry
    MAX-ACCESS  not-accessible
    STATUS      current
    DESCRIPTION   "An entry in the APS configuration table. There is one entry in this table
         for each facility involved in a protection group"
    INDEX       {
                  entityIndex
                }
    ::=  { apsProtFacilityConfigTable 1 }

ApsProtFacilityConfigEntry ::=  SEQUENCE
  { apsProtFacilityConfigSwitchCommand FspR7APSCommand,
    apsProtFacilityConfigInhibitSwitchToProt FspR7YesNo,
    apsProtFacilityConfigInhibitSwitchToWork FspR7YesNo }

apsProtFacilityConfigSwitchCommand OBJECT-TYPE
    SYNTAX      FspR7APSCommand
    MAX-ACCESS  read-write
    STATUS      current
    DESCRIPTION   "The switch command action for this facility. A command resulting
         in a switch event will also cause a change of the facility secondary state
         and a corresponding condition. Addressed by this command is the active port,
         the port to switch away from. Since this is a manual switch command, it will
         not switch if other port suffers from a signalfailure or a signal degrade."
    ::=  { apsProtFacilityConfigEntry 1 }

apsProtFacilityConfigInhibitSwitchToProt OBJECT-TYPE
    SYNTAX      FspR7YesNo
    MAX-ACCESS  read-write
    STATUS      current
    DESCRIPTION   "Inhibit Switch to protection facility. Inhibition blocks an automatic switch
         to the protection facility. Valid only for the working facility."
    ::=  { apsProtFacilityConfigEntry 2 }

apsProtFacilityConfigInhibitSwitchToWork OBJECT-TYPE
    SYNTAX      FspR7YesNo
    MAX-ACCESS  read-write
    STATUS      current
    DESCRIPTION   "Inhibit Switch to working facility. Inhibition blocks an automatic switch to the
         working facility. Valid only for the protection facility."
    ::=  { apsProtFacilityConfigEntry 3 }

shelfDiagnosticsTable OBJECT-TYPE
    SYNTAX      SEQUENCE OF ShelfDiagnosticsEntry
    MAX-ACCESS  not-accessible
    STATUS      current
    DESCRIPTION   "The ShelfDiagnostics table. This table extends the entries
         in the inventoryTable for the FspR7 shelves."
    ::=  { equipmentConfigAndStatus 12 }

shelfDiagnosticsEntry OBJECT-TYPE
    SYNTAX      ShelfDiagnosticsEntry
    MAX-ACCESS  not-accessible
    STATUS      current
    DESCRIPTION   "An entry in the ShelfDiagnostics table. Each entry in this table
         represents a shelf."
    INDEX       {
                  entityIndex
                }
    ::=  { shelfDiagnosticsTable 1 }

ShelfDiagnosticsEntry ::=  SEQUENCE
  { shelfDiagnosticsPowerConsumption Unsigned32,
    shelfDiagnosticsPowerOutput Unsigned32,
    shelfDiagnosticsMaxPowerConsumption Unsigned32 }

shelfDiagnosticsPowerConsumption OBJECT-TYPE
    SYNTAX      Unsigned32 
    UNITS       "W"
    MAX-ACCESS  read-only
    STATUS      current
    DESCRIPTION   "Actual power consumption of the shelf."
    ::=  { shelfDiagnosticsEntry 1 }

shelfDiagnosticsPowerOutput OBJECT-TYPE
    SYNTAX      Unsigned32 
    UNITS       "W"
    MAX-ACCESS  read-only
    STATUS      current
    DESCRIPTION   "Actual power output of the shelf."
    ::=  { shelfDiagnosticsEntry 2 }

shelfDiagnosticsMaxPowerConsumption OBJECT-TYPE
    SYNTAX      Unsigned32 
    UNITS       "0.1 W"
    MAX-ACCESS  read-only
    STATUS      current
    DESCRIPTION
        "Maximum Power Consumption of the device" 
    ::=  { shelfDiagnosticsEntry 3 }

dcnTopologyDataTable OBJECT-TYPE
    SYNTAX      SEQUENCE OF DcnTopologyDataEntry
    MAX-ACCESS  not-accessible
    STATUS      current
    DESCRIPTION   ""
    ::=  { equipmentConfigAndStatus 13 }

dcnTopologyDataEntry OBJECT-TYPE
    SYNTAX      DcnTopologyDataEntry
    MAX-ACCESS  not-accessible
    STATUS      current
    DESCRIPTION   "List of detected nodes in the DCN topology."
    INDEX       {
                  entityIndex,
                  dcnTopologyDataIndex
                }
    ::=  { dcnTopologyDataTable 1 }

DcnTopologyDataEntry ::=  SEQUENCE
  { dcnTopologyDataIndex Unsigned32,
    dcnTopologyDataNodeIpAddress IpAddress }

dcnTopologyDataIndex OBJECT-TYPE
    SYNTAX      Unsigned32
    MAX-ACCESS  not-accessible
    STATUS      current
    DESCRIPTION   ""
    ::=  { dcnTopologyDataEntry 1 }

dcnTopologyDataNodeIpAddress OBJECT-TYPE
    SYNTAX      IpAddress
    MAX-ACCESS  read-only
    STATUS      current
    DESCRIPTION
        "List of IP Addresses, Position of list is the internal NODE-ID in the ring" 
    ::=  { dcnTopologyDataEntry 2 }

dcnTopologyConfigTable OBJECT-TYPE
    SYNTAX      SEQUENCE OF DcnTopologyConfigEntry
    MAX-ACCESS  not-accessible
    STATUS      current
    DESCRIPTION   ""
    ::=  { equipmentConfigAndStatus 14 }

dcnTopologyConfigEntry OBJECT-TYPE
    SYNTAX      DcnTopologyConfigEntry
    MAX-ACCESS  not-accessible
    STATUS      current
    DESCRIPTION   ""
    INDEX       {
                  entityIndex
                }
    ::=  { dcnTopologyConfigTable 1 }

DcnTopologyConfigEntry ::=  SEQUENCE
  { dcnTopologyConfigActivateDetect FspR7YesNo }

dcnTopologyConfigActivateDetect OBJECT-TYPE
    SYNTAX      FspR7YesNo
    MAX-ACCESS  read-write
    STATUS      current
    DESCRIPTION
        "Initialize Topology Detection" 
    ::=  { dcnTopologyConfigEntry 1 }

dcnTopologyStatusTable OBJECT-TYPE
    SYNTAX      SEQUENCE OF DcnTopologyStatusEntry
    MAX-ACCESS  not-accessible
    STATUS      current
    DESCRIPTION   ""
    ::=  { equipmentConfigAndStatus 15 }

dcnTopologyStatusEntry OBJECT-TYPE
    SYNTAX      DcnTopologyStatusEntry
    MAX-ACCESS  not-accessible
    STATUS      current
    DESCRIPTION   ""
    INDEX       {
                  entityIndex
                }
    ::=  { dcnTopologyStatusTable 1 }

DcnTopologyStatusEntry ::=  SEQUENCE
  { dcnTopologyStatusTopologyType FspR7TopologyType }

dcnTopologyStatusTopologyType OBJECT-TYPE
    SYNTAX      FspR7TopologyType
    MAX-ACCESS  read-only
    STATUS      current
    DESCRIPTION
        "Monitored Topology Type" 
    ::=  { dcnTopologyStatusEntry 1 }

otdrConfigTable OBJECT-TYPE
    SYNTAX      SEQUENCE OF OtdrConfigEntry
    MAX-ACCESS  not-accessible
    STATUS      current
    DESCRIPTION   ""
    ::=  { equipmentConfigAndStatus 16 }

otdrConfigEntry OBJECT-TYPE
    SYNTAX      OtdrConfigEntry
    MAX-ACCESS  not-accessible
    STATUS      current
    DESCRIPTION   "Configuration of OTDR analysis."
    INDEX       {
                  entityIndex
                }
    ::=  { otdrConfigTable 1 }

OtdrConfigEntry ::=  SEQUENCE
  { otdrConfigTimePeriod FspR7OtdrPeriod }

otdrConfigTimePeriod OBJECT-TYPE
    SYNTAX      FspR7OtdrPeriod
    MAX-ACCESS  read-write
    STATUS      current
    DESCRIPTION
        "NONE - OTDR measurement disabled otherwise the OTDR duration in minutes." 
    ::=  { otdrConfigEntry 1 }

otdrDataTable OBJECT-TYPE
    SYNTAX      SEQUENCE OF OtdrDataEntry
    MAX-ACCESS  not-accessible
    STATUS      current
    DESCRIPTION   ""
    ::=  { equipmentConfigAndStatus 17 }

otdrDataEntry OBJECT-TYPE
    SYNTAX      OtdrDataEntry
    MAX-ACCESS  not-accessible
    STATUS      current
    DESCRIPTION   ""
    INDEX       {
                  entityIndex
                }
    ::=  { otdrDataTable 1 }

OtdrDataEntry ::=  SEQUENCE
  { otdrDataRemainingTime Unsigned32 }

otdrDataRemainingTime OBJECT-TYPE
    SYNTAX      Unsigned32 
    UNITS       "min"
    MAX-ACCESS  read-only
    STATUS      current
    DESCRIPTION
        "Time Remaining for Completion of OTDR Measurement. The timer is set by an Operation with parameter 'MEASURE'" 
    ::=  { otdrDataEntry 1 }

edfaConfigTable OBJECT-TYPE
    SYNTAX      SEQUENCE OF EdfaConfigEntry
    MAX-ACCESS  not-accessible
    STATUS      current
    DESCRIPTION   ""
    ::=  { equipmentConfigAndStatus 18 }

edfaConfigEntry OBJECT-TYPE
    SYNTAX      EdfaConfigEntry
    MAX-ACCESS  not-accessible
    STATUS      current
    DESCRIPTION   ""
    INDEX       {
                  entityIndex
                }
    ::=  { edfaConfigTable 1 }

EdfaConfigEntry ::=  SEQUENCE
  { edfaConfigTilt Integer32,
    edfaConfigGain FspR7Gain,
    edfaConfigVariableGain Unsigned32 }

edfaConfigTilt OBJECT-TYPE
    SYNTAX      Integer32 (-50..0 | -2147483648) 
    UNITS       "0.1 dB"
    MAX-ACCESS  read-write
    STATUS      current
    DESCRIPTION
        "Change of optical channel power in dB over the complete transmission band" 
    ::=  { edfaConfigEntry 1 }

edfaConfigGain OBJECT-TYPE
    SYNTAX      FspR7Gain
    MAX-ACCESS  read-write
    STATUS      current
    DESCRIPTION
        "Gain" 
    ::=  { edfaConfigEntry 2 }

edfaConfigVariableGain OBJECT-TYPE
    SYNTAX      Unsigned32 (0..350 | 4294967295) 
    UNITS       "0.1 dB"
    MAX-ACCESS  read-write
    STATUS      current
    DESCRIPTION
        "Variable Gain of EDFA" 
    ::=  { edfaConfigEntry 3 }

opticalAmplifierEquipmentDiagnosticsTable OBJECT-TYPE
    SYNTAX      SEQUENCE OF OpticalAmplifierEquipmentDiagnosticsEntry
    MAX-ACCESS  not-accessible
    STATUS      current
    DESCRIPTION   ""
    ::=  { equipmentConfigAndStatus 19 }

opticalAmplifierEquipmentDiagnosticsEntry OBJECT-TYPE
    SYNTAX      OpticalAmplifierEquipmentDiagnosticsEntry
    MAX-ACCESS  not-accessible
    STATUS      current
    DESCRIPTION   ""
    INDEX       {
                  entityIndex
                }
    ::=  { opticalAmplifierEquipmentDiagnosticsTable 1 }

OpticalAmplifierEquipmentDiagnosticsEntry ::=  SEQUENCE
  { opticalAmplifierEquipmentDiagnosticsSubTemp Integer32,
    opticalAmplifierEquipmentDiagnosticsUpperSubTempThres Integer32 }

opticalAmplifierEquipmentDiagnosticsSubTemp OBJECT-TYPE
    SYNTAX      Integer32 
    UNITS       "0.1 degree Celsius"
    MAX-ACCESS  read-only
    STATUS      current
    DESCRIPTION
        "Submodule Temperature" 
    ::=  { opticalAmplifierEquipmentDiagnosticsEntry 1 }

opticalAmplifierEquipmentDiagnosticsUpperSubTempThres OBJECT-TYPE
    SYNTAX      Integer32 
    UNITS       "0.1 degree Celsius"
    MAX-ACCESS  read-only
    STATUS      current
    DESCRIPTION
        "Submodule High Temperature Threshold" 
    ::=  { opticalAmplifierEquipmentDiagnosticsEntry 2 }

shelfConfigTable OBJECT-TYPE
    SYNTAX      SEQUENCE OF ShelfConfigEntry
    MAX-ACCESS  not-accessible
    STATUS      current
    DESCRIPTION   ""
    ::=  { equipmentConfigAndStatus 20 }

shelfConfigEntry OBJECT-TYPE
    SYNTAX      ShelfConfigEntry
    MAX-ACCESS  not-accessible
    STATUS      current
    DESCRIPTION   ""
    INDEX       {
                  entityIndex
                }
    ::=  { shelfConfigTable 1 }

ShelfConfigEntry ::=  SEQUENCE
  { shelfConfigRack SnmpAdminString,
    shelfConfigRackNumber Unsigned32,
    shelfConfigRackOrder Unsigned32 }

shelfConfigRack OBJECT-TYPE
    SYNTAX      SnmpAdminString
    MAX-ACCESS  read-write
    STATUS      current
    DESCRIPTION
        "Rack Containing Shelf" 
    ::=  { shelfConfigEntry 1 }

shelfConfigRackNumber OBJECT-TYPE
    SYNTAX      Unsigned32 (0..16 | 4294967295)
    MAX-ACCESS  read-write
    STATUS      current
    DESCRIPTION
        "Number of the Rack" 
    ::=  { shelfConfigEntry 2 }

shelfConfigRackOrder OBJECT-TYPE
    SYNTAX      Unsigned32 (0..45 | 4294967295) 
    UNITS       "HU"
    MAX-ACCESS  read-write
    STATUS      current
    DESCRIPTION
        "Defines the position of the shelf in a rack, starting from the top or bottom for the rack depending on Shelf Order (COUNT__ORDER). Shelf Position is used with Shelf Order for the graphical rack view." 
    ::=  { shelfConfigEntry 3 }

dcnTopologyConfigCapTable OBJECT-TYPE
    SYNTAX      SEQUENCE OF DcnTopologyConfigCapEntry
    MAX-ACCESS  not-accessible
    STATUS      current
    DESCRIPTION   ""
    ::=  { equipmentConfigAndStatus 21 }

dcnTopologyConfigCapEntry OBJECT-TYPE
    SYNTAX      DcnTopologyConfigCapEntry
    MAX-ACCESS  not-accessible
    STATUS      current
    DESCRIPTION   ""
    INDEX       {
                  entityIndex
                }
    ::=  { dcnTopologyConfigCapTable 1 }

DcnTopologyConfigCapEntry ::=  SEQUENCE
  { dcnTopologyConfigCapActivateDetect FspR7YesNoCaps }

dcnTopologyConfigCapActivateDetect OBJECT-TYPE
    SYNTAX      FspR7YesNoCaps
    MAX-ACCESS  read-only
    STATUS      current
    DESCRIPTION   "This object contains capabilities for dcnTopologyConfigActivateDetect object."
    ::=  { dcnTopologyConfigCapEntry 1 }

lanIpDataTable OBJECT-TYPE
    SYNTAX      SEQUENCE OF LanIpDataEntry
    MAX-ACCESS  not-accessible
    STATUS      current
    DESCRIPTION   "List of Entitiey AID's of OSC's belonging to this LAN"
    ::=  { equipmentConfigAndStatus 22 }

lanIpDataEntry OBJECT-TYPE
    SYNTAX      LanIpDataEntry
    MAX-ACCESS  not-accessible
    STATUS      current
    DESCRIPTION   ""
    INDEX       {
                  entityIndex
                }
    ::=  { lanIpDataTable 1 }

LanIpDataEntry ::=  SEQUENCE
  { lanIpDataOscmMembers SnmpAdminString }

lanIpDataOscmMembers OBJECT-TYPE
    SYNTAX      SnmpAdminString
    MAX-ACCESS  read-only
    STATUS      current
    DESCRIPTION
        "List of Entity AID's (modules, ports) belonging to this LAN" 
    ::=  { lanIpDataEntry 1 }

eRoadmConfigTable OBJECT-TYPE
    SYNTAX      SEQUENCE OF ERoadmConfigEntry
    MAX-ACCESS  not-accessible
    STATUS      current
    DESCRIPTION   ""
    ::=  { equipmentConfigAndStatus 23 }

eRoadmConfigEntry OBJECT-TYPE
    SYNTAX      ERoadmConfigEntry
    MAX-ACCESS  not-accessible
    STATUS      current
    DESCRIPTION   ""
    INDEX       {
                  entityIndex
                }
    ::=  { eRoadmConfigTable 1 }

ERoadmConfigEntry ::=  SEQUENCE
  { eRoadmConfigOpticalSetPoint Integer32,
    eRoadmConfigOffset Integer32,
    eRoadmConfigTilt Integer32,
    eRoadmConfigInitiateEqualization FspR7InitEqualization }

eRoadmConfigOpticalSetPoint OBJECT-TYPE
    SYNTAX      Integer32 (-250..100 | -2147483648) 
    UNITS       "0.1 dBm"
    MAX-ACCESS  read-write
    STATUS      current
    DESCRIPTION
        "Sets the optical power for power equalization in ROADM or for channel power control in OPCM" 
    ::=  { eRoadmConfigEntry 1 }

eRoadmConfigOffset OBJECT-TYPE
    SYNTAX      Integer32 (10..30 | -2147483648) 
    UNITS       "0.1 dB"
    MAX-ACCESS  read-write
    STATUS      current
    DESCRIPTION
        "Sets the offset for the mean optical power for power equalization in ROADM" 
    ::=  { eRoadmConfigEntry 2 }

eRoadmConfigTilt OBJECT-TYPE
    SYNTAX      Integer32 (-50..0 | -2147483648) 
    UNITS       "0.1 dB"
    MAX-ACCESS  read-write
    STATUS      current
    DESCRIPTION
        "Change of optical channel power in dB over the complete transmission band" 
    ::=  { eRoadmConfigEntry 3 }

eRoadmConfigInitiateEqualization OBJECT-TYPE
    SYNTAX      FspR7InitEqualization
    MAX-ACCESS  read-write
    STATUS      current
    DESCRIPTION
        "Initiate Equalization" 
    ::=  { eRoadmConfigEntry 4 }

eRoadmDataTable OBJECT-TYPE
    SYNTAX      SEQUENCE OF ERoadmDataEntry
    MAX-ACCESS  not-accessible
    STATUS      current
    DESCRIPTION   ""
    ::=  { equipmentConfigAndStatus 24 }

eRoadmDataEntry OBJECT-TYPE
    SYNTAX      ERoadmDataEntry
    MAX-ACCESS  not-accessible
    STATUS      current
    DESCRIPTION   ""
    INDEX       {
                  entityIndex
                }
    ::=  { eRoadmDataTable 1 }

ERoadmDataEntry ::=  SEQUENCE
  { eRoadmDataSumTransmited Unsigned32,
    eRoadmDataSumReceived Unsigned32,
    eRoadmDataConnectionState FspR7ConnectState }

eRoadmDataSumTransmited OBJECT-TYPE
    SYNTAX      Unsigned32 (0..96 | 4294967295)
    MAX-ACCESS  read-only
    STATUS      current
    DESCRIPTION
        "Sum of Transmitted Optical Channels Provisioned" 
    ::=  { eRoadmDataEntry 1 }

eRoadmDataSumReceived OBJECT-TYPE
    SYNTAX      Unsigned32 (0..80 | 4294967295)
    MAX-ACCESS  read-only
    STATUS      current
    DESCRIPTION
        "Sum of Received Optical Channels Provisioned" 
    ::=  { eRoadmDataEntry 2 }

eRoadmDataConnectionState OBJECT-TYPE
    SYNTAX      FspR7ConnectState
    MAX-ACCESS  read-only
    STATUS      current
    DESCRIPTION
        "Connection State" 
    ::=  { eRoadmDataEntry 3 }

eRoadmInfoTable OBJECT-TYPE
    SYNTAX      SEQUENCE OF ERoadmInfoEntry
    MAX-ACCESS  not-accessible
    STATUS      current
    DESCRIPTION   "This table contains information for EROADM"
    ::=  { equipmentConfigAndStatus 25 }

eRoadmInfoEntry OBJECT-TYPE
    SYNTAX      ERoadmInfoEntry
    MAX-ACCESS  not-accessible
    STATUS      current
    DESCRIPTION   ""
    INDEX       {
                  entityIndex
                }
    ::=  { eRoadmInfoTable 1 }

ERoadmInfoEntry ::=  SEQUENCE
  { eRoadmInfoNetworkPorts Unsigned32,
    eRoadmInfoClientPorts Unsigned32,
    eRoadmInfoInternalPorts Unsigned32,
    eRoadmInfoInternalPlugs FspR7EquipmentTypeCaps,
    eRoadmInfoInternalPlugRates FspR7PlugDataRateCaps,
    eRoadmInfoChannel FspR7ChannelIdentifierCaps,
    eRoadmInfoShelfHeight Unsigned32,
    eRoadmInfoUpgradePorts Unsigned32,
    eRoadmInfoMaxPowerConsumption Unsigned32,
    eRoadmInfoScuRing FspR7ScuRing,
    eRoadmInfoChannelSpacing FspR7ChannelSpacing }

eRoadmInfoNetworkPorts OBJECT-TYPE
    SYNTAX      Unsigned32
    MAX-ACCESS  read-only
    STATUS      current
    DESCRIPTION
        "Number of Network Ports" 
    ::=  { eRoadmInfoEntry 1 }

eRoadmInfoClientPorts OBJECT-TYPE
    SYNTAX      Unsigned32 (0..128 | 4294967295)
    MAX-ACCESS  read-only
    STATUS      current
    DESCRIPTION
        "Number of Client Ports" 
    ::=  { eRoadmInfoEntry 2 }

eRoadmInfoInternalPorts OBJECT-TYPE
    SYNTAX      Unsigned32
    MAX-ACCESS  read-only
    STATUS      current
    DESCRIPTION
        "Number of Internal Ports" 
    ::=  { eRoadmInfoEntry 3 }

eRoadmInfoInternalPlugs OBJECT-TYPE
    SYNTAX      FspR7EquipmentTypeCaps
    MAX-ACCESS  read-only
    STATUS      current
    DESCRIPTION
        "Internal Plugs Required" 
    ::=  { eRoadmInfoEntry 4 }

eRoadmInfoInternalPlugRates OBJECT-TYPE
    SYNTAX      FspR7PlugDataRateCaps
    MAX-ACCESS  read-only
    STATUS      current
    DESCRIPTION
        "List of Provisionable Internal Plug Rates Supported" 
    ::=  { eRoadmInfoEntry 5 }

eRoadmInfoChannel OBJECT-TYPE
    SYNTAX      FspR7ChannelIdentifierCaps
    MAX-ACCESS  read-only
    STATUS      current
    DESCRIPTION
        "Possible internal channel" 
    ::=  { eRoadmInfoEntry 6 }

eRoadmInfoShelfHeight OBJECT-TYPE
    SYNTAX      Unsigned32 
    UNITS       "HU"
    MAX-ACCESS  read-only
    STATUS      current
    DESCRIPTION
        "Height of Shelf in HU" 
    ::=  { eRoadmInfoEntry 7 }

eRoadmInfoUpgradePorts OBJECT-TYPE
    SYNTAX      Unsigned32
    MAX-ACCESS  read-only
    STATUS      current
    DESCRIPTION
        "Number of Upgrade Ports" 
    ::=  { eRoadmInfoEntry 8 }

eRoadmInfoMaxPowerConsumption OBJECT-TYPE
    SYNTAX      Unsigned32 
    UNITS       "0.1 W"
    MAX-ACCESS  read-only
    STATUS      current
    DESCRIPTION
        "Maximum Power Consumption of the device" 
    ::=  { eRoadmInfoEntry 9 }

eRoadmInfoScuRing OBJECT-TYPE
    SYNTAX      FspR7ScuRing
    MAX-ACCESS  read-only
    STATUS      current
    DESCRIPTION
        "SCU Interconnection" 
    ::=  { eRoadmInfoEntry 10 }

eRoadmInfoChannelSpacing OBJECT-TYPE
    SYNTAX      FspR7ChannelSpacing
    MAX-ACCESS  read-only
    STATUS      current
    DESCRIPTION
        "ITU Grid channel spacing" 
    ::=  { eRoadmInfoEntry 11 }

shelfInfoTable OBJECT-TYPE
    SYNTAX      SEQUENCE OF ShelfInfoEntry
    MAX-ACCESS  not-accessible
    STATUS      current
    DESCRIPTION   "This table contains information for SHELF"
    ::=  { equipmentConfigAndStatus 26 }

shelfInfoEntry OBJECT-TYPE
    SYNTAX      ShelfInfoEntry
    MAX-ACCESS  not-accessible
    STATUS      current
    DESCRIPTION   ""
    INDEX       {
                  entityIndex
                }
    ::=  { shelfInfoTable 1 }

ShelfInfoEntry ::=  SEQUENCE
  { shelfInfoStandardSlots Unsigned32,
    shelfInfoShelfHeight Unsigned32,
    shelfInfoStandardSlotHeight Unsigned32,
    shelfInfoNetworkPorts Unsigned32,
    shelfInfoClientPorts Unsigned32,
    shelfInfoInternalPorts Unsigned32,
    shelfInfoUpgradePorts Unsigned32,
    shelfInfoOscPorts Unsigned32,
    shelfInfoOscChannel FspR7OscChannel,
    shelfInfoOmBand FspR7OpticalBand,
    shelfInfoShelfId Unsigned32,
    shelfInfoChannelBandwidth FspR7ChannelBandwidth }

shelfInfoStandardSlots OBJECT-TYPE
    SYNTAX      Unsigned32 (2..20 | 4294967295)
    MAX-ACCESS  read-only
    STATUS      current
    DESCRIPTION
        "Number of Provisionable Standard Slots" 
    ::=  { shelfInfoEntry 1 }

shelfInfoShelfHeight OBJECT-TYPE
    SYNTAX      Unsigned32 
    UNITS       "HU"
    MAX-ACCESS  read-only
    STATUS      current
    DESCRIPTION
        "Height of Shelf in HU" 
    ::=  { shelfInfoEntry 2 }

shelfInfoStandardSlotHeight OBJECT-TYPE
    SYNTAX      Unsigned32 
    UNITS       "0.1 HU"
    MAX-ACCESS  read-only
    STATUS      current
    DESCRIPTION
        "Height of Standard Slots in Shelf in HU" 
    ::=  { shelfInfoEntry 3 }

shelfInfoNetworkPorts OBJECT-TYPE
    SYNTAX      Unsigned32
    MAX-ACCESS  read-only
    STATUS      current
    DESCRIPTION
        "Number of Network Ports" 
    ::=  { shelfInfoEntry 4 }

shelfInfoClientPorts OBJECT-TYPE
    SYNTAX      Unsigned32 (0..128 | 4294967295)
    MAX-ACCESS  read-only
    STATUS      current
    DESCRIPTION
        "Number of Client Ports" 
    ::=  { shelfInfoEntry 5 }

shelfInfoInternalPorts OBJECT-TYPE
    SYNTAX      Unsigned32
    MAX-ACCESS  read-only
    STATUS      current
    DESCRIPTION
        "Number of Internal Ports" 
    ::=  { shelfInfoEntry 6 }

shelfInfoUpgradePorts OBJECT-TYPE
    SYNTAX      Unsigned32
    MAX-ACCESS  read-only
    STATUS      current
    DESCRIPTION
        "Number of Upgrade Ports" 
    ::=  { shelfInfoEntry 7 }

shelfInfoOscPorts OBJECT-TYPE
    SYNTAX      Unsigned32 (0..10 | 4294967295)
    MAX-ACCESS  read-only
    STATUS      current
    DESCRIPTION
        "Number of OSC Ports" 
    ::=  { shelfInfoEntry 8 }

shelfInfoOscChannel OBJECT-TYPE
    SYNTAX      FspR7OscChannel
    MAX-ACCESS  read-only
    STATUS      current
    DESCRIPTION
        "OSC Channel" 
    ::=  { shelfInfoEntry 9 }

shelfInfoOmBand OBJECT-TYPE
    SYNTAX      FspR7OpticalBand
    MAX-ACCESS  read-only
    STATUS      current
    DESCRIPTION
        "Band Provision. Reference to BAND__INVENTORY." 
    ::=  { shelfInfoEntry 10 }

shelfInfoShelfId OBJECT-TYPE
    SYNTAX      Unsigned32
    MAX-ACCESS  read-only
    STATUS      current
    DESCRIPTION
        "Shelf ID" 
    ::=  { shelfInfoEntry 11 }

shelfInfoChannelBandwidth OBJECT-TYPE
    SYNTAX      FspR7ChannelBandwidth
    MAX-ACCESS  read-write
    STATUS      current
    DESCRIPTION
        "Channel Bandwidth" 
    ::=  { shelfInfoEntry 12 }

eRoadmConfigCapTable OBJECT-TYPE
    SYNTAX      SEQUENCE OF ERoadmConfigCapEntry
    MAX-ACCESS  not-accessible
    STATUS      current
    DESCRIPTION   ""
    ::=  { equipmentConfigAndStatus 27 }

eRoadmConfigCapEntry OBJECT-TYPE
    SYNTAX      ERoadmConfigCapEntry
    MAX-ACCESS  not-accessible
    STATUS      current
    DESCRIPTION   ""
    INDEX       {
                  entityIndex
                }
    ::=  { eRoadmConfigCapTable 1 }

ERoadmConfigCapEntry ::=  SEQUENCE
  { eRoadmConfigCapOpticalSetPoint FspR7Integer32Caps,
    eRoadmConfigCapOffset FspR7Integer32Caps,
    eRoadmConfigCapTilt FspR7Integer32Caps,
    eRoadmConfigCapInitiateEqualization FspR7InitEqualizationCaps }

eRoadmConfigCapOpticalSetPoint OBJECT-TYPE
    SYNTAX      FspR7Integer32Caps
    UNITS       "0.1 dBm"
    MAX-ACCESS  read-only
    STATUS      current
    DESCRIPTION
        "Sets the optical power for power equalization in ROADM or for channel power control in OPCM" 
    ::=  { eRoadmConfigCapEntry 1 }

eRoadmConfigCapOffset OBJECT-TYPE
    SYNTAX      FspR7Integer32Caps
    UNITS       "0.1 dB"
    MAX-ACCESS  read-only
    STATUS      current
    DESCRIPTION
        "Sets the offset for the mean optical power for power equalization in ROADM" 
    ::=  { eRoadmConfigCapEntry 2 }

eRoadmConfigCapTilt OBJECT-TYPE
    SYNTAX      FspR7Integer32Caps
    UNITS       "0.1 dB"
    MAX-ACCESS  read-only
    STATUS      current
    DESCRIPTION
        "Change of optical channel power in dB over the complete transmission band" 
    ::=  { eRoadmConfigCapEntry 3 }

eRoadmConfigCapInitiateEqualization OBJECT-TYPE
    SYNTAX      FspR7InitEqualizationCaps
    MAX-ACCESS  read-only
    STATUS      current
    DESCRIPTION
        "Initiate Equalization" 
    ::=  { eRoadmConfigCapEntry 4 }

capabilityDataTable OBJECT-TYPE
    SYNTAX      SEQUENCE OF CapabilityDataEntry
    MAX-ACCESS  not-accessible
    STATUS      current
    DESCRIPTION   ""
    ::=  { equipmentConfigAndStatus 28 }

capabilityDataEntry OBJECT-TYPE
    SYNTAX      CapabilityDataEntry
    MAX-ACCESS  not-accessible
    STATUS      current
    DESCRIPTION   "Each entry in this table represents a description for type equipment and capability level."
    INDEX       {
                  capabilityDataType,
                  capabilityDataCapabilityLevel
                }
    ::=  { capabilityDataTable 1 }

CapabilityDataEntry ::=  SEQUENCE
  { capabilityDataType FspR7EquipmentType,
    capabilityDataCapabilityLevel FspR7CapInventory,
    capabilityDataDescription SnmpAdminString }

capabilityDataType OBJECT-TYPE
    SYNTAX      FspR7EquipmentType
    MAX-ACCESS  not-accessible
    STATUS      current
    DESCRIPTION
        "The TYPE of Equipment and the MODE setting determine uniquely the number and allowed TYPE's of the provisionable dependent entities (plugs, interfaces, modules)" 
    ::=  { capabilityDataEntry 1 }

capabilityDataCapabilityLevel OBJECT-TYPE
    SYNTAX      FspR7CapInventory
    MAX-ACCESS  not-accessible
    STATUS      current
    DESCRIPTION   ""
    ::=  { capabilityDataEntry 2 }

capabilityDataDescription OBJECT-TYPE
    SYNTAX      SnmpAdminString
    MAX-ACCESS  read-only
    STATUS      current
    DESCRIPTION   ""
    ::=  { capabilityDataEntry 3 }

farEndPlugDiagnosticsTable OBJECT-TYPE
    SYNTAX      SEQUENCE OF FarEndPlugDiagnosticsEntry
    MAX-ACCESS  not-accessible
    STATUS      current
    DESCRIPTION   ""
    ::=  { equipmentConfigAndStatus 29 }

farEndPlugDiagnosticsEntry OBJECT-TYPE
    SYNTAX      FarEndPlugDiagnosticsEntry
    MAX-ACCESS  not-accessible
    STATUS      current
    DESCRIPTION   ""
    INDEX       {
                  entityIndex
                }
    ::=  { farEndPlugDiagnosticsTable 1 }

FarEndPlugDiagnosticsEntry ::=  SEQUENCE
  { farEndPlugDiagnosticsTemp Integer32,
    farEndPlugDiagnosticsUpperTempThres Integer32,
    farEndPlugDiagnosticsLowerTempThres Integer32 }

farEndPlugDiagnosticsTemp OBJECT-TYPE
    SYNTAX      Integer32 
    UNITS       "0.1 degree Celsius"
    MAX-ACCESS  read-only
    STATUS      current
    DESCRIPTION   "Actual temperature on the far end plug."
    ::=  { farEndPlugDiagnosticsEntry 1 }

farEndPlugDiagnosticsUpperTempThres OBJECT-TYPE
    SYNTAX      Integer32 
    UNITS       "0.1 degree Celsius"
    MAX-ACCESS  read-only
    STATUS      current
    DESCRIPTION   "Upper temperature threshold for threshold crossing alarm.
         Temperatures above this value will cause a Notification."
    ::=  { farEndPlugDiagnosticsEntry 2 }

farEndPlugDiagnosticsLowerTempThres OBJECT-TYPE
    SYNTAX      Integer32 
    UNITS       "0.1 degree Celsius"
    MAX-ACCESS  read-only
    STATUS      current
    DESCRIPTION   "Lower temperature threshold for threshold crossing alarm.
         Temperatures below this value will cause a Notification."
    ::=  { farEndPlugDiagnosticsEntry 3 }

farEndPlugConfigTable OBJECT-TYPE
    SYNTAX      SEQUENCE OF FarEndPlugConfigEntry
    MAX-ACCESS  not-accessible
    STATUS      current
    DESCRIPTION   ""
    ::=  { equipmentConfigAndStatus 30 }

farEndPlugConfigEntry OBJECT-TYPE
    SYNTAX      FarEndPlugConfigEntry
    MAX-ACCESS  not-accessible
    STATUS      current
    DESCRIPTION   ""
    INDEX       {
                  entityIndex
                }
    ::=  { farEndPlugConfigTable 1 }

FarEndPlugConfigEntry ::=  SEQUENCE
  { farEndPlugConfigAlias SnmpAdminString,
    farEndPlugConfigMaxDataRate FspR7PlugDataRate }

farEndPlugConfigAlias OBJECT-TYPE
    SYNTAX      SnmpAdminString
    MAX-ACCESS  read-write
    STATUS      current
    DESCRIPTION   "A string, configurable by the operator, containing a
         symbolic name for the trail which is terminated at this interface."
    ::=  { farEndPlugConfigEntry 1 }

farEndPlugConfigMaxDataRate OBJECT-TYPE
    SYNTAX      FspR7PlugDataRate
    MAX-ACCESS  read-write
    STATUS      current
    DESCRIPTION
        "Rate" 
    ::=  { farEndPlugConfigEntry 2 }

farEndPlugConfigCapTable OBJECT-TYPE
    SYNTAX      SEQUENCE OF FarEndPlugConfigCapEntry
    MAX-ACCESS  not-accessible
    STATUS      current
    DESCRIPTION   ""
    ::=  { equipmentConfigAndStatus 31 }

farEndPlugConfigCapEntry OBJECT-TYPE
    SYNTAX      FarEndPlugConfigCapEntry
    MAX-ACCESS  not-accessible
    STATUS      current
    DESCRIPTION   ""
    INDEX       {
                  entityIndex
                }
    ::=  { farEndPlugConfigCapTable 1 }

FarEndPlugConfigCapEntry ::=  SEQUENCE
  { farEndPlugConfigCapMaxDataRate FspR7PlugDataRateCaps }

farEndPlugConfigCapMaxDataRate OBJECT-TYPE
    SYNTAX      FspR7PlugDataRateCaps
    MAX-ACCESS  read-only
    STATUS      current
    DESCRIPTION
        "Rate" 
    ::=  { farEndPlugConfigCapEntry 1 }

farEndPlugDataTable OBJECT-TYPE
    SYNTAX      SEQUENCE OF FarEndPlugDataEntry
    MAX-ACCESS  not-accessible
    STATUS      current
    DESCRIPTION   ""
    ::=  { equipmentConfigAndStatus 32 }

farEndPlugDataEntry OBJECT-TYPE
    SYNTAX      FarEndPlugDataEntry
    MAX-ACCESS  not-accessible
    STATUS      current
    DESCRIPTION   ""
    INDEX       {
                  entityIndex
                }
    ::=  { farEndPlugDataTable 1 }

FarEndPlugDataEntry ::=  SEQUENCE
  { farEndPlugDataType FspR7EquipmentType,
    farEndPlugDataMaxDataRate FspR7PlugDataRate,
    farEndPlugDataTransmitChannel FspR7ChannelIdentifier,
    farEndPlugDataReach FspR7OpticalInterfaceReach,
    farEndPlugDataFiberType FspR7OpticalFiberType,
    farEndPlugDataConnectorType FspR7ConnectorType,
    farEndPlugDataAdmin FspR7AdminState }

farEndPlugDataType OBJECT-TYPE
    SYNTAX      FspR7EquipmentType
    MAX-ACCESS  read-only
    STATUS      current
    DESCRIPTION
        "The TYPE of Equipment and the MODE setting determine uniquely the number and allowed TYPE's of the provisionable dependent entities (plugs, interfaces, modules)" 
    ::=  { farEndPlugDataEntry 1 }

farEndPlugDataMaxDataRate OBJECT-TYPE
    SYNTAX      FspR7PlugDataRate
    MAX-ACCESS  read-only
    STATUS      current
    DESCRIPTION
        "Rate" 
    ::=  { farEndPlugDataEntry 2 }

farEndPlugDataTransmitChannel OBJECT-TYPE
    SYNTAX      FspR7ChannelIdentifier
    MAX-ACCESS  read-only
    STATUS      current
    DESCRIPTION
        "Channel" 
    ::=  { farEndPlugDataEntry 3 }

farEndPlugDataReach OBJECT-TYPE
    SYNTAX      FspR7OpticalInterfaceReach
    MAX-ACCESS  read-only
    STATUS      current
    DESCRIPTION
        "Reach" 
    ::=  { farEndPlugDataEntry 4 }

farEndPlugDataFiberType OBJECT-TYPE
    SYNTAX      FspR7OpticalFiberType
    MAX-ACCESS  read-only
    STATUS      current
    DESCRIPTION
        "Fiber of Optical Interface - Provision, Reference to FIBER__INVENTORY" 
    ::=  { farEndPlugDataEntry 5 }

farEndPlugDataConnectorType OBJECT-TYPE
    SYNTAX      FspR7ConnectorType
    MAX-ACCESS  read-only
    STATUS      current
    DESCRIPTION
        "Connector Type" 
    ::=  { farEndPlugDataEntry 6 }

farEndPlugDataAdmin OBJECT-TYPE
    SYNTAX      FspR7AdminState
    MAX-ACCESS  read-only
    STATUS      current
    DESCRIPTION
        "Administrative State is displayed in the GUI and Craft. Transition to Unassigend requires the entity to be deleted." 
    ::=  { farEndPlugDataEntry 7 }

moduleConfigCapTable OBJECT-TYPE
    SYNTAX      SEQUENCE OF ModuleConfigCapEntry
    MAX-ACCESS  not-accessible
    STATUS      current
    DESCRIPTION   "The ModuleConfigCap table. This table shows the capabilities for parameters from moduleConfigTable."
    ::=  { equipmentConfigAndStatus 35 }

moduleConfigCapEntry OBJECT-TYPE
    SYNTAX      ModuleConfigCapEntry
    MAX-ACCESS  not-accessible
    STATUS      current
    DESCRIPTION   ""
    INDEX       {
                  entityIndex
                }
    ::=  { moduleConfigCapTable 1 }

ModuleConfigCapEntry ::=  SEQUENCE
  { moduleConfigCapEqlzAdmin FspR7EqlzAdminStateCaps,
    moduleConfigCapInitiateEqualization FspR7InitEqualizationCaps,
    moduleConfigCapCac FspR7L2CacEnableCaps,
    moduleConfigCapFiberDetect FspR7FiberDetectCaps }

moduleConfigCapEqlzAdmin OBJECT-TYPE
    SYNTAX      FspR7EqlzAdminStateCaps
    MAX-ACCESS  read-only
    STATUS      current
    DESCRIPTION
        "Scheduled Equalization Administration" 
    ::=  { moduleConfigCapEntry 1 }

moduleConfigCapInitiateEqualization OBJECT-TYPE
    SYNTAX      FspR7InitEqualizationCaps
    MAX-ACCESS  read-only
    STATUS      current
    DESCRIPTION
        "Initiate Equalization" 
    ::=  { moduleConfigCapEntry 2 }

moduleConfigCapCac OBJECT-TYPE
    SYNTAX      FspR7L2CacEnableCaps
    MAX-ACCESS  read-only
    STATUS      current
    DESCRIPTION
        "Enable of CAC" 
    ::=  { moduleConfigCapEntry 3 }

moduleConfigCapFiberDetect OBJECT-TYPE
    SYNTAX      FspR7FiberDetectCaps
    MAX-ACCESS  read-only
    STATUS      current
    DESCRIPTION
        "Fiber Detect" 
    ::=  { moduleConfigCapEntry 4 }

interfaceConfigTable OBJECT-TYPE
    SYNTAX      SEQUENCE OF InterfaceConfigEntry
    MAX-ACCESS  not-accessible
    STATUS      current
    DESCRIPTION   "Contains entries for the configuration of interfaces.
         This table extends the entries in the ifTable (RFC 2863)."
    ::=  { interfaceConfigAndStatus 1 }

interfaceConfigEntry OBJECT-TYPE
    SYNTAX      InterfaceConfigEntry
    MAX-ACCESS  not-accessible
    STATUS      current
    DESCRIPTION   "The gpiTTP and ocTTP interfaces will have an entry in this
         table."
    INDEX       {
                  entityIndex
                }
    ::=  { interfaceConfigTable 1 }

InterfaceConfigEntry ::=  SEQUENCE
  { interfaceConfigIdentifier SnmpAdminString,
    interfaceConfigLoopConfig LoopConfig,
    interfaceConfigDataLayerPmReset FspR7PmReset,
    interfaceConfigEqlzAdmin FspR7EqlzAdminState,
    interfaceConfigDispertionConfig FspR7DispersionConfig,
    interfaceConfigTurnupConfig FspR7TurnupConfig,
    interfaceConfigInitiateEqualization FspR7InitEqualization,
    interfaceConfigExternalVid Unsigned32,
    interfaceConfigLanAid EntityIndex,
    interfaceConfigBehaviour FspR7PortBehaviour,
    interfaceConfigInitiateRamanEqualization FspR7InitEqualization,
    interfaceConfigSigDegPcslThreshold Unsigned32 }

interfaceConfigIdentifier OBJECT-TYPE
    SYNTAX      SnmpAdminString
    MAX-ACCESS  read-write
    STATUS      current
    DESCRIPTION   "A string, configurable by the operator, containing a
         symbolic name for the trail which is terminated at this interface."
    ::=  { interfaceConfigEntry 1 }

interfaceConfigLoopConfig OBJECT-TYPE
    SYNTAX      LoopConfig
    MAX-ACCESS  read-write
    STATUS      current
    DESCRIPTION   "The configuration of the loopback function.
         - noLoop: no loop configuration on the interface.
         - lineLoop: the incoming signal is looped to the outgoing
         line on the interface. The incoming signal is sent in the
         downstream direction and processed as normal.
         - inwardLoop: the output signal is looped to the incoming line
         on the interface. The looped signal is transmitted unchanged on
         the optical output."
    ::=  { interfaceConfigEntry 2 }

interfaceConfigDataLayerPmReset OBJECT-TYPE
    SYNTAX      FspR7PmReset
    MAX-ACCESS  read-write
    STATUS      current
    DESCRIPTION
        "Reset data-layer Performance registers" 
    ::=  { interfaceConfigEntry 3 }

interfaceConfigEqlzAdmin OBJECT-TYPE
    SYNTAX      FspR7EqlzAdminState
    MAX-ACCESS  read-write
    STATUS      current
    DESCRIPTION   "Scheduled Equalization Administration"
    ::=  { interfaceConfigEntry 4 }

interfaceConfigDispertionConfig OBJECT-TYPE
    SYNTAX      FspR7DispersionConfig
    MAX-ACCESS  read-write
    STATUS      current
    DESCRIPTION   "Facility Operation Tunable Dispersion Config."
    ::=  { interfaceConfigEntry 5 }

interfaceConfigTurnupConfig OBJECT-TYPE
    SYNTAX      FspR7TurnupConfig
    MAX-ACCESS  read-write
    STATUS      current
    DESCRIPTION   "Facility Operation Turnup Config."
    ::=  { interfaceConfigEntry 6 }

interfaceConfigInitiateEqualization OBJECT-TYPE
    SYNTAX      FspR7InitEqualization
    MAX-ACCESS  read-write
    STATUS      current
    DESCRIPTION   ""
    ::=  { interfaceConfigEntry 7 }

interfaceConfigExternalVid OBJECT-TYPE
    SYNTAX      Unsigned32 (1..4095 | 4294967295)
    MAX-ACCESS  read-write
    STATUS      current
    DESCRIPTION
        "External VID" 
    ::=  { interfaceConfigEntry 8 }

interfaceConfigLanAid OBJECT-TYPE
    SYNTAX      EntityIndex
    MAX-ACCESS  read-write
    STATUS      current
    DESCRIPTION
        "AID of LAN" 
    ::=  { interfaceConfigEntry 9 }

interfaceConfigBehaviour OBJECT-TYPE
    SYNTAX      FspR7PortBehaviour
    MAX-ACCESS  read-write
    STATUS      current
    DESCRIPTION
        "Behavior or Port usage based on configuration/usage in the system regardless of faceplate designation" 
    ::=  { interfaceConfigEntry 10 }

interfaceConfigInitiateRamanEqualization OBJECT-TYPE
    SYNTAX      FspR7InitEqualization
    MAX-ACCESS  read-write
    STATUS      current
    DESCRIPTION   ""
    ::=  { interfaceConfigEntry 11 }

interfaceConfigSigDegPcslThreshold OBJECT-TYPE
    SYNTAX      Unsigned32 (1..100 | 4294967295) 
    UNITS       "%"
    MAX-ACCESS  read-write
    STATUS      current
    DESCRIPTION
        "Block-Error-Based Degradation Definition for Physical Coding Sublayer" 
    ::=  { interfaceConfigEntry 12 }

interfaceDataTable OBJECT-TYPE
    SYNTAX      SEQUENCE OF InterfaceDataEntry
    MAX-ACCESS  not-accessible
    STATUS      current
    DESCRIPTION   "Contains entries for the configuration of interfaces.
         This table extends the entries in the ifTable (RFC 2863)."
    ::=  { interfaceConfigAndStatus 2 }

interfaceDataEntry OBJECT-TYPE
    SYNTAX      InterfaceDataEntry
    MAX-ACCESS  not-accessible
    STATUS      current
    DESCRIPTION   "The gpiTTP and ocTTP interfaces will have an entry in this table."
    INDEX       {
                  entityIndex
                }
    ::=  { interfaceDataTable 1 }

InterfaceDataEntry ::=  SEQUENCE
  { interfaceDataConnector FspR7ConnectorType,
    interfaceDataSignalMapping FspR7SignalMapping,
    interfaceDataRate Unsigned32,
    interfaceDataBehaviour FspR7PortBehaviour,
    interfaceDataTermLevel OhTerminationLevel,
    interfaceDataConnectionType FspR7TypeConnection,
    interfaceDataMonLevel FspR7MonLevel,
    interfaceDataValidSignalTimer Unsigned32,
    interfaceDataPayload OtnPayloadType,
    interfaceDataParity FspR7ParityBit,
    interfaceDataPhysIfBaseType FspR7InterfaceType,
    interfaceDataLaserReleaseTimer Unsigned32,
    interfaceDataCir Unsigned32,
    interfaceDataTransmitWavelength Unsigned32,
    interfaceDataTransmitFrequency Unsigned32,
    interfaceDataTransmitChannel FspR7ChannelIdentifier,
    interfaceDataType FspR7EquipmentType,
    interfaceDataConnectionState FspR7ConnectState,
    interfaceDataFacilityType FspR7InterfaceType,
    interfaceDataProtectionRole FspR7ProtectionRole,
    interfaceDataReach FspR7OpticalInterfaceReach,
    interfaceDataFiberType FspR7OpticalFiberType,
    interfaceDataOdtuType FspR7OdtuType,
    interfaceDataOduTribPortNo SnmpAdminString,
    interfaceDataOduTribTimeSlottNo SnmpAdminString,
    interfaceDataRevertiveMode ApsRevertMode,
    interfaceDataSignalDirection FspR7SignalDirection,
    interfaceDataBidirectionalChannel FspR7BidirectionalChannel,
    interfaceDataTransmitterWavelength Unsigned32,
    interfaceDataReceiverWavelength Unsigned32,
    interfaceDataTransmitterFrequency Unsigned32,
    interfaceDataReceiverFrequency Unsigned32 }

interfaceDataConnector OBJECT-TYPE
    SYNTAX      FspR7ConnectorType
    MAX-ACCESS  read-only
    STATUS      current
    DESCRIPTION   "The textual description of the external connector type
         provided for an interface (eg. SC, LC, RJ45, etc)."
    ::=  { interfaceDataEntry 1 }

interfaceDataSignalMapping OBJECT-TYPE
    SYNTAX      FspR7SignalMapping
    MAX-ACCESS  read-only
    STATUS      deprecated
    DESCRIPTION   "The signal mapping of the interface."
    ::=  { interfaceDataEntry 2 }

interfaceDataRate OBJECT-TYPE
    SYNTAX      Unsigned32 
    UNITS       "Mbps"
    MAX-ACCESS  read-only
    STATUS      current
    DESCRIPTION   "The data rate configured for this interface."
    ::=  { interfaceDataEntry 3 }

interfaceDataBehaviour OBJECT-TYPE
    SYNTAX      FspR7PortBehaviour
    MAX-ACCESS  read-only
    STATUS      current
    DESCRIPTION   "The configured behaviour of the interface. If configured
         as a network interface, the interface will use a WDM laser, and
         configuration restrictions may apply."
    ::=  { interfaceDataEntry 4 }

interfaceDataTermLevel OBJECT-TYPE
    SYNTAX      OhTerminationLevel
    MAX-ACCESS  read-only
    STATUS      current
    DESCRIPTION   "Configures the signal overhead termination level of the interface."
    ::=  { interfaceDataEntry 5 }

interfaceDataConnectionType OBJECT-TYPE
    SYNTAX      FspR7TypeConnection
    MAX-ACCESS  read-only
    STATUS      current
    DESCRIPTION
        "Connectivity Parameters for Facilities" 
    ::=  { interfaceDataEntry 6 }

interfaceDataMonLevel OBJECT-TYPE
    SYNTAX      FspR7MonLevel
    MAX-ACCESS  read-only
    STATUS      current
    DESCRIPTION
        "Highest signal level of intrusive or non-intrusive monitoring. Hardware may monitor the signal one layer higher than Termination Level (TERM)." 
    ::=  { interfaceDataEntry 7 }

interfaceDataValidSignalTimer OBJECT-TYPE
    SYNTAX      Unsigned32 (0..5760 | 4294967295) 
    UNITS       "min"
    MAX-ACCESS  read-only
    STATUS      current
    DESCRIPTION
        "AINS state signal quality soak time remaining until transition to IS." 
    ::=  { interfaceDataEntry 8 }

interfaceDataPayload OBJECT-TYPE
    SYNTAX      OtnPayloadType
    MAX-ACCESS  read-only
    STATUS      current
    DESCRIPTION
        "The PAYLOAD defines the transport service type of the payload" 
    ::=  { interfaceDataEntry 9 }

interfaceDataParity OBJECT-TYPE
    SYNTAX      FspR7ParityBit
    MAX-ACCESS  read-only
    STATUS      current
    DESCRIPTION
        "Parity Bit Settings" 
    ::=  { interfaceDataEntry 10 }

interfaceDataPhysIfBaseType OBJECT-TYPE
    SYNTAX      FspR7InterfaceType
    MAX-ACCESS  read-only
    STATUS      current
    DESCRIPTION   "The type of the physical interface. Will be nedded for LANIP
         interfaces to deliver information about the BASE facility type."
    ::=  { interfaceDataEntry 11 }

interfaceDataLaserReleaseTimer OBJECT-TYPE
    SYNTAX      Unsigned32 (0..1440 | 4294967295) 
    UNITS       "min"
    MAX-ACCESS  read-only
    STATUS      current
    DESCRIPTION
        "Fall-back timer for forced laser operation." 
    ::=  { interfaceDataEntry 12 }

interfaceDataCir OBJECT-TYPE
    SYNTAX      Unsigned32 
    UNITS       "Mbps"
    MAX-ACCESS  read-only
    STATUS      current
    DESCRIPTION   "Comitted Information Rate of the virtual channel."
    ::=  { interfaceDataEntry 13 }

interfaceDataTransmitWavelength OBJECT-TYPE
    SYNTAX      Unsigned32 
    UNITS       "0.01 nm"
    MAX-ACCESS  read-only
    STATUS      current
    DESCRIPTION
        "Wavelength of Optical Interface (unit: nm)" 
    ::=  { interfaceDataEntry 14 }

interfaceDataTransmitFrequency OBJECT-TYPE
    SYNTAX      Unsigned32 
    UNITS       "0.01 THz"
    MAX-ACCESS  read-only
    STATUS      current
    DESCRIPTION
        "Frequency of Optical Interface (unit: nm)" 
    ::=  { interfaceDataEntry 15 }

interfaceDataTransmitChannel OBJECT-TYPE
    SYNTAX      FspR7ChannelIdentifier
    MAX-ACCESS  read-only
    STATUS      current
    DESCRIPTION
        "Channel" 
    ::=  { interfaceDataEntry 16 }

interfaceDataType OBJECT-TYPE
    SYNTAX      FspR7EquipmentType
    MAX-ACCESS  read-write
    STATUS      current
    DESCRIPTION   "The TYPE of Module."
    ::=  { interfaceDataEntry 17 }

interfaceDataConnectionState OBJECT-TYPE
    SYNTAX      FspR7ConnectState
    MAX-ACCESS  read-only
    STATUS      current
    DESCRIPTION
        "Connection State" 
    ::=  { interfaceDataEntry 18 }

interfaceDataFacilityType OBJECT-TYPE
    SYNTAX      FspR7InterfaceType
    MAX-ACCESS  read-only
    STATUS      current
    DESCRIPTION
        "The TYPE defines the transport service type as wrapper with wrapper layer termination OR else as payload" 
    ::=  { interfaceDataEntry 19 }

interfaceDataProtectionRole OBJECT-TYPE
    SYNTAX      FspR7ProtectionRole
    MAX-ACCESS  read-only
    STATUS      current
    DESCRIPTION
        "Path label Working or Protect" 
    ::=  { interfaceDataEntry 20 }

interfaceDataReach OBJECT-TYPE
    SYNTAX      FspR7OpticalInterfaceReach
    MAX-ACCESS  read-only
    STATUS      current
    DESCRIPTION
        "Reach" 
    ::=  { interfaceDataEntry 21 }

interfaceDataFiberType OBJECT-TYPE
    SYNTAX      FspR7OpticalFiberType
    MAX-ACCESS  read-only
    STATUS      current
    DESCRIPTION
        "Fiber of Optical Interface - Provision, Reference to FIBER__INVENTORY" 
    ::=  { interfaceDataEntry 22 }

interfaceDataOdtuType OBJECT-TYPE
    SYNTAX      FspR7OdtuType
    MAX-ACCESS  read-only
    STATUS      current
    DESCRIPTION
        "ODTU Transport Unit" 
    ::=  { interfaceDataEntry 23 }

interfaceDataOduTribPortNo OBJECT-TYPE
    SYNTAX      SnmpAdminString
    MAX-ACCESS  read-only
    STATUS      current
    DESCRIPTION
        "ODU Tributary Port Number" 
    ::=  { interfaceDataEntry 24 }

interfaceDataOduTribTimeSlottNo OBJECT-TYPE
    SYNTAX      SnmpAdminString
    MAX-ACCESS  read-only
    STATUS      current
    DESCRIPTION
        "ODU Tributary slot number" 
    ::=  { interfaceDataEntry 25 }

interfaceDataRevertiveMode OBJECT-TYPE
    SYNTAX      ApsRevertMode
    MAX-ACCESS  read-only
    STATUS      current
    DESCRIPTION
        "Revertive Protection Switching" 
    ::=  { interfaceDataEntry 26 }

interfaceDataSignalDirection OBJECT-TYPE
    SYNTAX      FspR7SignalDirection
    MAX-ACCESS  read-only
    STATUS      current
    DESCRIPTION
        "Signal Direction" 
    ::=  { interfaceDataEntry 27 }

interfaceDataBidirectionalChannel OBJECT-TYPE
    SYNTAX      FspR7BidirectionalChannel
    MAX-ACCESS  read-only
    STATUS      current
    DESCRIPTION
        "Bidirectional Channel Rates from Provisioning" 
    ::=  { interfaceDataEntry 28 }

interfaceDataTransmitterWavelength OBJECT-TYPE
    SYNTAX      Unsigned32 
    UNITS       "0.01 nm"
    MAX-ACCESS  read-only
    STATUS      current
    DESCRIPTION
        "Transmitter Wavelength of Optical Interface (unit: nm)" 
    ::=  { interfaceDataEntry 29 }

interfaceDataReceiverWavelength OBJECT-TYPE
    SYNTAX      Unsigned32 
    UNITS       "0.01 nm"
    MAX-ACCESS  read-only
    STATUS      current
    DESCRIPTION
        "Receiver Wavelength of Optical Interface (unit: nm)" 
    ::=  { interfaceDataEntry 30 }

interfaceDataTransmitterFrequency OBJECT-TYPE
    SYNTAX      Unsigned32 
    UNITS       "0.01 THz"
    MAX-ACCESS  read-only
    STATUS      current
    DESCRIPTION
        "Transmitter Frequency of Optical Interface (unit: nm)" 
    ::=  { interfaceDataEntry 31 }

interfaceDataReceiverFrequency OBJECT-TYPE
    SYNTAX      Unsigned32 
    UNITS       "0.01 THz"
    MAX-ACCESS  read-only
    STATUS      current
    DESCRIPTION
        "Receiver Frequency of Optical Interface (unit: nm)" 
    ::=  { interfaceDataEntry 32 }

opticalIfConfigTable OBJECT-TYPE
    SYNTAX      SEQUENCE OF OpticalIfConfigEntry
    MAX-ACCESS  not-accessible
    STATUS      current
    DESCRIPTION   "Contains entries for the configuration of optical interfaces.
         This table extends the entries in the ifTable (RFC 2863)."
    ::=  { interfaceConfigAndStatus 3 }

opticalIfConfigEntry OBJECT-TYPE
    SYNTAX      OpticalIfConfigEntry
    MAX-ACCESS  not-accessible
    STATUS      current
    DESCRIPTION   "Only the gpiTTP and ocTTP optical interfaces will have an entry in this table."
    INDEX       {
                  entityIndex
                }
    ::=  { opticalIfConfigTable 1 }

OpticalIfConfigEntry ::=  SEQUENCE
  { opticalIfConfigAlsMode FspR7AlsMode,
    opticalIfConfigErrorForwarding FspR7ErrorFwdMode,
    opticalIfConfigFecType FspR7FecType,
    opticalIfConfigLaserOffDelayFunction EnableState,
    opticalIfConfigForceLaserOn FspR7LaserForcedOperation,
    opticalIfConfigLossAttenuation FspR7LossAttenuation,
    opticalIfConfigAprHighThreshold Unsigned32,
    opticalIfConfigAseTabCreation FspR7AseTabOpr,
    opticalIfConfigWdmRxChannel FspR7ChannelIdentifier,
    opticalIfConfigSigDegThresOtu Integer32,
    opticalIfConfigSigDegPeriodOtu Unsigned32,
    opticalIfConfigSigDegThresOdu Integer32,
    opticalIfConfigSigDegPeriodOdu Unsigned32,
    opticalIfConfigSigDegThresSonetSection FspR7BERThresholdSection,
    opticalIfConfigSigDegThresSdhSection Unsigned32,
    opticalIfConfigSigDegPeriodSdhSection Unsigned32,
    opticalIfConfigDispersionMode FspR7DispersionModes,
    opticalIfConfigDispersionSetting Integer32,
    opticalIfConfigOpticalSetPoint Integer32,
    opticalIfConfigOffset Integer32,
    opticalIfConfigTilt Integer32,
    opticalIfConfigAreaId IpAddress,
    opticalIfConfigAutoThresReset FspR7AutoThresReset,
    opticalIfConfigUtag FspR7UntaggedFrames,
    opticalIfConfigPvid Unsigned32,
    opticalIfConfigPriority Unsigned32,
    opticalIfConfigStagType FspR7SnmpHexString,
    opticalIfConfigCac FspR7L2CacEnable,
    opticalIfConfigMaxFrameSize Unsigned32,
    opticalIfConfigLagActivePorts Unsigned32,
    opticalIfConfigLagPrio Unsigned32,
    opticalIfConfigLagLoadBallanceSource FspR7LagLoadBallanceSource,
    opticalIfConfigLacpTimeout FspR7LacpTimeout,
    opticalIfConfigTransmitChannel FspR7ChannelIdentifier,
    opticalIfConfigFarEndCommunication FspR7YesNo,
    opticalIfConfigLacpMode FspR7LacpMode,
    opticalIfConfigTxOffDelay FspR7EnableDisable,
    opticalIfConfigOpuPayloadType FspR7OpuPayloadType,
    opticalIfConfigOscOpticalSetpoint Integer32,
    opticalIfConfigFiberBrand FspR7FiberBrand,
    opticalIfConfigTiltSet FspR7TiltSet,
    opticalIfConfigForceFwdAsePilotOn FspR7LaserForcedOperation,
    opticalIfConfigXfpDecisionThres FspR7XfpDecisionThres,
    opticalIfConfigDisparityCorrection EnableState,
    opticalIfConfigPrbsPmReset FspR7PrbsPmReset,
    opticalIfConfigTestPrbsRcvMode FspR7TestMode,
    opticalIfConfigTestPrbsTrmtMode FspR7TestMode,
    opticalIfConfigTributarySlotMethod FspR7ManualAuto,
    opticalIfConfigLaserDelayTimer FspR7LaserDelayTimer,
    opticalIfConfigLaserOffTimer Unsigned32,
    opticalIfConfigLaserOnTimer Unsigned32,
    opticalIfConfigLaneChannelSetting FspR7ChannelIdentifier,
    opticalIfConfigBip FspR7Bip,
    opticalIfConfigCodeGain FspR7CodeGain }

opticalIfConfigAlsMode OBJECT-TYPE
    SYNTAX      FspR7AlsMode
    MAX-ACCESS  read-write
    STATUS      current
    DESCRIPTION   "A configuration request for the Automatic Laser Shutdown
         (ALS) function. Refer to FspR7AlsMode Textual Convention for details."
    ::=  { opticalIfConfigEntry 1 }

opticalIfConfigErrorForwarding OBJECT-TYPE
    SYNTAX      FspR7ErrorFwdMode
    MAX-ACCESS  read-write
    STATUS      current
    DESCRIPTION   "A configuration request for the error forwarding function. Refer to
         FspR7ErrorFwdMode Textual Convention for details."
    ::=  { opticalIfConfigEntry 2 }

opticalIfConfigFecType OBJECT-TYPE
    SYNTAX      FspR7FecType
    MAX-ACCESS  read-write
    STATUS      current
    DESCRIPTION   "Configuration of FEC type."
    ::=  { opticalIfConfigEntry 3 }

opticalIfConfigLaserOffDelayFunction OBJECT-TYPE
    SYNTAX      EnableState
    MAX-ACCESS  read-write
    STATUS      current
    DESCRIPTION   "A configuration request for the Laser Off Delay function.
         This function delays turning off the laser as a consequent action to
         a defect."
    ::=  { opticalIfConfigEntry 4 }

opticalIfConfigForceLaserOn OBJECT-TYPE
    SYNTAX      FspR7LaserForcedOperation
    MAX-ACCESS  read-write
    STATUS      current
    DESCRIPTION
        "Laser Forced On" 
    ::=  { opticalIfConfigEntry 5 }

opticalIfConfigLossAttenuation OBJECT-TYPE
    SYNTAX      FspR7LossAttenuation
    MAX-ACCESS  read-write
    STATUS      current
    DESCRIPTION
        "LOS Attenuation Finding in progress" 
    ::=  { opticalIfConfigEntry 6 }

opticalIfConfigAprHighThreshold OBJECT-TYPE
    SYNTAX      Unsigned32 
    UNITS       "0.1 dBm"
    MAX-ACCESS  read-write
    STATUS      current
    DESCRIPTION
        "Automatic Power Reduction High Threshold" 
    ::=  { opticalIfConfigEntry 7 }

opticalIfConfigAseTabCreation OBJECT-TYPE
    SYNTAX      FspR7AseTabOpr
    MAX-ACCESS  read-write
    STATUS      current
    DESCRIPTION
        "ASE Table creation in process" 
    ::=  { opticalIfConfigEntry 8 }

opticalIfConfigWdmRxChannel OBJECT-TYPE
    SYNTAX      FspR7ChannelIdentifier
    MAX-ACCESS  read-write
    STATUS      current
    DESCRIPTION
        "Configuration of Rx optical channel" 
    ::=  { opticalIfConfigEntry 9 }

opticalIfConfigSigDegThresOtu OBJECT-TYPE
    SYNTAX      Integer32 (1..100 | -2147483648) 
    UNITS       "%"
    MAX-ACCESS  read-write
    STATUS      current
    DESCRIPTION
        "Background-Block-Error-Based Signal Degradation Definition for OTU" 
    ::=  { opticalIfConfigEntry 10 }

opticalIfConfigSigDegPeriodOtu OBJECT-TYPE
    SYNTAX      Unsigned32 (2..10 | 4294967295) 
    UNITS       "s"
    MAX-ACCESS  read-write
    STATUS      current
    DESCRIPTION
        "Integration Period for Signal degrade" 
    ::=  { opticalIfConfigEntry 11 }

opticalIfConfigSigDegThresOdu OBJECT-TYPE
    SYNTAX      Integer32 (1..100 | -2147483648) 
    UNITS       "%"
    MAX-ACCESS  read-write
    STATUS      current
    DESCRIPTION
        "Background-Block-Error-Based Signal Degradation Definition for ODU" 
    ::=  { opticalIfConfigEntry 12 }

opticalIfConfigSigDegPeriodOdu OBJECT-TYPE
    SYNTAX      Unsigned32 (2..10 | 4294967295) 
    UNITS       "s"
    MAX-ACCESS  read-write
    STATUS      current
    DESCRIPTION
        "Integration Period for Signal degrade" 
    ::=  { opticalIfConfigEntry 13 }

opticalIfConfigSigDegThresSonetSection OBJECT-TYPE
    SYNTAX      FspR7BERThresholdSection
    MAX-ACCESS  read-write
    STATUS      current
    DESCRIPTION
        "Bit-Error-Based Degradation Definition for SONET (standard integration period)" 
    ::=  { opticalIfConfigEntry 14 }

opticalIfConfigSigDegThresSdhSection OBJECT-TYPE
    SYNTAX      Unsigned32 (1..100 | 4294967295) 
    UNITS       "%"
    MAX-ACCESS  read-write
    STATUS      current
    DESCRIPTION
        "Block-Error-Based Degradation Definition for SDH (standard integration period).
         Defined as percentage Background Block Errors (30% default) evaluated
         over a defined period (SDPER-RS)." 
    ::=  { opticalIfConfigEntry 15 }

opticalIfConfigSigDegPeriodSdhSection OBJECT-TYPE
    SYNTAX      Unsigned32 (2..10 | 4294967295) 
    UNITS       "s"
    MAX-ACCESS  read-write
    STATUS      current
    DESCRIPTION
        "Provisionable Signal Degrade Integration Period for SDH" 
    ::=  { opticalIfConfigEntry 16 }

opticalIfConfigDispersionMode OBJECT-TYPE
    SYNTAX      FspR7DispersionModes
    MAX-ACCESS  read-write
    STATUS      current
    DESCRIPTION
        "Chromatic Dispersion Compensation Mode" 
    ::=  { opticalIfConfigEntry 17 }

opticalIfConfigDispersionSetting OBJECT-TYPE
    SYNTAX      Integer32 (-50000..50000 | -2147483648) 
    UNITS       "ps/nm"
    MAX-ACCESS  read-write
    STATUS      current
    DESCRIPTION
        "Chromatic Dispersion Compensation setting on module" 
    ::=  { opticalIfConfigEntry 18 }

opticalIfConfigOpticalSetPoint OBJECT-TYPE
    SYNTAX      Integer32 (-250..100 | -2147483648) 
    UNITS       "0.1 dBm"
    MAX-ACCESS  read-write
    STATUS      current
    DESCRIPTION   "Sets the optical power for power equalization in ROADM or for channel power
         control in OPCM"
    ::=  { opticalIfConfigEntry 19 }

opticalIfConfigOffset OBJECT-TYPE
    SYNTAX      Integer32 (10..30 | -2147483648) 
    UNITS       "0.1 dB"
    MAX-ACCESS  read-write
    STATUS      current
    DESCRIPTION   "Sets the offset for the mean optical power for power equalization in ROADM"
    ::=  { opticalIfConfigEntry 20 }

opticalIfConfigTilt OBJECT-TYPE
    SYNTAX      Integer32 (-50..0 | -2147483648) 
    UNITS       "0.1 dB"
    MAX-ACCESS  read-write
    STATUS      current
    DESCRIPTION   "Change of optical channel power in dB over the complete transmission band"
    ::=  { opticalIfConfigEntry 21 }

opticalIfConfigAreaId OBJECT-TYPE
    SYNTAX      IpAddress
    MAX-ACCESS  read-write
    STATUS      current
    DESCRIPTION
        "OSPF Area ID for IP Interface" 
    ::=  { opticalIfConfigEntry 22 }

opticalIfConfigAutoThresReset OBJECT-TYPE
    SYNTAX      FspR7AutoThresReset
    MAX-ACCESS  read-write
    STATUS      current
    DESCRIPTION   "This object is used for reseting the
         Adaptive Threshold value to the factory default.
        "
    ::=  { opticalIfConfigEntry 23 }

opticalIfConfigUtag OBJECT-TYPE
    SYNTAX      FspR7UntaggedFrames
    MAX-ACCESS  read-write
    STATUS      current
    DESCRIPTION
        "If untagged frames shall be enabled on this port or not." 
    ::=  { opticalIfConfigEntry 24 }

opticalIfConfigPvid OBJECT-TYPE
    SYNTAX      Unsigned32 (1..4095 | 4294967295)
    MAX-ACCESS  read-write
    STATUS      current
    DESCRIPTION
        "Default VLAN ID (both STAG/CTAG mode) in case UTAG is enabled" 
    ::=  { opticalIfConfigEntry 25 }

opticalIfConfigPriority OBJECT-TYPE
    SYNTAX      Unsigned32 (0..7 | 4294967295)
    MAX-ACCESS  read-write
    STATUS      current
    DESCRIPTION
        "Default PCP in case UTAG is Enabled. The Prio may be remapped in the EVC." 
    ::=  { opticalIfConfigEntry 26 }

opticalIfConfigStagType OBJECT-TYPE
    SYNTAX      FspR7SnmpHexString
    MAX-ACCESS  read-write
    STATUS      current
    DESCRIPTION
        "TAG type field" 
    ::=  { opticalIfConfigEntry 27 }

opticalIfConfigCac OBJECT-TYPE
    SYNTAX      FspR7L2CacEnable
    MAX-ACCESS  read-write
    STATUS      current
    DESCRIPTION
        "Enable of CAC" 
    ::=  { opticalIfConfigEntry 28 }

opticalIfConfigMaxFrameSize OBJECT-TYPE
    SYNTAX      Unsigned32 (1518..9600 | 4294967295)
    MAX-ACCESS  read-write
    STATUS      current
    DESCRIPTION
        "Max Frame Size" 
    ::=  { opticalIfConfigEntry 29 }

opticalIfConfigLagActivePorts OBJECT-TYPE
    SYNTAX      Unsigned32 (1..12 | 4294967295)
    MAX-ACCESS  read-write
    STATUS      current
    DESCRIPTION
        "Number of active ports in the Link Aggregation Group" 
    ::=  { opticalIfConfigEntry 30 }

opticalIfConfigLagPrio OBJECT-TYPE
    SYNTAX      Unsigned32 (0..65535 | 4294967295)
    MAX-ACCESS  read-write
    STATUS      current
    DESCRIPTION
        "Part of ID. Port pri that defines standby." 
    ::=  { opticalIfConfigEntry 31 }

opticalIfConfigLagLoadBallanceSource OBJECT-TYPE
    SYNTAX      FspR7LagLoadBallanceSource
    MAX-ACCESS  read-write
    STATUS      current
    DESCRIPTION
        "What source is used in the load balance calculation" 
    ::=  { opticalIfConfigEntry 32 }

opticalIfConfigLacpTimeout OBJECT-TYPE
    SYNTAX      FspR7LacpTimeout
    MAX-ACCESS  read-write
    STATUS      current
    DESCRIPTION
        "Timeout of the LACP" 
    ::=  { opticalIfConfigEntry 33 }

opticalIfConfigTransmitChannel OBJECT-TYPE
    SYNTAX      FspR7ChannelIdentifier
    MAX-ACCESS  read-write
    STATUS      current
    DESCRIPTION
        "Channel" 
    ::=  { opticalIfConfigEntry 34 }

opticalIfConfigFarEndCommunication OBJECT-TYPE
    SYNTAX      FspR7YesNo
    MAX-ACCESS  read-write
    STATUS      current
    DESCRIPTION
        "Used for Optojack plugs; Communication to Far End Plug is observed" 
    ::=  { opticalIfConfigEntry 35 }

opticalIfConfigLacpMode OBJECT-TYPE
    SYNTAX      FspR7LacpMode
    MAX-ACCESS  read-write
    STATUS      current
    DESCRIPTION
        "Enable of LACP state machine" 
    ::=  { opticalIfConfigEntry 36 }

opticalIfConfigTxOffDelay OBJECT-TYPE
    SYNTAX      FspR7EnableDisable
    MAX-ACCESS  read-write
    STATUS      current
    DESCRIPTION
        "Enable or disable TXOFFHOLD Period for Error Forwarding and LKDO-OFF Consequent Action." 
    ::=  { opticalIfConfigEntry 37 }

opticalIfConfigOpuPayloadType OBJECT-TYPE
    SYNTAX      FspR7OpuPayloadType
    MAX-ACCESS  read-write
    STATUS      current
    DESCRIPTION
        "OPU Payload Type Indicator" 
    ::=  { opticalIfConfigEntry 38 }

opticalIfConfigOscOpticalSetpoint OBJECT-TYPE
    SYNTAX      Integer32 (-250..50 | -2147483648) 
    UNITS       "0.1 dBm"
    MAX-ACCESS  read-write
    STATUS      current
    DESCRIPTION
        "Sets the OSC optical power" 
    ::=  { opticalIfConfigEntry 39 }

opticalIfConfigFiberBrand OBJECT-TYPE
    SYNTAX      FspR7FiberBrand
    MAX-ACCESS  read-write
    STATUS      current
    DESCRIPTION
        "Brand of fiber present in the fiber plant" 
    ::=  { opticalIfConfigEntry 40 }

opticalIfConfigTiltSet OBJECT-TYPE
    SYNTAX      FspR7TiltSet
    MAX-ACCESS  read-write
    STATUS      current
    DESCRIPTION
        "Tilt setting as discrete values versus a range" 
    ::=  { opticalIfConfigEntry 41 }

opticalIfConfigForceFwdAsePilotOn OBJECT-TYPE
    SYNTAX      FspR7LaserForcedOperation
    MAX-ACCESS  read-write
    STATUS      current
    DESCRIPTION
        "Force the BWD Raman pilot on to allow building of FWD Raman ASE Table" 
    ::=  { opticalIfConfigEntry 42 }

opticalIfConfigXfpDecisionThres OBJECT-TYPE
    SYNTAX      FspR7XfpDecisionThres
    MAX-ACCESS  read-write
    STATUS      current
    DESCRIPTION
        "XFP Decision threshold setting" 
    ::=  { opticalIfConfigEntry 43 }

opticalIfConfigDisparityCorrection OBJECT-TYPE
    SYNTAX      EnableState
    MAX-ACCESS  read-write
    STATUS      current
    DESCRIPTION
        "Disparity correction" 
    ::=  { opticalIfConfigEntry 44 }

opticalIfConfigPrbsPmReset OBJECT-TYPE
    SYNTAX      FspR7PrbsPmReset
    MAX-ACCESS  read-write
    STATUS      current
    DESCRIPTION
        "Reset PRBS PM counters" 
    ::=  { opticalIfConfigEntry 45 }

opticalIfConfigTestPrbsRcvMode OBJECT-TYPE
    SYNTAX      FspR7TestMode
    MAX-ACCESS  read-write
    STATUS      current
    DESCRIPTION
        "PRBS test pattern received" 
    ::=  { opticalIfConfigEntry 46 }

opticalIfConfigTestPrbsTrmtMode OBJECT-TYPE
    SYNTAX      FspR7TestMode
    MAX-ACCESS  read-write
    STATUS      current
    DESCRIPTION
        "PRBS test pattern transmitted" 
    ::=  { opticalIfConfigEntry 47 }

opticalIfConfigTributarySlotMethod OBJECT-TYPE
    SYNTAX      FspR7ManualAuto
    MAX-ACCESS  read-write
    STATUS      current
    DESCRIPTION
        "Tributary Slot assignment method" 
    ::=  { opticalIfConfigEntry 48 }

opticalIfConfigLaserDelayTimer OBJECT-TYPE
    SYNTAX      FspR7LaserDelayTimer
    MAX-ACCESS  read-write
    STATUS      current
    DESCRIPTION
        "Relevant only when ERRFWD=LSROFF. Enables/disables the
         possibility to delay turning off and on the laser.
         This applies to the case when turning off the laser
         is done as an error forwarding mechanism." 
    ::=  { opticalIfConfigEntry 49 }

opticalIfConfigLaserOffTimer OBJECT-TYPE
    SYNTAX      Unsigned32 (1..1000 | 4294967295) 
    UNITS       "ms"
    MAX-ACCESS  read-write
    STATUS      current
    DESCRIPTION
        "Delay before laser is swiched off" 
    ::=  { opticalIfConfigEntry 50 }

opticalIfConfigLaserOnTimer OBJECT-TYPE
    SYNTAX      Unsigned32 (1..1000 | 4294967295) 
    UNITS       "ms"
    MAX-ACCESS  read-write
    STATUS      current
    DESCRIPTION
        "Delay before laser is switched on" 
    ::=  { opticalIfConfigEntry 51 }

opticalIfConfigLaneChannelSetting OBJECT-TYPE
    SYNTAX      FspR7ChannelIdentifier
    MAX-ACCESS  read-write
    STATUS      current
    DESCRIPTION
        "Lane Channel Setting" 
    ::=  { opticalIfConfigEntry 52 }

opticalIfConfigBip OBJECT-TYPE
    SYNTAX      FspR7Bip
    MAX-ACCESS  read-write
    STATUS      current
    DESCRIPTION
        "Bit Interleaved Parity" 
    ::=  { opticalIfConfigEntry 53 }

opticalIfConfigCodeGain OBJECT-TYPE
    SYNTAX      FspR7CodeGain
    MAX-ACCESS  read-write
    STATUS      current
    DESCRIPTION
        "Forward Error Correction Coding gain" 
    ::=  { opticalIfConfigEntry 54 }

opticalIfDataTable OBJECT-TYPE
    SYNTAX      SEQUENCE OF OpticalIfDataEntry
    MAX-ACCESS  not-accessible
    STATUS      current
    DESCRIPTION   "Contains diagnostic entries for optical interfaces.
         This table extends the entries in the ifTable (RFC 2863)."
    ::=  { interfaceConfigAndStatus 4 }

opticalIfDataEntry OBJECT-TYPE
    SYNTAX      OpticalIfDataEntry
    MAX-ACCESS  not-accessible
    STATUS      current
    DESCRIPTION   ""
    INDEX       {
                  entityIndex
                }
    ::=  { opticalIfDataTable 1 }

OpticalIfDataEntry ::=  SEQUENCE
  { opticalIfDataWdmChannel FspR7ChannelIdentifier,
    opticalIfDataWavelength SnmpAdminString,
    opticalIfDataFiberType FspR7OpticalFiberType,
    opticalIfDataLinkLength FspR7OpticalInterfaceReach,
    opticalIfDataAlsHoldoff FspR7AlsHoldoff,
    opticalIfDataLaserOffDelayTime FspR7LaserOffDelayTime,
    opticalIfDataProtectionRole FspR7ProtectionRole,
    opticalIfDataChannelSpacing FspR7ChannelSpacing,
    opticalIfDataTunableLowestChannel FspR7ChannelIdentifier,
    opticalIfDataTunableHighestChannel FspR7ChannelIdentifier,
    opticalIfDataTransmitWavelength Unsigned32,
    opticalIfDataFrequency Unsigned32,
    opticalIfDataChannelsNumber FspR7NumberOfChannels,
    opticalIfDataFunction FspR7InterfaceFunction,
    opticalIfDataPortMode FspR7PortMode,
    opticalIfDataPortRole FspR7PortRole,
    opticalIfDataCirRcv Unsigned32,
    opticalIfDataCbsRcv Unsigned32,
    opticalIfDataCirTrmt Unsigned32,
    opticalIfDataCbsTrmt Unsigned32,
    opticalIfDataVethAid EntityIndex,
    opticalIfDataLagPorts FspR7LagPorts,
    opticalIfDataLagPortType FspR7LagPortType,
    opticalIfDataLagStandby FspR7LagStandby,
    opticalIfDataLacpMode FspR7LacpMode,
    opticalIfDataLagKey Unsigned32,
    opticalIfDataLagPortNo Unsigned32,
    opticalIfDataLagState FspR7LagState,
    opticalIfDataLagIdFend FspR7LagIdFend,
    opticalIfDataLagFendState FspR7LagFendState,
    opticalIfDataLagSysMac MacAddress,
    opticalIfDataLagSysIdFend FspR7LagSysIdFend,
    opticalIfDataLagSysPrio Unsigned32,
    opticalIfDataBand FspR7OpticalBand,
    opticalIfDataStuff FspR7Stuff,
    opticalIfDataChannelsProvision FspR7NumberOfChannels,
    opticalIfDataAutoPTassignment FspR7ManualAuto,
    opticalIfDataTributaryFreeSlotNo Unsigned32,
    opticalIfDataTributaryAssignedSlotNo Unsigned32,
    opticalIfDataOdtuType FspR7OdtuType,
    opticalIfDataOduTribPortNo SnmpAdminString,
    opticalIfDataOduTribTimeSlottNo SnmpAdminString,
    opticalIfDataLaserDelayTimer FspR7LaneGroupInventory,
    opticalIfDataLaneChannel1 FspR7ChannelIdentifier,
    opticalIfDataLaneChannel2 FspR7ChannelIdentifier,
    opticalIfDataLaneChannel3 FspR7ChannelIdentifier,
    opticalIfDataLaneChannel4 FspR7ChannelIdentifier,
    opticalIfDataReceiverWavelength Unsigned32,
    opticalIfDataReceiverFrequency Unsigned32 }

opticalIfDataWdmChannel OBJECT-TYPE
    SYNTAX      FspR7ChannelIdentifier
    MAX-ACCESS  read-only
    STATUS      current
    DESCRIPTION   "The WDM channel, as per ADVA grid, of this interface."
    ::=  { opticalIfDataEntry 1 }

opticalIfDataWavelength OBJECT-TYPE
    SYNTAX      SnmpAdminString
    MAX-ACCESS  read-only
    STATUS      deprecated
    DESCRIPTION   "Parameter deprecated. Look at TransmitWavelength parameter."
    ::=  { opticalIfDataEntry 2 }

opticalIfDataFiberType OBJECT-TYPE
    SYNTAX      FspR7OpticalFiberType
    MAX-ACCESS  read-only
    STATUS      current
    DESCRIPTION   "The fiber type of this interface. For interface modules not
         supporting Fibre Channel Transmission, the value will be 'unspecified'."
    ::=  { opticalIfDataEntry 3 }

opticalIfDataLinkLength OBJECT-TYPE
    SYNTAX      FspR7OpticalInterfaceReach
    MAX-ACCESS  read-only
    STATUS      current
    DESCRIPTION
        "Reach" 
    ::=  { opticalIfDataEntry 4 }

opticalIfDataAlsHoldoff OBJECT-TYPE
    SYNTAX      FspR7AlsHoldoff
    MAX-ACCESS  read-only
    STATUS      current
    DESCRIPTION   "Refer to FspR7AlsHoldoff Textual Convention for details."
    ::=  { opticalIfDataEntry 5 }

opticalIfDataLaserOffDelayTime OBJECT-TYPE
    SYNTAX      FspR7LaserOffDelayTime
    MAX-ACCESS  read-only
    STATUS      current
    DESCRIPTION   "Laser Off Delay function. This function delays turning off the laser
         as a consequent action to a defect."
    ::=  { opticalIfDataEntry 6 }

opticalIfDataProtectionRole OBJECT-TYPE
    SYNTAX      FspR7ProtectionRole
    MAX-ACCESS  read-only
    STATUS      current
    DESCRIPTION
        "Path label Working or Protect" 
    ::=  { opticalIfDataEntry 7 }

opticalIfDataChannelSpacing OBJECT-TYPE
    SYNTAX      FspR7ChannelSpacing
    MAX-ACCESS  read-only
    STATUS      current
    DESCRIPTION
        "ITU Grid channel spacing" 
    ::=  { opticalIfDataEntry 8 }

opticalIfDataTunableLowestChannel OBJECT-TYPE
    SYNTAX      FspR7ChannelIdentifier
    MAX-ACCESS  read-only
    STATUS      current
    DESCRIPTION
        "The lowest channel for tunable Laser Module" 
    ::=  { opticalIfDataEntry 9 }

opticalIfDataTunableHighestChannel OBJECT-TYPE
    SYNTAX      FspR7ChannelIdentifier
    MAX-ACCESS  read-only
    STATUS      current
    DESCRIPTION
        "The highest channel for tunable Laser Module" 
    ::=  { opticalIfDataEntry 10 }

opticalIfDataTransmitWavelength OBJECT-TYPE
    SYNTAX      Unsigned32 
    UNITS       "0.01 nm"
    MAX-ACCESS  read-only
    STATUS      current
    DESCRIPTION   "The transmit wavelength of this interface."
    ::=  { opticalIfDataEntry 11 }

opticalIfDataFrequency OBJECT-TYPE
    SYNTAX      Unsigned32 
    UNITS       "0.01 THz"
    MAX-ACCESS  read-only
    STATUS      current
    DESCRIPTION
        "Frequency of Optical Interface (unit: nm)" 
    ::=  { opticalIfDataEntry 12 }

opticalIfDataChannelsNumber OBJECT-TYPE
    SYNTAX      FspR7NumberOfChannels
    MAX-ACCESS  read-only
    STATUS      current
    DESCRIPTION   "Number of channels supported by an entity"
    ::=  { opticalIfDataEntry 13 }

opticalIfDataFunction OBJECT-TYPE
    SYNTAX      FspR7InterfaceFunction
    MAX-ACCESS  read-only
    STATUS      current
    DESCRIPTION
        "Interface Function" 
    ::=  { opticalIfDataEntry 14 }

opticalIfDataPortMode OBJECT-TYPE
    SYNTAX      FspR7PortMode
    MAX-ACCESS  read-only
    STATUS      current
    DESCRIPTION
        "Port Mode" 
    ::=  { opticalIfDataEntry 15 }

opticalIfDataPortRole OBJECT-TYPE
    SYNTAX      FspR7PortRole
    MAX-ACCESS  read-only
    STATUS      current
    DESCRIPTION
        "ADVA cloud Port Roles" 
    ::=  { opticalIfDataEntry 16 }

opticalIfDataCirRcv OBJECT-TYPE
    SYNTAX      Unsigned32 
    UNITS       "Mbps"
    MAX-ACCESS  read-only
    STATUS      current
    DESCRIPTION
        "CIR (Committed Information Rate ) is used on Ethernet Interfaces with a policing function" 
    ::=  { opticalIfDataEntry 17 }

opticalIfDataCbsRcv OBJECT-TYPE
    SYNTAX      Unsigned32 (0..26214400 | 4294967295) 
    UNITS       "Byte"
    MAX-ACCESS  read-only
    STATUS      current
    DESCRIPTION
        "Committed Burst Size" 
    ::=  { opticalIfDataEntry 18 }

opticalIfDataCirTrmt OBJECT-TYPE
    SYNTAX      Unsigned32 
    UNITS       "Mbps"
    MAX-ACCESS  read-only
    STATUS      current
    DESCRIPTION
        "CIR (Committed Information Rate ) is used on Ethernet Interfaces with a policing function" 
    ::=  { opticalIfDataEntry 19 }

opticalIfDataCbsTrmt OBJECT-TYPE
    SYNTAX      Unsigned32 (0..25600 | 4294967295) 
    UNITS       "kByte"
    MAX-ACCESS  read-only
    STATUS      current
    DESCRIPTION
        "Committed Burst Size" 
    ::=  { opticalIfDataEntry 20 }

opticalIfDataVethAid OBJECT-TYPE
    SYNTAX      EntityIndex
    MAX-ACCESS  read-only
    STATUS      current
    DESCRIPTION
        "Shows if PORT is a member in the LAG with the VETH AID" 
    ::=  { opticalIfDataEntry 21 }

opticalIfDataLagPorts OBJECT-TYPE
    SYNTAX      FspR7LagPorts
    MAX-ACCESS  read-only
    STATUS      current
    DESCRIPTION
        "A list of ports(AIDs) in the LAG." 
    ::=  { opticalIfDataEntry 22 }

opticalIfDataLagPortType OBJECT-TYPE
    SYNTAX      FspR7LagPortType
    MAX-ACCESS  read-only
    STATUS      current
    DESCRIPTION
        "Type/Speed of connected ports in the Link Aggregation Group" 
    ::=  { opticalIfDataEntry 23 }

opticalIfDataLagStandby OBJECT-TYPE
    SYNTAX      FspR7LagStandby
    MAX-ACCESS  read-only
    STATUS      current
    DESCRIPTION
        "Port is in standby in the Link Aggregation Group" 
    ::=  { opticalIfDataEntry 24 }

opticalIfDataLacpMode OBJECT-TYPE
    SYNTAX      FspR7LacpMode
    MAX-ACCESS  read-only
    STATUS      current
    DESCRIPTION
        "Enable of LACP state machine" 
    ::=  { opticalIfDataEntry 25 }

opticalIfDataLagKey OBJECT-TYPE
    SYNTAX      Unsigned32
    MAX-ACCESS  read-only
    STATUS      current
    DESCRIPTION
        "Part of ID. Operational KEY" 
    ::=  { opticalIfDataEntry 26 }

opticalIfDataLagPortNo OBJECT-TYPE
    SYNTAX      Unsigned32
    MAX-ACCESS  read-only
    STATUS      current
    DESCRIPTION
        "Part of ID. Hardcoded to physical port no." 
    ::=  { opticalIfDataEntry 27 }

opticalIfDataLagState OBJECT-TYPE
    SYNTAX      FspR7LagState
    MAX-ACCESS  read-only
    STATUS      current
    DESCRIPTION
        "State of the LACP on this port" 
    ::=  { opticalIfDataEntry 28 }

opticalIfDataLagIdFend OBJECT-TYPE
    SYNTAX      FspR7LagIdFend
    MAX-ACCESS  read-only
    STATUS      current
    DESCRIPTION
        "Part of Partner PORT ID. Operational Key, Pri and No. uses 4+2+4 HEX values. Coded as 10 HEXV2 in DD." 
    ::=  { opticalIfDataEntry 29 }

opticalIfDataLagFendState OBJECT-TYPE
    SYNTAX      FspR7LagFendState
    MAX-ACCESS  read-only
    STATUS      current
    DESCRIPTION
        "State of the LACP on partner port" 
    ::=  { opticalIfDataEntry 30 }

opticalIfDataLagSysMac OBJECT-TYPE
    SYNTAX      MacAddress
    MAX-ACCESS  read-only
    STATUS      current
    DESCRIPTION
        "System MAC set to first member port" 
    ::=  { opticalIfDataEntry 31 }

opticalIfDataLagSysIdFend OBJECT-TYPE
    SYNTAX      FspR7LagSysIdFend
    MAX-ACCESS  read-only
    STATUS      current
    DESCRIPTION
        "System ID (Pri&MAC) received from the Partner of the Link Aggregation Group." 
    ::=  { opticalIfDataEntry 32 }

opticalIfDataLagSysPrio OBJECT-TYPE
    SYNTAX      Unsigned32 (0..65535 | 4294967295)
    MAX-ACCESS  read-only
    STATUS      current
    DESCRIPTION
        "Link Aggregation Group Actor System Priority Part of LAG ID" 
    ::=  { opticalIfDataEntry 33 }

opticalIfDataBand OBJECT-TYPE
    SYNTAX      FspR7OpticalBand
    MAX-ACCESS  read-only
    STATUS      current
    DESCRIPTION
        "Band Provision. Reference to BAND__INVENTORY." 
    ::=  { opticalIfDataEntry 34 }

opticalIfDataStuff OBJECT-TYPE
    SYNTAX      FspR7Stuff
    MAX-ACCESS  read-only
    STATUS      current
    DESCRIPTION
        "Indicates if bit/byte stuffing is used in the transport signal." 
    ::=  { opticalIfDataEntry 35 }

opticalIfDataChannelsProvision OBJECT-TYPE
    SYNTAX      FspR7NumberOfChannels
    MAX-ACCESS  read-only
    STATUS      current
    DESCRIPTION
        "Number of channels supported by an entity" 
    ::=  { opticalIfDataEntry 36 }

opticalIfDataAutoPTassignment OBJECT-TYPE
    SYNTAX      FspR7ManualAuto
    MAX-ACCESS  read-only
    STATUS      current
    DESCRIPTION
        "Auto assignment of ODU PT" 
    ::=  { opticalIfDataEntry 37 }

opticalIfDataTributaryFreeSlotNo OBJECT-TYPE
    SYNTAX      Unsigned32 (0..512 | 4294967295)
    MAX-ACCESS  read-only
    STATUS      current
    DESCRIPTION
        "Number of Tributary Slots which are available for assignment." 
    ::=  { opticalIfDataEntry 38 }

opticalIfDataTributaryAssignedSlotNo OBJECT-TYPE
    SYNTAX      Unsigned32 (0..512 | 4294967295)
    MAX-ACCESS  read-only
    STATUS      current
    DESCRIPTION
        "Number of Tributary Slots which have been assigned." 
    ::=  { opticalIfDataEntry 39 }

opticalIfDataOdtuType OBJECT-TYPE
    SYNTAX      FspR7OdtuType
    MAX-ACCESS  read-only
    STATUS      current
    DESCRIPTION
        "ODTU Transport Unit" 
    ::=  { opticalIfDataEntry 40 }

opticalIfDataOduTribPortNo OBJECT-TYPE
    SYNTAX      SnmpAdminString
    MAX-ACCESS  read-only
    STATUS      current
    DESCRIPTION
        "ODU Tributary Port Number" 
    ::=  { opticalIfDataEntry 41 }

opticalIfDataOduTribTimeSlottNo OBJECT-TYPE
    SYNTAX      SnmpAdminString
    MAX-ACCESS  read-only
    STATUS      current
    DESCRIPTION
        "ODU Tributary slot number" 
    ::=  { opticalIfDataEntry 42 }

opticalIfDataLaserDelayTimer OBJECT-TYPE
    SYNTAX      FspR7LaneGroupInventory
    MAX-ACCESS  read-only
    STATUS      current
    DESCRIPTION
        "Lane group to provision" 
    ::=  { opticalIfDataEntry 43 }

opticalIfDataLaneChannel1 OBJECT-TYPE
    SYNTAX      FspR7ChannelIdentifier
    MAX-ACCESS  read-only
    STATUS      current
    DESCRIPTION
        "Lane Channel" 
    ::=  { opticalIfDataEntry 44 }

opticalIfDataLaneChannel2 OBJECT-TYPE
    SYNTAX      FspR7ChannelIdentifier
    MAX-ACCESS  read-only
    STATUS      current
    DESCRIPTION
        "Lane Channel" 
    ::=  { opticalIfDataEntry 45 }

opticalIfDataLaneChannel3 OBJECT-TYPE
    SYNTAX      FspR7ChannelIdentifier
    MAX-ACCESS  read-only
    STATUS      current
    DESCRIPTION
        "Lane Channel" 
    ::=  { opticalIfDataEntry 46 }

opticalIfDataLaneChannel4 OBJECT-TYPE
    SYNTAX      FspR7ChannelIdentifier
    MAX-ACCESS  read-only
    STATUS      current
    DESCRIPTION
        "Lane Channel" 
    ::=  { opticalIfDataEntry 47 }

opticalIfDataReceiverWavelength OBJECT-TYPE
    SYNTAX      Unsigned32 
    UNITS       "0.01 nm"
    MAX-ACCESS  read-only
    STATUS      current
    DESCRIPTION
        "Receiver Wavelength of Optical Interface (unit: nm)" 
    ::=  { opticalIfDataEntry 48 }

opticalIfDataReceiverFrequency OBJECT-TYPE
    SYNTAX      Unsigned32 
    UNITS       "0.01 THz"
    MAX-ACCESS  read-only
    STATUS      current
    DESCRIPTION
        "Receiver Frequency of Optical Interface (unit: nm)" 
    ::=  { opticalIfDataEntry 49 }

opticalIfDiagTable OBJECT-TYPE
    SYNTAX      SEQUENCE OF OpticalIfDiagEntry
    MAX-ACCESS  not-accessible
    STATUS      current
    DESCRIPTION   "Contains diagnostic entries for optical interfaces. This
         table extends the entries in the ifTable (RFC 2863)."
    ::=  { interfaceConfigAndStatus 5 }

opticalIfDiagEntry OBJECT-TYPE
    SYNTAX      OpticalIfDiagEntry
    MAX-ACCESS  not-accessible
    STATUS      current
    DESCRIPTION   ""
    INDEX       {
                  entityIndex
                }
    ::=  { opticalIfDiagTable 1 }

OpticalIfDiagEntry ::=  SEQUENCE
  { opticalIfDiagLaserBiasCurrentNormalized Unsigned32,
    opticalIfDiagLaserTemp Integer32,
    opticalIfDiagInputPower Integer32,
    opticalIfDiagOutputPower Integer32,
    opticalIfDiagLaserBiasCurrentLevel Unsigned32,
    opticalIfDiagPumpLaser1Temp Integer32,
    opticalIfDiagPumpLaser2Temp Integer32,
    opticalIfDiagPumpLaserBiasCurrent1 Unsigned32,
    opticalIfDiagPumpLaserBiasCurrent2 Unsigned32,
    opticalIfDiagAttenuationOfVoa Unsigned32,
    opticalIfDiagBackreflectionPowerReceived Integer32,
    opticalIfDiagOscGain Unsigned32,
    opticalIfDiagOscPowerReceived Integer32,
    opticalIfDiagRamanPumpPower Integer32,
    opticalIfDiagRamanEstSignalGain Unsigned32,
    opticalIfDiagChromaticDispersionCompensation Integer32,
    opticalIfDiagLinkAttenuation Integer32,
    opticalIfDiagPumpLaserBiasCurrent3 Unsigned32,
    opticalIfDiagPumpLaser3Temp Integer32,
    opticalIfDiagLatency Unsigned32,
    opticalIfDiagRoundTripDelay Unsigned32,
    opticalIfDiagOscOutputPower Integer32,
    opticalIfDiagPumpLaser4Temp Integer32,
    opticalIfDiagPumpLaserBiasCurrent4 Unsigned32,
    opticalIfDiagEstimatedChPwrRcv Integer32,
    opticalIfDiagLocalOscTemp Integer32,
    opticalIfDiagDifferentialGroupDelay Integer32,
    opticalIfDiagChromaticDispersion Integer32,
    opticalIfDiagSignalToNoiseRatio Integer32,
    opticalIfDiagCarrierFreqOffset Integer32,
    opticalIfDiagLocalOscBiasLevel Unsigned32,
    opticalIfDiagPrbsElapsedTime Unsigned32,
    opticalIfDiagPrbsErrorFreeTime Unsigned32,
    opticalIfDiagPrbsAvgBER Counter64String,
    opticalIfDiagPrbsMaxBER Counter64String,
    opticalIfDiagLogicalLanesSkew Integer32,
    opticalIfDiagCurrentEdfaOpt Integer32,
    opticalIfDiagTotalGainMeasurement Integer32 }

opticalIfDiagLaserBiasCurrentNormalized OBJECT-TYPE
    SYNTAX      Unsigned32 
    UNITS       "%"
    MAX-ACCESS  read-only
    STATUS      current
    DESCRIPTION
        "Instantaneous Laser Bias Current Normalized" 
    ::=  { opticalIfDiagEntry 1 }

opticalIfDiagLaserTemp OBJECT-TYPE
    SYNTAX      Integer32 
    UNITS       "0.1 degree Celsius"
    MAX-ACCESS  read-only
    STATUS      current
    DESCRIPTION   "The laser temperature, measured with
         a granularity of 0.1 degree Celsius"
    ::=  { opticalIfDiagEntry 2 }

opticalIfDiagInputPower OBJECT-TYPE
    SYNTAX      Integer32 
    UNITS       "0.1 dBm"
    MAX-ACCESS  read-only
    STATUS      current
    DESCRIPTION   "The optical input power of a transmitter in dBm,
         measured in the range of -x to +y dBm (TBD).
         It is only valid when there is no loss of signal at the input,
         in which case a value of -65535 is returned.
         A value of -65535 also indicates that OIP is not available.
         When out of range, -65534 indicates that the OIP is outside
         the maximum value and -65533 for outside the minimum value."
    ::=  { opticalIfDiagEntry 3 }

opticalIfDiagOutputPower OBJECT-TYPE
    SYNTAX      Integer32 
    UNITS       "0.1 dBm"
    MAX-ACCESS  read-only
    STATUS      current
    DESCRIPTION   "The optical output power of a transmitter in dBm,
         measured in the range of -x to +y dBm.(TBD)
         It is only valid when there the laserState is 'On'.
         If not, a value of -65535 is returned.
         A value of -65535 also indicates that OOP is not available.
         When out of range, -65534 indicates that the OOP is outside
         the maximum value and -65533 for outside the minimum value."
    ::=  { opticalIfDiagEntry 4 }

opticalIfDiagLaserBiasCurrentLevel OBJECT-TYPE
    SYNTAX      Unsigned32 
    UNITS       "0.001 A"
    MAX-ACCESS  read-only
    STATUS      current
    DESCRIPTION   "The actual current of the transmitter in mA.
         If the value is -65535, the current is not available."
    ::=  { opticalIfDiagEntry 5 }

opticalIfDiagPumpLaser1Temp OBJECT-TYPE
    SYNTAX      Integer32 
    UNITS       "0.1 degree Celsius"
    MAX-ACCESS  read-only
    STATUS      current
    DESCRIPTION
        "Laser 1 Temperature" 
    ::=  { opticalIfDiagEntry 6 }

opticalIfDiagPumpLaser2Temp OBJECT-TYPE
    SYNTAX      Integer32 
    UNITS       "0.1 degree Celsius"
    MAX-ACCESS  read-only
    STATUS      current
    DESCRIPTION
        "Laser 2 Temperature" 
    ::=  { opticalIfDiagEntry 7 }

opticalIfDiagPumpLaserBiasCurrent1 OBJECT-TYPE
    SYNTAX      Unsigned32 
    UNITS       "0.001 A"
    MAX-ACCESS  read-only
    STATUS      current
    DESCRIPTION
        "Laser Bias Current Level for Laser Pump 1" 
    ::=  { opticalIfDiagEntry 8 }

opticalIfDiagPumpLaserBiasCurrent2 OBJECT-TYPE
    SYNTAX      Unsigned32 
    UNITS       "0.001 A"
    MAX-ACCESS  read-only
    STATUS      current
    DESCRIPTION
        "Laser Bias Current Level for Laser Pump 2" 
    ::=  { opticalIfDiagEntry 9 }

opticalIfDiagAttenuationOfVoa OBJECT-TYPE
    SYNTAX      Unsigned32 
    UNITS       "0.1 dB"
    MAX-ACCESS  read-only
    STATUS      current
    DESCRIPTION
        "Variable Attenuator attenuation in dB" 
    ::=  { opticalIfDiagEntry 10 }

opticalIfDiagBackreflectionPowerReceived OBJECT-TYPE
    SYNTAX      Integer32 
    UNITS       "0.1 dB"
    MAX-ACCESS  read-only
    STATUS      current
    DESCRIPTION
        "Back Reflection Received Current" 
    ::=  { opticalIfDiagEntry 11 }

opticalIfDiagOscGain OBJECT-TYPE
    SYNTAX      Unsigned32 
    UNITS       "0.1 dB"
    MAX-ACCESS  read-only
    STATUS      current
    DESCRIPTION
        "Current Raman OSC gain" 
    ::=  { opticalIfDiagEntry 12 }

opticalIfDiagOscPowerReceived OBJECT-TYPE
    SYNTAX      Integer32 
    UNITS       "0.1 dBm"
    MAX-ACCESS  read-only
    STATUS      current
    DESCRIPTION
        "Optical Supervisory Channel Input Power Received Current" 
    ::=  { opticalIfDiagEntry 13 }

opticalIfDiagRamanPumpPower OBJECT-TYPE
    SYNTAX      Integer32 
    UNITS       "0.1 dBm"
    MAX-ACCESS  read-only
    STATUS      current
    DESCRIPTION
        "Total raman pump power" 
    ::=  { opticalIfDiagEntry 14 }

opticalIfDiagRamanEstSignalGain OBJECT-TYPE
    SYNTAX      Unsigned32 
    UNITS       "0.1 dB"
    MAX-ACCESS  read-only
    STATUS      current
    DESCRIPTION
        "Current Estimated signal gain" 
    ::=  { opticalIfDiagEntry 15 }

opticalIfDiagChromaticDispersionCompensation OBJECT-TYPE
    SYNTAX      Integer32 
    UNITS       "ps/nm"
    MAX-ACCESS  read-only
    STATUS      current
    DESCRIPTION
        "Chromatic Dispersion Compensation" 
    ::=  { opticalIfDiagEntry 16 }

opticalIfDiagLinkAttenuation OBJECT-TYPE
    SYNTAX      Integer32 
    UNITS       "0.1 dB"
    MAX-ACCESS  read-only
    STATUS      current
    DESCRIPTION
        "Link Attenuation" 
    ::=  { opticalIfDiagEntry 17 }

opticalIfDiagPumpLaserBiasCurrent3 OBJECT-TYPE
    SYNTAX      Unsigned32 
    UNITS       "0.001 A"
    MAX-ACCESS  read-only
    STATUS      current
    DESCRIPTION
        "Laser Bias Current Level for Laser Pump 3" 
    ::=  { opticalIfDiagEntry 18 }

opticalIfDiagPumpLaser3Temp OBJECT-TYPE
    SYNTAX      Integer32 
    UNITS       "0.1 degree Celsius"
    MAX-ACCESS  read-only
    STATUS      current
    DESCRIPTION
        "Laser 3 Temperature" 
    ::=  { opticalIfDiagEntry 19 }

opticalIfDiagLatency OBJECT-TYPE
    SYNTAX      Unsigned32 (0..300000 | 4294967295) 
    UNITS       "0.1 us"
    MAX-ACCESS  read-only
    STATUS      current
    DESCRIPTION
        "Measured round trip delay" 
    ::=  { opticalIfDiagEntry 20 }

opticalIfDiagRoundTripDelay OBJECT-TYPE
    SYNTAX      Unsigned32 (0..30000000 | 4294967295) 
    UNITS       "ns"
    MAX-ACCESS  read-only
    STATUS      current
    DESCRIPTION
        "Measured round trip delay" 
    ::=  { opticalIfDiagEntry 21 }

opticalIfDiagOscOutputPower OBJECT-TYPE
    SYNTAX      Integer32 
    UNITS       "0.1 dBm"
    MAX-ACCESS  read-only
    STATUS      current
    DESCRIPTION
        "Instantaneous OSC Optical Power Transmitted (Output)" 
    ::=  { opticalIfDiagEntry 22 }

opticalIfDiagPumpLaser4Temp OBJECT-TYPE
    SYNTAX      Integer32 
    UNITS       "0.1 degree Celsius"
    MAX-ACCESS  read-only
    STATUS      current
    DESCRIPTION
        "Laser 4 Temperature" 
    ::=  { opticalIfDiagEntry 23 }

opticalIfDiagPumpLaserBiasCurrent4 OBJECT-TYPE
    SYNTAX      Unsigned32 
    UNITS       "0.001 A"
    MAX-ACCESS  read-only
    STATUS      current
    DESCRIPTION
        "Laser Bias Current Level for Laser Pump 4" 
    ::=  { opticalIfDiagEntry 24 }

opticalIfDiagEstimatedChPwrRcv OBJECT-TYPE
    SYNTAX      Integer32 
    UNITS       "0.1 dBm"
    MAX-ACCESS  read-only
    STATUS      current
    DESCRIPTION
        "Estimated Instantaneous Channel Power Received" 
    ::=  { opticalIfDiagEntry 25 }

opticalIfDiagLocalOscTemp OBJECT-TYPE
    SYNTAX      Integer32 
    UNITS       "0.1 degree Celsius"
    MAX-ACCESS  read-only
    STATUS      current
    DESCRIPTION
        "Instantaneous Rx Laser Temperature (used for Local Oscillator)" 
    ::=  { opticalIfDiagEntry 26 }

opticalIfDiagDifferentialGroupDelay OBJECT-TYPE
    SYNTAX      Integer32 
    UNITS       "ps"
    MAX-ACCESS  read-only
    STATUS      current
    DESCRIPTION
        "Differential Group Delay measured and compensated by the module" 
    ::=  { opticalIfDiagEntry 27 }

opticalIfDiagChromaticDispersion OBJECT-TYPE
    SYNTAX      Integer32 
    UNITS       "ps/nm"
    MAX-ACCESS  read-only
    STATUS      current
    DESCRIPTION
        "Chromatic Dispersion Compensation" 
    ::=  { opticalIfDiagEntry 28 }

opticalIfDiagSignalToNoiseRatio OBJECT-TYPE
    SYNTAX      Integer32 
    UNITS       "0.1 dB"
    MAX-ACCESS  read-only
    STATUS      current
    DESCRIPTION
        "Signal-to-Noise Ratio measured by the module" 
    ::=  { opticalIfDiagEntry 29 }

opticalIfDiagCarrierFreqOffset OBJECT-TYPE
    SYNTAX      Integer32 
    UNITS       "0.001 GHz"
    MAX-ACCESS  read-only
    STATUS      current
    DESCRIPTION
        "Carrier Frequency Offset" 
    ::=  { opticalIfDiagEntry 30 }

opticalIfDiagLocalOscBiasLevel OBJECT-TYPE
    SYNTAX      Unsigned32 
    UNITS       "0.001 A"
    MAX-ACCESS  read-only
    STATUS      current
    DESCRIPTION
        "Rx Laser Bias Current Level used for Local Oscillator" 
    ::=  { opticalIfDiagEntry 31 }

opticalIfDiagPrbsElapsedTime OBJECT-TYPE
    SYNTAX      Unsigned32 
    UNITS       "s"
    MAX-ACCESS  read-only
    STATUS      current
    DESCRIPTION
        "Time elapsed since PRBS test monitoring started - reset" 
    ::=  { opticalIfDiagEntry 32 }

opticalIfDiagPrbsErrorFreeTime OBJECT-TYPE
    SYNTAX      Unsigned32 
    UNITS       "s"
    MAX-ACCESS  read-only
    STATUS      current
    DESCRIPTION
        "Time elapsed since last PRBS Error detected" 
    ::=  { opticalIfDiagEntry 33 }

opticalIfDiagPrbsAvgBER OBJECT-TYPE
    SYNTAX      Counter64String 
    UNITS       "1.0E-15"
    MAX-ACCESS  read-only
    STATUS      current
    DESCRIPTION
        "Average BER for the PRBS test signal during the monitored time" 
    ::=  { opticalIfDiagEntry 34 }

opticalIfDiagPrbsMaxBER OBJECT-TYPE
    SYNTAX      Counter64String 
    UNITS       "1.0E-15"
    MAX-ACCESS  read-only
    STATUS      current
    DESCRIPTION
        "Maximum measured BER for the PRBS Test signal during monitored time" 
    ::=  { opticalIfDiagEntry 35 }

opticalIfDiagLogicalLanesSkew OBJECT-TYPE
    SYNTAX      Integer32 
    UNITS       "ns"
    MAX-ACCESS  read-only
    STATUS      current
    DESCRIPTION
        "Skew between logical lanes farthest apart" 
    ::=  { opticalIfDiagEntry 36 }

opticalIfDiagCurrentEdfaOpt OBJECT-TYPE
    SYNTAX      Integer32 
    UNITS       "0.1 dBm"
    MAX-ACCESS  read-only
    STATUS      current
    DESCRIPTION
        "Total optical output power from the EDFA amplifier." 
    ::=  { opticalIfDiagEntry 37 }

opticalIfDiagTotalGainMeasurement OBJECT-TYPE
    SYNTAX      Integer32 
    UNITS       "0.1 dB"
    MAX-ACCESS  read-only
    STATUS      current
    DESCRIPTION
        "Total Gain measured, sum of amplifier gain less other attenuation (such as VOA)." 
    ::=  { opticalIfDiagEntry 38 }

ethernetConfigTable OBJECT-TYPE
    SYNTAX      SEQUENCE OF EthernetConfigEntry
    MAX-ACCESS  not-accessible
    STATUS      current
    DESCRIPTION   "Contains entries for the Status information for Ethernet
         interfaces equipped on a Unit. This table extends the entries in the
         ifTable (RFC 2863).
        "
    ::=  { interfaceConfigAndStatus 6 }

ethernetConfigEntry OBJECT-TYPE
    SYNTAX      EthernetConfigEntry
    MAX-ACCESS  not-accessible
    STATUS      current
    DESCRIPTION   "The objects in this table are used for configuration
         of the ethernet interface.
        "
    INDEX       {
                  entityIndex
                }
    ::=  { ethernetConfigTable 1 }

EthernetConfigEntry ::=  SEQUENCE
  { ethernetConfigAutoNegotiation EnableState,
    ethernetConfigDuplexMode EthDuplexMode,
    ethernetConfigBitrate FspR7Bitrate,
    ethernetConfigFlowControl FspR7FlowControlMode,
    ethernetConfigIpType FspR7IpType,
    ethernetConfigIpAddrMonitor IpAddress,
    ethernetConfigIpMaskMonitor IpAddress,
    ethernetConfigAreaId IpAddress }

ethernetConfigAutoNegotiation OBJECT-TYPE
    SYNTAX      EnableState
    MAX-ACCESS  read-write
    STATUS      current
    DESCRIPTION   "The autoneg status of the ethernet layer.
         read-write if FspR7InterfaceType = ifTypeE10or100bt
         read-only if FspR7InterfaceType = ifTypeE100fx
        "
    ::=  { ethernetConfigEntry 1 }

ethernetConfigDuplexMode OBJECT-TYPE
    SYNTAX      EthDuplexMode
    MAX-ACCESS  read-write
    STATUS      current
    DESCRIPTION   "The duplex configuration of the ethernet layer.
         read-write if FspR7InterfaceType = ifTypeE10or100bt
         read-only if FspR7InterfaceType = ifTypeE100fx
        "
    ::=  { ethernetConfigEntry 2 }

ethernetConfigBitrate OBJECT-TYPE
    SYNTAX      FspR7Bitrate
    MAX-ACCESS  read-write
    STATUS      current
    DESCRIPTION   "The bite rate configuration of the ethernet layer.
         read-write if FspR7InterfaceType = ifTypeE10or100bt
         read-only if FspR7InterfaceType = ifTypeE100fx
        "
    ::=  { ethernetConfigEntry 3 }

ethernetConfigFlowControl OBJECT-TYPE
    SYNTAX      FspR7FlowControlMode
    MAX-ACCESS  read-write
    STATUS      current
    DESCRIPTION
        "Flow Control mechanism" 
    ::=  { ethernetConfigEntry 4 }

ethernetConfigIpType OBJECT-TYPE
    SYNTAX      FspR7IpType
    MAX-ACCESS  read-write
    STATUS      current
    DESCRIPTION
        "Type of IP configuration" 
    ::=  { ethernetConfigEntry 5 }

ethernetConfigIpAddrMonitor OBJECT-TYPE
    SYNTAX      IpAddress
    MAX-ACCESS  read-only
    STATUS      current
    DESCRIPTION
        "IP address assigned to LAN IP Interface" 
    ::=  { ethernetConfigEntry 6 }

ethernetConfigIpMaskMonitor OBJECT-TYPE
    SYNTAX      IpAddress
    MAX-ACCESS  read-only
    STATUS      current
    DESCRIPTION
        "IP mask assigned to LAN IP Interface" 
    ::=  { ethernetConfigEntry 7 }

ethernetConfigAreaId OBJECT-TYPE
    SYNTAX      IpAddress
    MAX-ACCESS  read-write
    STATUS      current
    DESCRIPTION
        "OSPF Area ID for IP Interface" 
    ::=  { ethernetConfigEntry 8 }

lanIpConfigTable OBJECT-TYPE
    SYNTAX      SEQUENCE OF LanIpConfigEntry
    MAX-ACCESS  not-accessible
    STATUS      current
    DESCRIPTION   ""
    ::=  { interfaceConfigAndStatus 8 }

lanIpConfigEntry OBJECT-TYPE
    SYNTAX      LanIpConfigEntry
    MAX-ACCESS  not-accessible
    STATUS      current
    DESCRIPTION   ""
    INDEX       {
                  entityIndex
                }
    ::=  { lanIpConfigTable 1 }

LanIpConfigEntry ::=  SEQUENCE
  { lanIpConfigIpAddr IpAddress,
    lanIpConfigIpAddrMask IpAddress,
    lanIpConfigPrio Unsigned32,
    lanIpConfigAuthType FspR7CpAuthType,
    lanIpConfigAuthString SnmpAdminString }

lanIpConfigIpAddr OBJECT-TYPE
    SYNTAX      IpAddress
    MAX-ACCESS  read-write
    STATUS      current
    DESCRIPTION
        "IP Address assigned to LAN IP Interface" 
    ::=  { lanIpConfigEntry 1 }

lanIpConfigIpAddrMask OBJECT-TYPE
    SYNTAX      IpAddress
    MAX-ACCESS  read-write
    STATUS      current
    DESCRIPTION
        "IP MASK assigned to LAN IP Interface" 
    ::=  { lanIpConfigEntry 2 }

lanIpConfigPrio OBJECT-TYPE
    SYNTAX      Unsigned32 (0..255 | 4294967295)
    MAX-ACCESS  read-write
    STATUS      current
    DESCRIPTION
        "Priority" 
    ::=  { lanIpConfigEntry 3 }

lanIpConfigAuthType OBJECT-TYPE
    SYNTAX      FspR7CpAuthType
    MAX-ACCESS  read-write
    STATUS      current
    DESCRIPTION
        "OSPF Authentication Type" 
    ::=  { lanIpConfigEntry 4 }

lanIpConfigAuthString OBJECT-TYPE
    SYNTAX      SnmpAdminString
    MAX-ACCESS  read-write
    STATUS      current
    DESCRIPTION
        "OSPF Authentication Key/String depending on Authentication Type" 
    ::=  { lanIpConfigEntry 5 }

ospfConfigTable OBJECT-TYPE
    SYNTAX      SEQUENCE OF OspfConfigEntry
    MAX-ACCESS  not-accessible
    STATUS      current
    DESCRIPTION   ""
    ::=  { interfaceConfigAndStatus 9 }

ospfConfigEntry OBJECT-TYPE
    SYNTAX      OspfConfigEntry
    MAX-ACCESS  not-accessible
    STATUS      current
    DESCRIPTION   ""
    INDEX       {
                  entityIndex
                }
    ::=  { ospfConfigTable 1 }

OspfConfigEntry ::=  SEQUENCE
  { ospfConfigOspf FspR7OspfMode,
    ospfConfigMetric Unsigned32 }

ospfConfigOspf OBJECT-TYPE
    SYNTAX      FspR7OspfMode
    MAX-ACCESS  read-write
    STATUS      current
    DESCRIPTION
        "OSPF Routing (Dynamic)" 
    ::=  { ospfConfigEntry 1 }

ospfConfigMetric OBJECT-TYPE
    SYNTAX      Unsigned32 (0..65535 | 4294967295)
    MAX-ACCESS  read-write
    STATUS      current
    DESCRIPTION
        "Routing Metric" 
    ::=  { ospfConfigEntry 2 }

ospfDataTable OBJECT-TYPE
    SYNTAX      SEQUENCE OF OspfDataEntry
    MAX-ACCESS  not-accessible
    STATUS      current
    DESCRIPTION   ""
    ::=  { interfaceConfigAndStatus 10 }

ospfDataEntry OBJECT-TYPE
    SYNTAX      OspfDataEntry
    MAX-ACCESS  not-accessible
    STATUS      current
    DESCRIPTION   ""
    INDEX       {
                  entityIndex
                }
    ::=  { ospfDataTable 1 }

OspfDataEntry ::=  SEQUENCE
  { ospfDataDesignatedRouter IpAddress,
    ospfDataBkupDesignatedRouter IpAddress }

ospfDataDesignatedRouter OBJECT-TYPE
    SYNTAX      IpAddress
    MAX-ACCESS  read-only
    STATUS      current
    DESCRIPTION
        "IP Address of Designated Router" 
    ::=  { ospfDataEntry 1 }

ospfDataBkupDesignatedRouter OBJECT-TYPE
    SYNTAX      IpAddress
    MAX-ACCESS  read-only
    STATUS      current
    DESCRIPTION
        "IP Address of Backup Designated Router" 
    ::=  { ospfDataEntry 2 }

pppfConfigTable OBJECT-TYPE
    SYNTAX      SEQUENCE OF PppfConfigEntry
    MAX-ACCESS  not-accessible
    STATUS      current
    DESCRIPTION   ""
    ::=  { interfaceConfigAndStatus 11 }

pppfConfigEntry OBJECT-TYPE
    SYNTAX      PppfConfigEntry
    MAX-ACCESS  not-accessible
    STATUS      current
    DESCRIPTION   ""
    INDEX       {
                  entityIndex
                }
    ::=  { pppfConfigTable 1 }

PppfConfigEntry ::=  SEQUENCE
  { pppfConfigBitrate Unsigned32,
    pppfConfigIpType FspR7IpType,
    pppfConfigDataLayerPmReset FspR7PmReset,
    pppfConfigAreaId IpAddress,
    pppfConfigBaud FspR7Baund,
    pppfConfigAlias SnmpAdminString,
    pppfConfigAuthType FspR7CpAuthType,
    pppfConfigAuthString SnmpAdminString }

pppfConfigBitrate OBJECT-TYPE
    SYNTAX      Unsigned32 (1..13702 | 4294967295) 
    UNITS       "kbps"
    MAX-ACCESS  read-write
    STATUS      current
    DESCRIPTION
        "Maximum provisioned bit rate for PPP/IP Link of transmitter for an ECC" 
    ::=  { pppfConfigEntry 1 }

pppfConfigIpType OBJECT-TYPE
    SYNTAX      FspR7IpType
    MAX-ACCESS  read-write
    STATUS      current
    DESCRIPTION
        "Type of IP configuration" 
    ::=  { pppfConfigEntry 2 }

pppfConfigDataLayerPmReset OBJECT-TYPE
    SYNTAX      FspR7PmReset
    MAX-ACCESS  read-write
    STATUS      current
    DESCRIPTION
        "Reset data-layer Performance registers" 
    ::=  { pppfConfigEntry 3 }

pppfConfigAreaId OBJECT-TYPE
    SYNTAX      IpAddress
    MAX-ACCESS  read-write
    STATUS      current
    DESCRIPTION
        "OSPF Area ID for IP Interface" 
    ::=  { pppfConfigEntry 4 }

pppfConfigBaud OBJECT-TYPE
    SYNTAX      FspR7Baund
    MAX-ACCESS  read-write
    STATUS      current
    DESCRIPTION
        "Baud rate of the serial interface" 
    ::=  { pppfConfigEntry 5 }

pppfConfigAlias OBJECT-TYPE
    SYNTAX      SnmpAdminString
    MAX-ACCESS  read-write
    STATUS      current
    DESCRIPTION
        "User Applied Descriptor" 
    ::=  { pppfConfigEntry 6 }

pppfConfigAuthType OBJECT-TYPE
    SYNTAX      FspR7CpAuthType
    MAX-ACCESS  read-write
    STATUS      current
    DESCRIPTION
        "OSPF Authentication Type" 
    ::=  { pppfConfigEntry 7 }

pppfConfigAuthString OBJECT-TYPE
    SYNTAX      SnmpAdminString
    MAX-ACCESS  read-write
    STATUS      current
    DESCRIPTION
        "OSPF Authentication Key/String depending on Authentication Type" 
    ::=  { pppfConfigEntry 8 }

pppDataTable OBJECT-TYPE
    SYNTAX      SEQUENCE OF PppDataEntry
    MAX-ACCESS  not-accessible
    STATUS      current
    DESCRIPTION   ""
    ::=  { interfaceConfigAndStatus 12 }

pppDataEntry OBJECT-TYPE
    SYNTAX      PppDataEntry
    MAX-ACCESS  not-accessible
    STATUS      current
    DESCRIPTION   ""
    INDEX       {
                  entityIndex
                }
    ::=  { pppDataTable 1 }

PppDataEntry ::=  SEQUENCE
  { pppDataNearEndIp IpAddress,
    pppDataFarEndIp IpAddress,
    pppDataEccInstance EntityIndex,
    pppDataNearEndIpMonitor IpAddress,
    pppDataProxyArp FspR7NoYes }

pppDataNearEndIp OBJECT-TYPE
    SYNTAX      IpAddress
    MAX-ACCESS  read-only
    STATUS      current
    DESCRIPTION
        "IP Address assigned to PPP Termination Point on Near-End NE. Defaults to System IP address" 
    ::=  { pppDataEntry 1 }

pppDataFarEndIp OBJECT-TYPE
    SYNTAX      IpAddress
    MAX-ACCESS  read-only
    STATUS      current
    DESCRIPTION
        "IP Address assigned to PPP Termination Point on Far-End NE. Default is set by NE System on LINK establishment if FENDIPACPT = Y" 
    ::=  { pppDataEntry 2 }

pppDataEccInstance OBJECT-TYPE
    SYNTAX      EntityIndex
    MAX-ACCESS  read-only
    STATUS      current
    DESCRIPTION
        "Address Identifier of ECC Entity." 
    ::=  { pppDataEntry 3 }

pppDataNearEndIpMonitor OBJECT-TYPE
    SYNTAX      IpAddress
    MAX-ACCESS  read-only
    STATUS      current
    DESCRIPTION
        "IP address assigned to Near-End NE" 
    ::=  { pppDataEntry 4 }

pppDataProxyArp OBJECT-TYPE
    SYNTAX      FspR7NoYes
    MAX-ACCESS  read-only
    STATUS      current
    DESCRIPTION   "If enabled then ARP requests for FENDIP (coming in on another
         interface in the same subnet as FENDIP) will be replied too."
    ::=  { pppDataEntry 5 }

crsDcnDataTable OBJECT-TYPE
    SYNTAX      SEQUENCE OF CrsDcnDataEntry
    MAX-ACCESS  not-accessible
    STATUS      current
    DESCRIPTION   ""
    ::=  { interfaceConfigAndStatus 13 }

crsDcnDataEntry OBJECT-TYPE
    SYNTAX      CrsDcnDataEntry
    MAX-ACCESS  not-accessible
    STATUS      current
    DESCRIPTION   ""
    INDEX       {
                  entityIndex
                }
    ::=  { crsDcnDataTable 1 }

CrsDcnDataEntry ::=  SEQUENCE
  { crsDcnDataPppInstance EntityIndex,
    crsDcnDataEccInstance EntityIndex }

crsDcnDataPppInstance OBJECT-TYPE
    SYNTAX      EntityIndex
    MAX-ACCESS  read-only
    STATUS      current
    DESCRIPTION
        "Address Identifier of PPPIP LINK Entity." 
    ::=  { crsDcnDataEntry 1 }

crsDcnDataEccInstance OBJECT-TYPE
    SYNTAX      EntityIndex
    MAX-ACCESS  read-only
    STATUS      current
    DESCRIPTION
        "Address Identifier of ECC Entity." 
    ::=  { crsDcnDataEntry 2 }

eocDataTable OBJECT-TYPE
    SYNTAX      SEQUENCE OF EocDataEntry
    MAX-ACCESS  not-accessible
    STATUS      current
    DESCRIPTION   ""
    ::=  { interfaceConfigAndStatus 14 }

eocDataEntry OBJECT-TYPE
    SYNTAX      EocDataEntry
    MAX-ACCESS  not-accessible
    STATUS      current
    DESCRIPTION   ""
    INDEX       {
                  entityIndex
                }
    ::=  { eocDataTable 1 }

EocDataEntry ::=  SEQUENCE
  { eocDataProtAvailability FspR7EocProtAvailability,
    eocDataIpEntity EntityIndex,
    eocDataMaxDataRate Unsigned32,
    eocDataConnectionType FspR7TypeConnection,
    eocDataProtectionRole FspR7ProtectionRole }

eocDataProtAvailability OBJECT-TYPE
    SYNTAX      FspR7EocProtAvailability
    MAX-ACCESS  read-only
    STATUS      current
    DESCRIPTION   "The availability of protection switching functionality on the EOC."
    ::=  { eocDataEntry 1 }

eocDataIpEntity OBJECT-TYPE
    SYNTAX      EntityIndex
    MAX-ACCESS  read-only
    STATUS      current
    DESCRIPTION   "Address of IP Entity on Module with Router Capability to which the
         EOC is connected."
    ::=  { eocDataEntry 2 }

eocDataMaxDataRate OBJECT-TYPE
    SYNTAX      Unsigned32 
    UNITS       "kbps"
    MAX-ACCESS  read-only
    STATUS      current
    DESCRIPTION   "Max data rate of the EOC"
    ::=  { eocDataEntry 3 }

eocDataConnectionType OBJECT-TYPE
    SYNTAX      FspR7TypeConnection
    MAX-ACCESS  read-only
    STATUS      current
    DESCRIPTION   "Uni- or bidirectional traffic."
    ::=  { eocDataEntry 4 }

eocDataProtectionRole OBJECT-TYPE
    SYNTAX      FspR7ProtectionRole
    MAX-ACCESS  read-only
    STATUS      current
    DESCRIPTION
        "Path label Working or Protect" 
    ::=  { eocDataEntry 5 }

opticalIfOlmTable OBJECT-TYPE
    SYNTAX      SEQUENCE OF OpticalIfOlmEntry
    MAX-ACCESS  not-accessible
    STATUS      current
    DESCRIPTION   "Contains optical line monitoring entries for optical interfaces.
         This table extends the entries in the
         ifTable (RFC 2863)."
    ::=  { interfaceConfigAndStatus 15 }

opticalIfOlmEntry OBJECT-TYPE
    SYNTAX      OpticalIfOlmEntry
    MAX-ACCESS  not-accessible
    STATUS      current
    DESCRIPTION   ""
    INDEX       {
                  entityIndex
                }
    ::=  { opticalIfOlmTable 1 }

OpticalIfOlmEntry ::=  SEQUENCE
  { opticalIfOlmRxLineAttenuation Integer32,
    opticalIfOlmTxLineAttenuation Integer32,
    opticalIfOlmFarEndSigDegThres Unsigned32 }

opticalIfOlmRxLineAttenuation OBJECT-TYPE
    SYNTAX      Integer32 
    UNITS       "0.1 dB"
    MAX-ACCESS  read-only
    STATUS      current
    DESCRIPTION   "The Attenuation (in 0.1 dB) on line connected to receiver
         of this interface. If there is loss of signal then ine
         attenuation is -65535. The value -255 will be returned if
         the value isn't available."
    ::=  { opticalIfOlmEntry 1 }

opticalIfOlmTxLineAttenuation OBJECT-TYPE
    SYNTAX      Integer32 
    UNITS       "0.1 dB"
    MAX-ACCESS  read-only
    STATUS      current
    DESCRIPTION   "The Attenuation (in 0.1 dB) on line connected to
         transmitter of this interface. If there is loss of signal
         then line attenuation is -65535. The value -255 will be
         returned if the value isn't available."
    ::=  { opticalIfOlmEntry 2 }

opticalIfOlmFarEndSigDegThres OBJECT-TYPE
    SYNTAX      Unsigned32 
    UNITS       "0.1 dB"
    MAX-ACCESS  read-only
    STATUS      current
    DESCRIPTION
        "Far End Signal Degrade Threshold" 
    ::=  { opticalIfOlmEntry 3 }

opticalAmplifierInterfaceDiagnosticsTable OBJECT-TYPE
    SYNTAX      SEQUENCE OF OpticalAmplifierInterfaceDiagnosticsEntry
    MAX-ACCESS  not-accessible
    STATUS      current
    DESCRIPTION   ""
    ::=  { interfaceConfigAndStatus 16 }

opticalAmplifierInterfaceDiagnosticsEntry OBJECT-TYPE
    SYNTAX      OpticalAmplifierInterfaceDiagnosticsEntry
    MAX-ACCESS  not-accessible
    STATUS      current
    DESCRIPTION   ""
    INDEX       {
                  entityIndex
                }
    ::=  { opticalAmplifierInterfaceDiagnosticsTable 1 }

OpticalAmplifierInterfaceDiagnosticsEntry ::=  SEQUENCE
  { opticalAmplifierInterfaceDiagnosticsOperatingHours Unsigned32,
    opticalAmplifierInterfaceDiagnosticsLaserBiasCurrentLevelAverage Unsigned32,
    opticalAmplifierInterfaceDiagnosticsAttenuation Integer32,
    opticalAmplifierInterfaceDiagnosticsAttenuationVoa Unsigned32,
    opticalAmplifierInterfaceDiagnosticsSubTemp Integer32,
    opticalAmplifierInterfaceDiagnosticsUpperSubTempThres Integer32 }

opticalAmplifierInterfaceDiagnosticsOperatingHours OBJECT-TYPE
    SYNTAX      Unsigned32 
    UNITS       "0.1 h"
    MAX-ACCESS  read-only
    STATUS      current
    DESCRIPTION
        "Accumulated total of Operating Hours" 
    ::=  { opticalAmplifierInterfaceDiagnosticsEntry 1 }

opticalAmplifierInterfaceDiagnosticsLaserBiasCurrentLevelAverage OBJECT-TYPE
    SYNTAX      Unsigned32 
    UNITS       "0.001 A"
    MAX-ACCESS  read-only
    STATUS      current
    DESCRIPTION
        "Laser Bias Current Level averaged over 10 seconds" 
    ::=  { opticalAmplifierInterfaceDiagnosticsEntry 2 }

opticalAmplifierInterfaceDiagnosticsAttenuation OBJECT-TYPE
    SYNTAX      Integer32 
    UNITS       "0.1 dB"
    MAX-ACCESS  read-only
    STATUS      current
    DESCRIPTION
        "Signal attenuation in dB associated with Port. Generally, this parameter is used for the EDFA mid-stage access port (Port 2) and is the attenuation between the first stage transmit (Port 2 Tx) and the second stage receive (Port 2 Rx)." 
    ::=  { opticalAmplifierInterfaceDiagnosticsEntry 3 }

opticalAmplifierInterfaceDiagnosticsAttenuationVoa OBJECT-TYPE
    SYNTAX      Unsigned32 
    UNITS       "0.1 dB"
    MAX-ACCESS  read-only
    STATUS      current
    DESCRIPTION
        "Variable Attenuator attenuation in dB" 
    ::=  { opticalAmplifierInterfaceDiagnosticsEntry 4 }

opticalAmplifierInterfaceDiagnosticsSubTemp OBJECT-TYPE
    SYNTAX      Integer32 
    UNITS       "0.1 degree Celsius"
    MAX-ACCESS  read-only
    STATUS      current
    DESCRIPTION
        "Submodule Temperature" 
    ::=  { opticalAmplifierInterfaceDiagnosticsEntry 5 }

opticalAmplifierInterfaceDiagnosticsUpperSubTempThres OBJECT-TYPE
    SYNTAX      Integer32 
    UNITS       "0.1 degree Celsius"
    MAX-ACCESS  read-only
    STATUS      current
    DESCRIPTION
        "Submodule High Temperature Threshold" 
    ::=  { opticalAmplifierInterfaceDiagnosticsEntry 6 }

ethernetDataTable OBJECT-TYPE
    SYNTAX      SEQUENCE OF EthernetDataEntry
    MAX-ACCESS  not-accessible
    STATUS      current
    DESCRIPTION   ""
    ::=  { interfaceConfigAndStatus 17 }

ethernetDataEntry OBJECT-TYPE
    SYNTAX      EthernetDataEntry
    MAX-ACCESS  not-accessible
    STATUS      current
    DESCRIPTION   ""
    INDEX       {
                  entityIndex
                }
    ::=  { ethernetDataTable 1 }

EthernetDataEntry ::=  SEQUENCE
  { ethernetDataMonitoredDuplexMode EthDuplexMode,
    ethernetDataMonitoredBitrate Unsigned32,
    ethernetDataType FspR7InterfaceType,
    ethernetDataValidSignalTimer Unsigned32 }

ethernetDataMonitoredDuplexMode OBJECT-TYPE
    SYNTAX      EthDuplexMode
    MAX-ACCESS  read-only
    STATUS      current
    DESCRIPTION
        "Duplex Mode (monitor), available when Auto Negoiation is Enable (AUTONEG=ENABLE)" 
    ::=  { ethernetDataEntry 1 }

ethernetDataMonitoredBitrate OBJECT-TYPE
    SYNTAX      Unsigned32 
    UNITS       "Mbps"
    MAX-ACCESS  read-only
    STATUS      current
    DESCRIPTION
        "Bit Rate read from card, - relevant to- auto clock" 
    ::=  { ethernetDataEntry 2 }

ethernetDataType OBJECT-TYPE
    SYNTAX      FspR7InterfaceType
    MAX-ACCESS  read-only
    STATUS      current
    DESCRIPTION
        "The TYPE defines the transport service type as wrapper with wrapper layer termination OR else as payload" 
    ::=  { ethernetDataEntry 3 }

ethernetDataValidSignalTimer OBJECT-TYPE
    SYNTAX      Unsigned32 (0..5760 | 4294967295) 
    UNITS       "min"
    MAX-ACCESS  read-only
    STATUS      current
    DESCRIPTION
        "AINS state signal quality soak time remaining until transition to IS." 
    ::=  { ethernetDataEntry 4 }

opticalFilterIfDataTable OBJECT-TYPE
    SYNTAX      SEQUENCE OF OpticalFilterIfDataEntry
    MAX-ACCESS  not-accessible
    STATUS      current
    DESCRIPTION   ""
    ::=  { interfaceConfigAndStatus 19 }

opticalFilterIfDataEntry OBJECT-TYPE
    SYNTAX      OpticalFilterIfDataEntry
    MAX-ACCESS  not-accessible
    STATUS      current
    DESCRIPTION   ""
    INDEX       {
                  entityIndex
                }
    ::=  { opticalFilterIfDataTable 1 }

OpticalFilterIfDataEntry ::=  SEQUENCE
  { opticalFilterIfDataMultiplexLevel FspR7OpticalMultiplexLevel }

opticalFilterIfDataMultiplexLevel OBJECT-TYPE
    SYNTAX      FspR7OpticalMultiplexLevel
    MAX-ACCESS  read-only
    STATUS      current
    DESCRIPTION
        "Optical Multiplex Level" 
    ::=  { opticalFilterIfDataEntry 1 }

apsProtFacilityConfigCapTable OBJECT-TYPE
    SYNTAX      SEQUENCE OF ApsProtFacilityConfigCapEntry
    MAX-ACCESS  not-accessible
    STATUS      current
    DESCRIPTION   ""
    ::=  { interfaceConfigAndStatus 20 }

apsProtFacilityConfigCapEntry OBJECT-TYPE
    SYNTAX      ApsProtFacilityConfigCapEntry
    MAX-ACCESS  not-accessible
    STATUS      current
    DESCRIPTION   ""
    INDEX       {
                  entityIndex
                }
    ::=  { apsProtFacilityConfigCapTable 1 }

ApsProtFacilityConfigCapEntry ::=  SEQUENCE
  { apsProtFacilityConfigCapSwitchCommand FspR7APSCommandCaps,
    apsProtFacilityConfigCapInhibitSwitchToProt FspR7YesNoCaps,
    apsProtFacilityConfigCapInhibitSwitchToWork FspR7YesNoCaps }

apsProtFacilityConfigCapSwitchCommand OBJECT-TYPE
    SYNTAX      FspR7APSCommandCaps
    MAX-ACCESS  read-only
    STATUS      current
    DESCRIPTION   "This object contains capabilities for
         apsProtFacilityConfigSwitchCommand object."
    ::=  { apsProtFacilityConfigCapEntry 1 }

apsProtFacilityConfigCapInhibitSwitchToProt OBJECT-TYPE
    SYNTAX      FspR7YesNoCaps
    MAX-ACCESS  read-only
    STATUS      current
    DESCRIPTION   "This object contains capabilities for
         apsProtFacilityConfigInhibitSwitchToProt object."
    ::=  { apsProtFacilityConfigCapEntry 2 }

apsProtFacilityConfigCapInhibitSwitchToWork OBJECT-TYPE
    SYNTAX      FspR7YesNoCaps
    MAX-ACCESS  read-only
    STATUS      current
    DESCRIPTION   "This object contains capabilities for
         apsProtFacilityConfigInhibitSwitchToWork object."
    ::=  { apsProtFacilityConfigCapEntry 3 }

interfaceConfigCapTable OBJECT-TYPE
    SYNTAX      SEQUENCE OF InterfaceConfigCapEntry
    MAX-ACCESS  not-accessible
    STATUS      current
    DESCRIPTION   ""
    ::=  { interfaceConfigAndStatus 21 }

interfaceConfigCapEntry OBJECT-TYPE
    SYNTAX      InterfaceConfigCapEntry
    MAX-ACCESS  not-accessible
    STATUS      current
    DESCRIPTION   ""
    INDEX       {
                  entityIndex
                }
    ::=  { interfaceConfigCapTable 1 }

InterfaceConfigCapEntry ::=  SEQUENCE
  { interfaceConfigCapLoopConfig LoopConfigCaps,
    interfaceConfigCapDataLayerPmReset FspR7PmResetCaps,
    interfaceConfigCapEqlzAdmin FspR7EqlzAdminStateCaps,
    interfaceConfigCapDispertionConfig FspR7DispersionConfigCaps,
    interfaceConfigCapTurnupConfig FspR7TurnupConfigCaps,
    interfaceConfigCapInitiateEqualization FspR7InitEqualizationCaps,
    interfaceConfigCapBehaviour FspR7PortBehaviourCaps,
    interfaceConfigCapInitiateRamanEqualization FspR7InitEqualizationCaps,
    interfaceConfigCapSigDegPcslThreshold FspR7Unsigned32Caps }

interfaceConfigCapLoopConfig OBJECT-TYPE
    SYNTAX      LoopConfigCaps
    MAX-ACCESS  read-only
    STATUS      current
    DESCRIPTION   "This object contains capabilities for
         interfaceConfigLoopConfig object."
    ::=  { interfaceConfigCapEntry 1 }

interfaceConfigCapDataLayerPmReset OBJECT-TYPE
    SYNTAX      FspR7PmResetCaps
    MAX-ACCESS  read-only
    STATUS      current
    DESCRIPTION   "This object contains capabilities for
         interfaceConfigDataLayerPmReset object."
    ::=  { interfaceConfigCapEntry 2 }

interfaceConfigCapEqlzAdmin OBJECT-TYPE
    SYNTAX      FspR7EqlzAdminStateCaps
    MAX-ACCESS  read-only
    STATUS      current
    DESCRIPTION   "Scheduled Equalization Administration"
    ::=  { interfaceConfigCapEntry 3 }

interfaceConfigCapDispertionConfig OBJECT-TYPE
    SYNTAX      FspR7DispersionConfigCaps
    MAX-ACCESS  read-only
    STATUS      current
    DESCRIPTION   "Facility Operation Tunable Dispersion Config."
    ::=  { interfaceConfigCapEntry 4 }

interfaceConfigCapTurnupConfig OBJECT-TYPE
    SYNTAX      FspR7TurnupConfigCaps
    MAX-ACCESS  read-only
    STATUS      current
    DESCRIPTION   "Facility Operation Turnup Configuration."
    ::=  { interfaceConfigCapEntry 5 }

interfaceConfigCapInitiateEqualization OBJECT-TYPE
    SYNTAX      FspR7InitEqualizationCaps
    MAX-ACCESS  read-only
    STATUS      current
    DESCRIPTION
        "Initiate Equalization" 
    ::=  { interfaceConfigCapEntry 6 }

interfaceConfigCapBehaviour OBJECT-TYPE
    SYNTAX      FspR7PortBehaviourCaps
    MAX-ACCESS  read-only
    STATUS      current
    DESCRIPTION
        "Behavior or Port usage based on configuration/usage in the system regardless of faceplate designation" 
    ::=  { interfaceConfigCapEntry 7 }

interfaceConfigCapInitiateRamanEqualization OBJECT-TYPE
    SYNTAX      FspR7InitEqualizationCaps
    MAX-ACCESS  read-only
    STATUS      current
    DESCRIPTION
        "Initiate RAMAN Equalization" 
    ::=  { interfaceConfigCapEntry 8 }

interfaceConfigCapSigDegPcslThreshold OBJECT-TYPE
    SYNTAX      FspR7Unsigned32Caps
    UNITS       "%"
    MAX-ACCESS  read-only
    STATUS      current
    DESCRIPTION
        "Block-Error-Based Degradation Definition for Physical Coding Sublayer" 
    ::=  { interfaceConfigCapEntry 9 }

opticalIfConfigCapTable OBJECT-TYPE
    SYNTAX      SEQUENCE OF OpticalIfConfigCapEntry
    MAX-ACCESS  not-accessible
    STATUS      current
    DESCRIPTION   ""
    ::=  { interfaceConfigAndStatus 22 }

opticalIfConfigCapEntry OBJECT-TYPE
    SYNTAX      OpticalIfConfigCapEntry
    MAX-ACCESS  not-accessible
    STATUS      current
    DESCRIPTION   ""
    INDEX       {
                  entityIndex
                }
    ::=  { opticalIfConfigCapTable 1 }

OpticalIfConfigCapEntry ::=  SEQUENCE
  { opticalIfConfigCapForceLaserOn FspR7LaserForcedOperationCaps,
    opticalIfConfigCapLossAttenuation FspR7LossAttenuationCaps,
    opticalIfConfigCapWdmRxChannel FspR7ChannelIdentifierCaps,
    opticalIfConfigCapSigDegThresSonetSection FspR7BERThresholdSectionCaps,
    opticalIfConfigCapDispersionMode FspR7DispersionModesCaps,
    opticalIfConfigCapAutoThresReset FspR7AutoThresResetCaps,
    opticalIfConfigCapAseTabCreation FspR7AseTabOprCaps,
    opticalIfConfigCapUtag FspR7UntaggedFramesCaps,
    opticalIfConfigCapCac FspR7L2CacEnableCaps,
    opticalIfConfigCapLagLoadBallanceSource FspR7LagLoadBallanceSourceCaps,
    opticalIfConfigCapLacpTimeout FspR7LacpTimeoutCaps,
    opticalIfConfigCapFarEndCommunication FspR7YesNoCaps,
    opticalIfConfigCapLacpMode FspR7LacpModeCaps,
    opticalIfConfigCapTxOffDelay FspR7EnableDisableCaps,
    opticalIfConfigCapOpuPayloadType FspR7OpuPayloadTypeCaps,
    opticalIfConfigCapOpticalSetPoint FspR7Integer32Caps,
    opticalIfConfigCapTransmitChannel FspR7ChannelIdentifierCaps,
    opticalIfConfigCapFiberBrand FspR7FiberBrandCaps,
    opticalIfConfigCapTiltSet FspR7TiltSetCaps,
    opticalIfConfigCapForceFwdAsePilotOn FspR7LaserForcedOperationCaps,
    opticalIfConfigCapXfpDecisionThres FspR7XfpDecisionThresCaps,
    opticalIfConfigCapPrbsPmReset FspR7PrbsPmResetCaps,
    opticalIfConfigCapTestPrbsRcvMode FspR7TestModeCaps,
    opticalIfConfigCapTestPrbsTrmtMode FspR7TestModeCaps,
    opticalIfConfigCapTributarySlotMethod FspR7ManualAutoCaps,
    opticalIfConfigCapOffset FspR7Integer32Caps,
    opticalIfConfigCapTilt FspR7Integer32Caps,
    opticalIfConfigCapLaserDelayTimer FspR7LaserDelayTimerCaps,
    opticalIfConfigCapLaserOffTimer FspR7Unsigned32Caps,
    opticalIfConfigCapLaserOnTimer FspR7Unsigned32Caps,
    opticalIfConfigCapLaneChannelSetting FspR7ChannelIdentifierCaps,
    opticalIfConfigCapBip FspR7BipCaps,
    opticalIfConfigCapCodeGain FspR7CodeGainCaps }

opticalIfConfigCapForceLaserOn OBJECT-TYPE
    SYNTAX      FspR7LaserForcedOperationCaps
    MAX-ACCESS  read-only
    STATUS      current
    DESCRIPTION   "This object contains capabilities for
         opticalIfConfigForceLaserOn object."
    ::=  { opticalIfConfigCapEntry 1 }

opticalIfConfigCapLossAttenuation OBJECT-TYPE
    SYNTAX      FspR7LossAttenuationCaps
    MAX-ACCESS  read-only
    STATUS      current
    DESCRIPTION   "This object contains capabilities for
         opticalIfConfigLossAttenuation object."
    ::=  { opticalIfConfigCapEntry 2 }

opticalIfConfigCapWdmRxChannel OBJECT-TYPE
    SYNTAX      FspR7ChannelIdentifierCaps
    MAX-ACCESS  read-only
    STATUS      current
    DESCRIPTION
        "Configuration of Rx optical channel" 
    ::=  { opticalIfConfigCapEntry 3 }

opticalIfConfigCapSigDegThresSonetSection OBJECT-TYPE
    SYNTAX      FspR7BERThresholdSectionCaps
    MAX-ACCESS  read-only
    STATUS      current
    DESCRIPTION
        "Bit-Error-Based Degradation Definition for SONET (standard integration period)" 
    ::=  { opticalIfConfigCapEntry 4 }

opticalIfConfigCapDispersionMode OBJECT-TYPE
    SYNTAX      FspR7DispersionModesCaps
    MAX-ACCESS  read-only
    STATUS      current
    DESCRIPTION
        "Chromatic Dispersion Compensation Mode" 
    ::=  { opticalIfConfigCapEntry 5 }

opticalIfConfigCapAutoThresReset OBJECT-TYPE
    SYNTAX      FspR7AutoThresResetCaps
    MAX-ACCESS  read-only
    STATUS      current
    DESCRIPTION   "This object is used for displaing
         the capabilities for Adaptive Threshold Control
         manipulation.s
        "
    ::=  { opticalIfConfigCapEntry 6 }

opticalIfConfigCapAseTabCreation OBJECT-TYPE
    SYNTAX      FspR7AseTabOprCaps
    MAX-ACCESS  read-only
    STATUS      current
    DESCRIPTION
        "ASE Table creation in process" 
    ::=  { opticalIfConfigCapEntry 7 }

opticalIfConfigCapUtag OBJECT-TYPE
    SYNTAX      FspR7UntaggedFramesCaps
    MAX-ACCESS  read-only
    STATUS      current
    DESCRIPTION
        "If untagged frames shall be enabled on this port or not." 
    ::=  { opticalIfConfigCapEntry 8 }

opticalIfConfigCapCac OBJECT-TYPE
    SYNTAX      FspR7L2CacEnableCaps
    MAX-ACCESS  read-only
    STATUS      current
    DESCRIPTION
        "Enable of CAC" 
    ::=  { opticalIfConfigCapEntry 9 }

opticalIfConfigCapLagLoadBallanceSource OBJECT-TYPE
    SYNTAX      FspR7LagLoadBallanceSourceCaps
    MAX-ACCESS  read-only
    STATUS      current
    DESCRIPTION
        "What source is used in the load balance calculation" 
    ::=  { opticalIfConfigCapEntry 10 }

opticalIfConfigCapLacpTimeout OBJECT-TYPE
    SYNTAX      FspR7LacpTimeoutCaps
    MAX-ACCESS  read-only
    STATUS      current
    DESCRIPTION
        "Timeout of the LACP" 
    ::=  { opticalIfConfigCapEntry 11 }

opticalIfConfigCapFarEndCommunication OBJECT-TYPE
    SYNTAX      FspR7YesNoCaps
    MAX-ACCESS  read-only
    STATUS      current
    DESCRIPTION
        "Used for Optojack plugs; Communication to Far End Plug is observed" 
    ::=  { opticalIfConfigCapEntry 12 }

opticalIfConfigCapLacpMode OBJECT-TYPE
    SYNTAX      FspR7LacpModeCaps
    MAX-ACCESS  read-only
    STATUS      current
    DESCRIPTION
        "Enable of LACP state machine" 
    ::=  { opticalIfConfigCapEntry 13 }

opticalIfConfigCapTxOffDelay OBJECT-TYPE
    SYNTAX      FspR7EnableDisableCaps
    MAX-ACCESS  read-only
    STATUS      current
    DESCRIPTION
        "Enable or disable TXOFFHOLD Period for Error Forwarding and LKDO-OFF Consequent Action." 
    ::=  { opticalIfConfigCapEntry 14 }

opticalIfConfigCapOpuPayloadType OBJECT-TYPE
    SYNTAX      FspR7OpuPayloadTypeCaps
    MAX-ACCESS  read-only
    STATUS      current
    DESCRIPTION
        "OPU Payload Type Indicator" 
    ::=  { opticalIfConfigCapEntry 15 }

opticalIfConfigCapOpticalSetPoint OBJECT-TYPE
    SYNTAX      FspR7Integer32Caps
    UNITS       "0.1 dBm"
    MAX-ACCESS  read-only
    STATUS      current
    DESCRIPTION   ""
    ::=  { opticalIfConfigCapEntry 16 }

opticalIfConfigCapTransmitChannel OBJECT-TYPE
    SYNTAX      FspR7ChannelIdentifierCaps
    MAX-ACCESS  read-only
    STATUS      current
    DESCRIPTION
        "Channel" 
    ::=  { opticalIfConfigCapEntry 17 }

opticalIfConfigCapFiberBrand OBJECT-TYPE
    SYNTAX      FspR7FiberBrandCaps
    MAX-ACCESS  read-only
    STATUS      current
    DESCRIPTION
        "Brand of fiber present in the fiber plant" 
    ::=  { opticalIfConfigCapEntry 18 }

opticalIfConfigCapTiltSet OBJECT-TYPE
    SYNTAX      FspR7TiltSetCaps
    MAX-ACCESS  read-only
    STATUS      current
    DESCRIPTION
        "Tilt setting as discrete values versus a range" 
    ::=  { opticalIfConfigCapEntry 19 }

opticalIfConfigCapForceFwdAsePilotOn OBJECT-TYPE
    SYNTAX      FspR7LaserForcedOperationCaps
    MAX-ACCESS  read-only
    STATUS      current
    DESCRIPTION
        "Force the BWD Raman pilot on to allow building of FWD Raman ASE Table" 
    ::=  { opticalIfConfigCapEntry 20 }

opticalIfConfigCapXfpDecisionThres OBJECT-TYPE
    SYNTAX      FspR7XfpDecisionThresCaps
    MAX-ACCESS  read-only
    STATUS      current
    DESCRIPTION
        "XFP Decision threshold setting" 
    ::=  { opticalIfConfigCapEntry 21 }

opticalIfConfigCapPrbsPmReset OBJECT-TYPE
    SYNTAX      FspR7PrbsPmResetCaps
    MAX-ACCESS  read-only
    STATUS      current
    DESCRIPTION
        "Reset PRBS PM counters" 
    ::=  { opticalIfConfigCapEntry 22 }

opticalIfConfigCapTestPrbsRcvMode OBJECT-TYPE
    SYNTAX      FspR7TestModeCaps
    MAX-ACCESS  read-only
    STATUS      current
    DESCRIPTION
        "PRBS test pattern received" 
    ::=  { opticalIfConfigCapEntry 23 }

opticalIfConfigCapTestPrbsTrmtMode OBJECT-TYPE
    SYNTAX      FspR7TestModeCaps
    MAX-ACCESS  read-only
    STATUS      current
    DESCRIPTION
        "PRBS test pattern transmitted" 
    ::=  { opticalIfConfigCapEntry 24 }

opticalIfConfigCapTributarySlotMethod OBJECT-TYPE
    SYNTAX      FspR7ManualAutoCaps
    MAX-ACCESS  read-only
    STATUS      current
    DESCRIPTION
        "Tributary Slot assignment method" 
    ::=  { opticalIfConfigCapEntry 25 }

opticalIfConfigCapOffset OBJECT-TYPE
    SYNTAX      FspR7Integer32Caps
    UNITS       "0.1 dB"
    MAX-ACCESS  read-only
    STATUS      current
    DESCRIPTION
        "Sets the offset for the mean optical power for power equalization in ROADM" 
    ::=  { opticalIfConfigCapEntry 26 }

opticalIfConfigCapTilt OBJECT-TYPE
    SYNTAX      FspR7Integer32Caps
    UNITS       "0.1 dB"
    MAX-ACCESS  read-only
    STATUS      current
    DESCRIPTION
        "Change of optical channel power in dB over the complete transmission band" 
    ::=  { opticalIfConfigCapEntry 27 }

opticalIfConfigCapLaserDelayTimer OBJECT-TYPE
    SYNTAX      FspR7LaserDelayTimerCaps
    MAX-ACCESS  read-only
    STATUS      current
    DESCRIPTION
        "Relevant only when ERRFWD=LSROFF. Enables/disables the
         possibility to delay turning off and on the laser.
         This applies to the case when turning off the laser
         is done as an error forwarding mechanism." 
    ::=  { opticalIfConfigCapEntry 28 }

opticalIfConfigCapLaserOffTimer OBJECT-TYPE
    SYNTAX      FspR7Unsigned32Caps
    UNITS       "ms"
    MAX-ACCESS  read-only
    STATUS      current
    DESCRIPTION
        "Delay before laser is swiched off" 
    ::=  { opticalIfConfigCapEntry 29 }

opticalIfConfigCapLaserOnTimer OBJECT-TYPE
    SYNTAX      FspR7Unsigned32Caps
    UNITS       "ms"
    MAX-ACCESS  read-only
    STATUS      current
    DESCRIPTION
        "Delay before laser is switched on" 
    ::=  { opticalIfConfigCapEntry 30 }

opticalIfConfigCapLaneChannelSetting OBJECT-TYPE
    SYNTAX      FspR7ChannelIdentifierCaps
    MAX-ACCESS  read-only
    STATUS      current
    DESCRIPTION
        "Lane Channel Setting" 
    ::=  { opticalIfConfigCapEntry 31 }

opticalIfConfigCapBip OBJECT-TYPE
    SYNTAX      FspR7BipCaps
    MAX-ACCESS  read-only
    STATUS      current
    DESCRIPTION
        "Bit Interleaved Parity" 
    ::=  { opticalIfConfigCapEntry 32 }

opticalIfConfigCapCodeGain OBJECT-TYPE
    SYNTAX      FspR7CodeGainCaps
    MAX-ACCESS  read-only
    STATUS      current
    DESCRIPTION
        "Forward Error Correction Coding gain" 
    ::=  { opticalIfConfigCapEntry 33 }

eroadmIfDiagnosticsTable OBJECT-TYPE
    SYNTAX      SEQUENCE OF EroadmIfDiagnosticsEntry
    MAX-ACCESS  not-accessible
    STATUS      current
    DESCRIPTION   ""
    ::=  { interfaceConfigAndStatus 23 }

eroadmIfDiagnosticsEntry OBJECT-TYPE
    SYNTAX      EroadmIfDiagnosticsEntry
    MAX-ACCESS  not-accessible
    STATUS      current
    DESCRIPTION   ""
    INDEX       {
                  entityIndex
                }
    ::=  { eroadmIfDiagnosticsTable 1 }

EroadmIfDiagnosticsEntry ::=  SEQUENCE
  { eroadmIfDiagnosticsAttenuationVoa Unsigned32,
    eroadmIfDiagnosticsOutputPower Integer32 }

eroadmIfDiagnosticsAttenuationVoa OBJECT-TYPE
    SYNTAX      Unsigned32 
    UNITS       "0.1 dB"
    MAX-ACCESS  read-only
    STATUS      current
    DESCRIPTION
        "Variable Attenuator attenuation in dB" 
    ::=  { eroadmIfDiagnosticsEntry 1 }

eroadmIfDiagnosticsOutputPower OBJECT-TYPE
    SYNTAX      Integer32 
    UNITS       "0.1 dBm"
    MAX-ACCESS  read-only
    STATUS      current
    DESCRIPTION   "The optical output power of a transmitter in dBm,
         measured in the range of -x to +y dBm.(TBD)
         It is only valid when there the laserState is 'On'.
         If not, a value of -65535 is returned.
         A value of -65535 also indicates that OOP is not available.
         When out of range, -65534 indicates that the OOP is outside
         the maximum value and -65533 for outside the minimum value."
    ::=  { eroadmIfDiagnosticsEntry 2 }

tifiConfigTable OBJECT-TYPE
    SYNTAX      SEQUENCE OF TifiConfigEntry
    MAX-ACCESS  not-accessible
    STATUS      current
    DESCRIPTION   ""
    ::=  { interfaceConfigAndStatus 24 }

tifiConfigEntry OBJECT-TYPE
    SYNTAX      TifiConfigEntry
    MAX-ACCESS  not-accessible
    STATUS      current
    DESCRIPTION   ""
    INDEX       {
                  entityIndex
                }
    ::=  { tifiConfigTable 1 }

TifiConfigEntry ::=  SEQUENCE
  { tifiConfigInvertTifInputLogic FspR7InvertTelemetryInputLogic,
    tifiConfigTifAlarmType SnmpAdminString,
    tifiConfigTifAlarmMessage SnmpAdminString }

tifiConfigInvertTifInputLogic OBJECT-TYPE
    SYNTAX      FspR7InvertTelemetryInputLogic
    MAX-ACCESS  read-write
    STATUS      current
    DESCRIPTION
        "Change telemetry interface input logic" 
    ::=  { tifiConfigEntry 1 }

tifiConfigTifAlarmType OBJECT-TYPE
    SYNTAX      SnmpAdminString
    MAX-ACCESS  read-write
    STATUS      current
    DESCRIPTION
        "Telemetry interface alarm type" 
    ::=  { tifiConfigEntry 2 }

tifiConfigTifAlarmMessage OBJECT-TYPE
    SYNTAX      SnmpAdminString
    MAX-ACCESS  read-write
    STATUS      current
    DESCRIPTION
        "Telemetry interface alarm message" 
    ::=  { tifiConfigEntry 3 }

tifiDataTable OBJECT-TYPE
    SYNTAX      SEQUENCE OF TifiDataEntry
    MAX-ACCESS  not-accessible
    STATUS      current
    DESCRIPTION   ""
    ::=  { interfaceConfigAndStatus 25 }

tifiDataEntry OBJECT-TYPE
    SYNTAX      TifiDataEntry
    MAX-ACCESS  not-accessible
    STATUS      current
    DESCRIPTION   ""
    INDEX       {
                  entityIndex
                }
    ::=  { tifiDataTable 1 }

TifiDataEntry ::=  SEQUENCE
  { tifiDataTifAlarmType SnmpAdminString,
    tifiDataTifAlarmMessage SnmpAdminString }

tifiDataTifAlarmType OBJECT-TYPE
    SYNTAX      SnmpAdminString
    MAX-ACCESS  read-only
    STATUS      current
    DESCRIPTION
        "Telemetry interface alarm type" 
    ::=  { tifiDataEntry 1 }

tifiDataTifAlarmMessage OBJECT-TYPE
    SYNTAX      SnmpAdminString
    MAX-ACCESS  read-only
    STATUS      current
    DESCRIPTION
        "Telemetry interface alarm message" 
    ::=  { tifiDataEntry 2 }

tifoDataTable OBJECT-TYPE
    SYNTAX      SEQUENCE OF TifoDataEntry
    MAX-ACCESS  not-accessible
    STATUS      current
    DESCRIPTION   ""
    ::=  { interfaceConfigAndStatus 26 }

tifoDataEntry OBJECT-TYPE
    SYNTAX      TifoDataEntry
    MAX-ACCESS  not-accessible
    STATUS      current
    DESCRIPTION   ""
    INDEX       {
                  entityIndex
                }
    ::=  { tifoDataTable 1 }

TifoDataEntry ::=  SEQUENCE
  { tifoDataTelemetry FspR7TelemetryOutput }

tifoDataTelemetry OBJECT-TYPE
    SYNTAX      FspR7TelemetryOutput
    MAX-ACCESS  read-only
    STATUS      current
    DESCRIPTION
        "Telemetry interface output provision" 
    ::=  { tifoDataEntry 1 }

tifoConfigTable OBJECT-TYPE
    SYNTAX      SEQUENCE OF TifoConfigEntry
    MAX-ACCESS  not-accessible
    STATUS      current
    DESCRIPTION   ""
    ::=  { interfaceConfigAndStatus 27 }

tifoConfigEntry OBJECT-TYPE
    SYNTAX      TifoConfigEntry
    MAX-ACCESS  not-accessible
    STATUS      current
    DESCRIPTION   ""
    INDEX       {
                  entityIndex
                }
    ::=  { tifoConfigTable 1 }

TifoConfigEntry ::=  SEQUENCE
  { tifoConfigTelemetry FspR7TelemetryOutput }

tifoConfigTelemetry OBJECT-TYPE
    SYNTAX      FspR7TelemetryOutput
    MAX-ACCESS  read-write
    STATUS      current
    DESCRIPTION
        "Telemetry interface output provision" 
    ::=  { tifoConfigEntry 1 }

opticalLinkConfigTable OBJECT-TYPE
    SYNTAX      SEQUENCE OF OpticalLinkConfigEntry
    MAX-ACCESS  not-accessible
    STATUS      current
    DESCRIPTION   ""
    ::=  { interfaceConfigAndStatus 28 }

opticalLinkConfigEntry OBJECT-TYPE
    SYNTAX      OpticalLinkConfigEntry
    MAX-ACCESS  not-accessible
    STATUS      current
    DESCRIPTION   ""
    INDEX       {
                  entityIndex
                }
    ::=  { opticalLinkConfigTable 1 }

OpticalLinkConfigEntry ::=  SEQUENCE
  { opticalLinkConfigTxLineAttenuation Integer32,
    opticalLinkConfigRxLineAttenuation Integer32,
    opticalLinkConfigFarEndLocation SnmpAdminString }

opticalLinkConfigTxLineAttenuation OBJECT-TYPE
    SYNTAX      Integer32 
    UNITS       "0.1 dB"
    MAX-ACCESS  read-write
    STATUS      current
    DESCRIPTION   "The Attenuation (in 0.1 dB) on line connected to
         transmitter of this interface. If there is loss of signal
         then line attenuation is -65535. The value -255 will be
         returned if the value isn't available."
    ::=  { opticalLinkConfigEntry 1 }

opticalLinkConfigRxLineAttenuation OBJECT-TYPE
    SYNTAX      Integer32 
    UNITS       "0.1 dB"
    MAX-ACCESS  read-write
    STATUS      current
    DESCRIPTION   "The Attenuation (in 0.1 dB) on line connected to receiver
         of this interface. If there is loss of signal then ine
         attenuation is -65535. The value -255 will be returned if
         the value isn't available."
    ::=  { opticalLinkConfigEntry 2 }

opticalLinkConfigFarEndLocation OBJECT-TYPE
    SYNTAX      SnmpAdminString
    MAX-ACCESS  read-write
    STATUS      current
    DESCRIPTION   ""
    ::=  { opticalLinkConfigEntry 3 }

opticalLinkDataTable OBJECT-TYPE
    SYNTAX      SEQUENCE OF OpticalLinkDataEntry
    MAX-ACCESS  not-accessible
    STATUS      current
    DESCRIPTION   ""
    ::=  { interfaceConfigAndStatus 29 }

opticalLinkDataEntry OBJECT-TYPE
    SYNTAX      OpticalLinkDataEntry
    MAX-ACCESS  not-accessible
    STATUS      current
    DESCRIPTION   ""
    INDEX       {
                  entityIndex
                }
    ::=  { opticalLinkDataTable 1 }

OpticalLinkDataEntry ::=  SEQUENCE
  { opticalLinkDataLogicalInterfaceAid EntityIndex }

opticalLinkDataLogicalInterfaceAid OBJECT-TYPE
    SYNTAX      EntityIndex
    MAX-ACCESS  read-only
    STATUS      current
    DESCRIPTION
        "Logical Interface AID" 
    ::=  { opticalLinkDataEntry 1 }

virtualOpticalChannelConfigTable OBJECT-TYPE
    SYNTAX      SEQUENCE OF VirtualOpticalChannelConfigEntry
    MAX-ACCESS  not-accessible
    STATUS      current
    DESCRIPTION   ""
    ::=  { interfaceConfigAndStatus 30 }

virtualOpticalChannelConfigEntry OBJECT-TYPE
    SYNTAX      VirtualOpticalChannelConfigEntry
    MAX-ACCESS  not-accessible
    STATUS      current
    DESCRIPTION   ""
    INDEX       {
                  entityIndex
                }
    ::=  { virtualOpticalChannelConfigTable 1 }

VirtualOpticalChannelConfigEntry ::=  SEQUENCE
  { virtualOpticalChannelConfigAlias SnmpAdminString }

virtualOpticalChannelConfigAlias OBJECT-TYPE
    SYNTAX      SnmpAdminString
    MAX-ACCESS  read-write
    STATUS      current
    DESCRIPTION
        "User Applied Descriptor" 
    ::=  { virtualOpticalChannelConfigEntry 1 }

virtualOpticalChannelDataTable OBJECT-TYPE
    SYNTAX      SEQUENCE OF VirtualOpticalChannelDataEntry
    MAX-ACCESS  not-accessible
    STATUS      current
    DESCRIPTION   ""
    ::=  { interfaceConfigAndStatus 31 }

virtualOpticalChannelDataEntry OBJECT-TYPE
    SYNTAX      VirtualOpticalChannelDataEntry
    MAX-ACCESS  not-accessible
    STATUS      current
    DESCRIPTION   ""
    INDEX       {
                  entityIndex
                }
    ::=  { virtualOpticalChannelDataTable 1 }

VirtualOpticalChannelDataEntry ::=  SEQUENCE
  { virtualOpticalChannelDataTransmitWavelength Unsigned32,
    virtualOpticalChannelDataTransmitFrequency Unsigned32,
    virtualOpticalChannelDataTransmitChannel FspR7ChannelIdentifier,
    virtualOpticalChannelDataConnectState FspR7ConnectState,
    virtualOpticalChannelDataOwnerAid EntityIndex }

virtualOpticalChannelDataTransmitWavelength OBJECT-TYPE
    SYNTAX      Unsigned32 
    UNITS       "0.01 nm"
    MAX-ACCESS  read-only
    STATUS      current
    DESCRIPTION
        "Wavelength of Optical Interface (unit: nm)" 
    ::=  { virtualOpticalChannelDataEntry 1 }

virtualOpticalChannelDataTransmitFrequency OBJECT-TYPE
    SYNTAX      Unsigned32 
    UNITS       "0.01 THz"
    MAX-ACCESS  read-only
    STATUS      current
    DESCRIPTION
        "Frequency of Optical Interface (unit: nm)" 
    ::=  { virtualOpticalChannelDataEntry 2 }

virtualOpticalChannelDataTransmitChannel OBJECT-TYPE
    SYNTAX      FspR7ChannelIdentifier
    MAX-ACCESS  read-only
    STATUS      current
    DESCRIPTION
        "Channel" 
    ::=  { virtualOpticalChannelDataEntry 3 }

virtualOpticalChannelDataConnectState OBJECT-TYPE
    SYNTAX      FspR7ConnectState
    MAX-ACCESS  read-only
    STATUS      current
    DESCRIPTION
        "Connection State" 
    ::=  { virtualOpticalChannelDataEntry 4 }

virtualOpticalChannelDataOwnerAid OBJECT-TYPE
    SYNTAX      EntityIndex
    MAX-ACCESS  read-only
    STATUS      current
    DESCRIPTION
        "Channel Group which is the parent (owner) of the channel" 
    ::=  { virtualOpticalChannelDataEntry 5 }

logicalIfConfigTable OBJECT-TYPE
    SYNTAX      SEQUENCE OF LogicalIfConfigEntry
    MAX-ACCESS  not-accessible
    STATUS      current
    DESCRIPTION   ""
    ::=  { interfaceConfigAndStatus 32 }

logicalIfConfigEntry OBJECT-TYPE
    SYNTAX      LogicalIfConfigEntry
    MAX-ACCESS  not-accessible
    STATUS      current
    DESCRIPTION   ""
    INDEX       {
                  entityIndex
                }
    ::=  { logicalIfConfigTable 1 }

LogicalIfConfigEntry ::=  SEQUENCE
  { logicalIfConfigAlias SnmpAdminString,
    logicalIfConfigAreaId IpAddress,
    logicalIfConfigMetric Unsigned32,
    logicalIfConfigHelloInterval Unsigned32,
    logicalIfConfigDeadInterval Unsigned32,
    logicalIfConfigPrio Unsigned32,
    logicalIfConfigRetransmitInterval Unsigned32,
    logicalIfConfigAuthType FspR7CpAuthType,
    logicalIfConfigAuthString SnmpAdminString,
    logicalIfConfigOspf FspR7OspfMode,
    logicalIfConfigPushedNearEndIpHeader IpAddress,
    logicalIfConfigPushedFarEndIpHeader IpAddress,
    logicalIfConfigTimeToLive Unsigned32 }

logicalIfConfigAlias OBJECT-TYPE
    SYNTAX      SnmpAdminString
    MAX-ACCESS  read-write
    STATUS      current
    DESCRIPTION   "Alias."
    ::=  { logicalIfConfigEntry 1 }

logicalIfConfigAreaId OBJECT-TYPE
    SYNTAX      IpAddress
    MAX-ACCESS  read-write
    STATUS      current
    DESCRIPTION
        "OSPF Area ID for IP Interface" 
    ::=  { logicalIfConfigEntry 2 }

logicalIfConfigMetric OBJECT-TYPE
    SYNTAX      Unsigned32 (0..65535 | 4294967295)
    MAX-ACCESS  read-write
    STATUS      current
    DESCRIPTION
        "Routing Metric" 
    ::=  { logicalIfConfigEntry 3 }

logicalIfConfigHelloInterval OBJECT-TYPE
    SYNTAX      Unsigned32 (1..65535 | 4294967295) 
    UNITS       "s"
    MAX-ACCESS  read-write
    STATUS      current
    DESCRIPTION
        "Hello Interval" 
    ::=  { logicalIfConfigEntry 4 }

logicalIfConfigDeadInterval OBJECT-TYPE
    SYNTAX      Unsigned32 (1..65535 | 4294967295) 
    UNITS       "s"
    MAX-ACCESS  read-write
    STATUS      current
    DESCRIPTION
        "Dead Interval" 
    ::=  { logicalIfConfigEntry 5 }

logicalIfConfigPrio OBJECT-TYPE
    SYNTAX      Unsigned32 (0..255 | 4294967295)
    MAX-ACCESS  read-write
    STATUS      current
    DESCRIPTION
        "Priority" 
    ::=  { logicalIfConfigEntry 6 }

logicalIfConfigRetransmitInterval OBJECT-TYPE
    SYNTAX      Unsigned32 (0..3600 | 4294967295) 
    UNITS       "s"
    MAX-ACCESS  read-write
    STATUS      current
    DESCRIPTION
        "Retransmit Interval" 
    ::=  { logicalIfConfigEntry 7 }

logicalIfConfigAuthType OBJECT-TYPE
    SYNTAX      FspR7CpAuthType
    MAX-ACCESS  read-write
    STATUS      current
    DESCRIPTION
        "OSPF Authentication Type" 
    ::=  { logicalIfConfigEntry 8 }

logicalIfConfigAuthString OBJECT-TYPE
    SYNTAX      SnmpAdminString
    MAX-ACCESS  read-write
    STATUS      current
    DESCRIPTION
        "OSPF Authentication Key/String depending on Authentication Type" 
    ::=  { logicalIfConfigEntry 9 }

logicalIfConfigOspf OBJECT-TYPE
    SYNTAX      FspR7OspfMode
    MAX-ACCESS  read-write
    STATUS      current
    DESCRIPTION
        "OSPF Routing (Dynamic)" 
    ::=  { logicalIfConfigEntry 10 }

logicalIfConfigPushedNearEndIpHeader OBJECT-TYPE
    SYNTAX      IpAddress
    MAX-ACCESS  read-write
    STATUS      current
    DESCRIPTION
        "Pushed Near End IP address in encapsulating header" 
    ::=  { logicalIfConfigEntry 11 }

logicalIfConfigPushedFarEndIpHeader OBJECT-TYPE
    SYNTAX      IpAddress
    MAX-ACCESS  read-write
    STATUS      current
    DESCRIPTION
        "Pushed Far End IP address in encapsulating header" 
    ::=  { logicalIfConfigEntry 12 }

logicalIfConfigTimeToLive OBJECT-TYPE
    SYNTAX      Unsigned32 (1..255 | 4294967295)
    MAX-ACCESS  read-write
    STATUS      current
    DESCRIPTION
        "Time to Live" 
    ::=  { logicalIfConfigEntry 13 }

logicalIfDataTable OBJECT-TYPE
    SYNTAX      SEQUENCE OF LogicalIfDataEntry
    MAX-ACCESS  not-accessible
    STATUS      current
    DESCRIPTION   ""
    ::=  { interfaceConfigAndStatus 33 }

logicalIfDataEntry OBJECT-TYPE
    SYNTAX      LogicalIfDataEntry
    MAX-ACCESS  not-accessible
    STATUS      current
    DESCRIPTION   ""
    INDEX       {
                  entityIndex
                }
    ::=  { logicalIfDataTable 1 }

LogicalIfDataEntry ::=  SEQUENCE
  { logicalIfDataFacilityType FspR7InterfaceType,
    logicalIfDataLanLinkAid EntityIndex,
    logicalIfDataLogicalInterfaceId Unsigned32,
    logicalIfDataOspf FspR7OspfMode,
    logicalIfDataDcnAid EntityIndex,
    logicalIfDataLanLinkAidDerived EntityIndex,
    logicalIfDataIpType FspR7IpType,
    logicalIfDataIpAddr IpAddress,
    logicalIfDataIpAddrMonitor IpAddress,
    logicalIfDataIpMask IpAddress,
    logicalIfDataIpMaskMonitor IpAddress,
    logicalIfDataEncapsulation FspR7CpEncapsulation,
    logicalIfDataIPv6 SnmpAdminString,
    logicalIfDataIPv6PrefixLen Unsigned32,
    logicalIfDataIPv6LinkLocal SnmpAdminString,
    logicalIfDataIpMode FspR7IpMode,
    logicalIfDataMtu Unsigned32 }

logicalIfDataFacilityType OBJECT-TYPE
    SYNTAX      FspR7InterfaceType
    MAX-ACCESS  read-only
    STATUS      current
    DESCRIPTION   "Facility Type."
    ::=  { logicalIfDataEntry 1 }

logicalIfDataLanLinkAid OBJECT-TYPE
    SYNTAX      EntityIndex
    MAX-ACCESS  read-only
    STATUS      current
    DESCRIPTION   "Sup. DCN Facility AID."
    ::=  { logicalIfDataEntry 2 }

logicalIfDataLogicalInterfaceId OBJECT-TYPE
    SYNTAX      Unsigned32
    MAX-ACCESS  read-only
    STATUS      current
    DESCRIPTION   "Logical InterfaceId."
    ::=  { logicalIfDataEntry 3 }

logicalIfDataOspf OBJECT-TYPE
    SYNTAX      FspR7OspfMode
    MAX-ACCESS  read-only
    STATUS      current
    DESCRIPTION
        "OSPF Routing (Dynamic)" 
    ::=  { logicalIfDataEntry 4 }

logicalIfDataDcnAid OBJECT-TYPE
    SYNTAX      EntityIndex
    MAX-ACCESS  read-only
    STATUS      current
    DESCRIPTION   "Sup. DCN Facility AID."
    ::=  { logicalIfDataEntry 5 }

logicalIfDataLanLinkAidDerived OBJECT-TYPE
    SYNTAX      EntityIndex
    MAX-ACCESS  read-only
    STATUS      current
    DESCRIPTION   "Sup. DCN Facility AID."
    ::=  { logicalIfDataEntry 6 }

logicalIfDataIpType OBJECT-TYPE
    SYNTAX      FspR7IpType
    MAX-ACCESS  read-only
    STATUS      current
    DESCRIPTION
        "Type of IP configuration" 
    ::=  { logicalIfDataEntry 7 }

logicalIfDataIpAddr OBJECT-TYPE
    SYNTAX      IpAddress
    MAX-ACCESS  read-only
    STATUS      current
    DESCRIPTION
        "IP Address assigned to LAN IP Interface" 
    ::=  { logicalIfDataEntry 8 }

logicalIfDataIpAddrMonitor OBJECT-TYPE
    SYNTAX      IpAddress
    MAX-ACCESS  read-only
    STATUS      current
    DESCRIPTION
        "IP address assigned to LAN IP Interface" 
    ::=  { logicalIfDataEntry 9 }

logicalIfDataIpMask OBJECT-TYPE
    SYNTAX      IpAddress
    MAX-ACCESS  read-only
    STATUS      current
    DESCRIPTION
        "IP MASK assigned to LAN IP Interface" 
    ::=  { logicalIfDataEntry 10 }

logicalIfDataIpMaskMonitor OBJECT-TYPE
    SYNTAX      IpAddress
    MAX-ACCESS  read-only
    STATUS      current
    DESCRIPTION
        "IP mask assigned to LAN IP Interface" 
    ::=  { logicalIfDataEntry 11 }

logicalIfDataEncapsulation OBJECT-TYPE
    SYNTAX      FspR7CpEncapsulation
    MAX-ACCESS  read-only
    STATUS      current
    DESCRIPTION
        "Encapsulation" 
    ::=  { logicalIfDataEntry 12 }

logicalIfDataIPv6 OBJECT-TYPE
    SYNTAX      SnmpAdminString
    MAX-ACCESS  read-only
    STATUS      current
    DESCRIPTION
        "IPv6 Address" 
    ::=  { logicalIfDataEntry 13 }

logicalIfDataIPv6PrefixLen OBJECT-TYPE
    SYNTAX      Unsigned32 (0..128 | 4294967295)
    MAX-ACCESS  read-only
    STATUS      current
    DESCRIPTION
        "IPv6 Subnet Prefix Length" 
    ::=  { logicalIfDataEntry 14 }

logicalIfDataIPv6LinkLocal OBJECT-TYPE
    SYNTAX      SnmpAdminString
    MAX-ACCESS  read-only
    STATUS      current
    DESCRIPTION
        "IPv6 Link Local Address. This address is derived from MAC" 
    ::=  { logicalIfDataEntry 15 }

logicalIfDataIpMode OBJECT-TYPE
    SYNTAX      FspR7IpMode
    MAX-ACCESS  read-only
    STATUS      current
    DESCRIPTION
        "IP Mode of Operation either IPv4 only or IPv4 and IPv6. When operation supports IPv6, it is used for addresses external to the network." 
    ::=  { logicalIfDataEntry 16 }

logicalIfDataMtu OBJECT-TYPE
    SYNTAX      Unsigned32 (1280..1500 | 4294967295) 
    UNITS       "Byte"
    MAX-ACCESS  read-only
    STATUS      current
    DESCRIPTION
        "Maximum Transmission Unit" 
    ::=  { logicalIfDataEntry 17 }

ptpEntityDataTable OBJECT-TYPE
    SYNTAX      SEQUENCE OF PtpEntityDataEntry
    MAX-ACCESS  not-accessible
    STATUS      current
    DESCRIPTION   ""
    ::=  { interfaceConfigAndStatus 34 }

ptpEntityDataEntry OBJECT-TYPE
    SYNTAX      PtpEntityDataEntry
    MAX-ACCESS  not-accessible
    STATUS      current
    DESCRIPTION   ""
    INDEX       {
                  ptpEntityIndex
                }
    ::=  { ptpEntityDataTable 1 }

PtpEntityDataEntry ::=  SEQUENCE
  { ptpEntityDataConnEqptState FspR7ConnectState,
    ptpEntityDataChannelProvision FspR7ChannelIdentifier,
    ptpEntityDataLambda Unsigned32,
    ptpEntityDataFrequency Unsigned32,
    ptpEntityDataReach FspR7OpticalInterfaceReach,
    ptpEntityDataBandProvision FspR7OpticalBand,
    ptpEntityDataSubBandProvision FspR7OpticalSubBand,
    ptpEntityDataGroupProvision FspR7OpticalGroup,
    ptpEntityDataSfProvision FspR7SingleFiberLocation,
    ptpEntityDataConnector FspR7ConnectorType,
    ptpEntityDataFiber FspR7OpticalFiberType,
    ptpEntityDataDirection ApsDirection,
    ptpEntityDataLevel FspR7OpticalMultiplexLevel,
    ptpEntityDataFunction FspR7InterfaceFunction,
    ptpEntityDataPartnerAid EntityIndex,
    ptpEntityDataTerminationType FspR7EquipmentType,
    ptpEntityDataValidSignalTimer Unsigned32,
    ptpEntityDataConnectionType FspR7TypeConnection,
    ptpEntityDataOutputPower Integer32,
    ptpEntityDataInputPower Integer32,
    ptpEntityDataFiberConnAttenuation Integer32,
    ptpEntityDataFiberDetectStatus FspR7FDStatusCaps }

ptpEntityDataConnEqptState OBJECT-TYPE
    SYNTAX      FspR7ConnectState
    MAX-ACCESS  read-only
    STATUS      current
    DESCRIPTION   ""
    ::=  { ptpEntityDataEntry 1 }

ptpEntityDataChannelProvision OBJECT-TYPE
    SYNTAX      FspR7ChannelIdentifier
    MAX-ACCESS  read-only
    STATUS      current
    DESCRIPTION   ""
    ::=  { ptpEntityDataEntry 2 }

ptpEntityDataLambda OBJECT-TYPE
    SYNTAX      Unsigned32 
    UNITS       "0.01 nm"
    MAX-ACCESS  read-only
    STATUS      current
    DESCRIPTION   ""
    ::=  { ptpEntityDataEntry 3 }

ptpEntityDataFrequency OBJECT-TYPE
    SYNTAX      Unsigned32 
    UNITS       "0.01 THz"
    MAX-ACCESS  read-only
    STATUS      current
    DESCRIPTION   ""
    ::=  { ptpEntityDataEntry 4 }

ptpEntityDataReach OBJECT-TYPE
    SYNTAX      FspR7OpticalInterfaceReach
    MAX-ACCESS  read-only
    STATUS      current
    DESCRIPTION   ""
    ::=  { ptpEntityDataEntry 5 }

ptpEntityDataBandProvision OBJECT-TYPE
    SYNTAX      FspR7OpticalBand
    MAX-ACCESS  read-only
    STATUS      current
    DESCRIPTION   ""
    ::=  { ptpEntityDataEntry 6 }

ptpEntityDataSubBandProvision OBJECT-TYPE
    SYNTAX      FspR7OpticalSubBand
    MAX-ACCESS  read-only
    STATUS      current
    DESCRIPTION   ""
    ::=  { ptpEntityDataEntry 7 }

ptpEntityDataGroupProvision OBJECT-TYPE
    SYNTAX      FspR7OpticalGroup
    MAX-ACCESS  read-only
    STATUS      current
    DESCRIPTION   ""
    ::=  { ptpEntityDataEntry 8 }

ptpEntityDataSfProvision OBJECT-TYPE
    SYNTAX      FspR7SingleFiberLocation
    MAX-ACCESS  read-only
    STATUS      current
    DESCRIPTION   ""
    ::=  { ptpEntityDataEntry 9 }

ptpEntityDataConnector OBJECT-TYPE
    SYNTAX      FspR7ConnectorType
    MAX-ACCESS  read-only
    STATUS      current
    DESCRIPTION   ""
    ::=  { ptpEntityDataEntry 10 }

ptpEntityDataFiber OBJECT-TYPE
    SYNTAX      FspR7OpticalFiberType
    MAX-ACCESS  read-only
    STATUS      current
    DESCRIPTION   ""
    ::=  { ptpEntityDataEntry 11 }

ptpEntityDataDirection OBJECT-TYPE
    SYNTAX      ApsDirection
    MAX-ACCESS  read-only
    STATUS      current
    DESCRIPTION   ""
    ::=  { ptpEntityDataEntry 12 }

ptpEntityDataLevel OBJECT-TYPE
    SYNTAX      FspR7OpticalMultiplexLevel
    MAX-ACCESS  read-only
    STATUS      current
    DESCRIPTION   ""
    ::=  { ptpEntityDataEntry 13 }

ptpEntityDataFunction OBJECT-TYPE
    SYNTAX      FspR7InterfaceFunction
    MAX-ACCESS  read-only
    STATUS      current
    DESCRIPTION   ""
    ::=  { ptpEntityDataEntry 14 }

ptpEntityDataPartnerAid OBJECT-TYPE
    SYNTAX      EntityIndex
    MAX-ACCESS  read-only
    STATUS      current
    DESCRIPTION   ""
    ::=  { ptpEntityDataEntry 15 }

ptpEntityDataTerminationType OBJECT-TYPE
    SYNTAX      FspR7EquipmentType
    MAX-ACCESS  read-only
    STATUS      current
    DESCRIPTION
        "Type of Physical Termination" 
    ::=  { ptpEntityDataEntry 16 }

ptpEntityDataValidSignalTimer OBJECT-TYPE
    SYNTAX      Unsigned32 (0..5760 | 4294967295) 
    UNITS       "min"
    MAX-ACCESS  read-only
    STATUS      current
    DESCRIPTION
        "AINS state signal quality soak time remaining until transition to IS." 
    ::=  { ptpEntityDataEntry 17 }

ptpEntityDataConnectionType OBJECT-TYPE
    SYNTAX      FspR7TypeConnection
    MAX-ACCESS  read-only
    STATUS      current
    DESCRIPTION
        "Connectivity Parameters for Facilities" 
    ::=  { ptpEntityDataEntry 18 }

ptpEntityDataOutputPower OBJECT-TYPE
    SYNTAX      Integer32 
    UNITS       "0.1 dBm"
    MAX-ACCESS  read-only
    STATUS      current
    DESCRIPTION
        "Instantaneous Optical Power Transmitted (Output)" 
    ::=  { ptpEntityDataEntry 19 }

ptpEntityDataInputPower OBJECT-TYPE
    SYNTAX      Integer32 
    UNITS       "0.1 dBm"
    MAX-ACCESS  read-only
    STATUS      current
    DESCRIPTION
        "Total Optical Input Power Received" 
    ::=  { ptpEntityDataEntry 20 }

ptpEntityDataFiberConnAttenuation OBJECT-TYPE
    SYNTAX      Integer32 
    UNITS       "0.1 dB"
    MAX-ACCESS  read-only
    STATUS      current
    DESCRIPTION
        "Fiber Connection Attenuation" 
    ::=  { ptpEntityDataEntry 21 }

ptpEntityDataFiberDetectStatus OBJECT-TYPE
    SYNTAX      FspR7FDStatusCaps
    MAX-ACCESS  read-only
    STATUS      current
    DESCRIPTION
        "Fiber Detect Status" 
    ::=  { ptpEntityDataEntry 22 }

farEndIfDiagnosticsTable OBJECT-TYPE
    SYNTAX      SEQUENCE OF FarEndIfDiagnosticsEntry
    MAX-ACCESS  not-accessible
    STATUS      current
    DESCRIPTION   "Contains diagnostic entries for optical interfaces. This
         table extends the entries in the ifTable (RFC 2863)."
    ::=  { interfaceConfigAndStatus 35 }

farEndIfDiagnosticsEntry OBJECT-TYPE
    SYNTAX      FarEndIfDiagnosticsEntry
    MAX-ACCESS  not-accessible
    STATUS      current
    DESCRIPTION   ""
    INDEX       {
                  entityIndex
                }
    ::=  { farEndIfDiagnosticsTable 1 }

FarEndIfDiagnosticsEntry ::=  SEQUENCE
  { farEndIfDiagnosticsLaserBiasCurrentLevel Unsigned32,
    farEndIfDiagnosticsInputPower Integer32,
    farEndIfDiagnosticsOutputPower Integer32 }

farEndIfDiagnosticsLaserBiasCurrentLevel OBJECT-TYPE
    SYNTAX      Unsigned32 
    UNITS       "0.001 A"
    MAX-ACCESS  read-only
    STATUS      current
    DESCRIPTION
        "Laser Bias Current Level on demand" 
    ::=  { farEndIfDiagnosticsEntry 1 }

farEndIfDiagnosticsInputPower OBJECT-TYPE
    SYNTAX      Integer32 
    UNITS       "0.1 dBm"
    MAX-ACCESS  read-only
    STATUS      current
    DESCRIPTION   "The optical input power of a transmitter in dBm,
         measured in the range of -x to +y dBm (TBD).
         It is only valid when there is no loss of signal at the input,
         in which case a value of -65535 is returned.
         A value of -65535 also indicates that OIP is not available.
         When out of range, -65534 indicates that the OIP is outside
         the maximum value and -65533 for outside the minimum value."
    ::=  { farEndIfDiagnosticsEntry 2 }

farEndIfDiagnosticsOutputPower OBJECT-TYPE
    SYNTAX      Integer32 
    UNITS       "0.1 dBm"
    MAX-ACCESS  read-only
    STATUS      current
    DESCRIPTION   "The optical output power of a transmitter in dBm,
         measured in the range of -x to +y dBm.(TBD)
         It is only valid when there the laserState is 'On'.
         If not, a value of -65535 is returned.
         A value of -65535 also indicates that OOP is not available.
         When out of range, -65534 indicates that the OOP is outside
         the maximum value and -65533 for outside the minimum value."
    ::=  { farEndIfDiagnosticsEntry 3 }

farEndIfConfigTable OBJECT-TYPE
    SYNTAX      SEQUENCE OF FarEndIfConfigEntry
    MAX-ACCESS  not-accessible
    STATUS      current
    DESCRIPTION   ""
    ::=  { interfaceConfigAndStatus 36 }

farEndIfConfigEntry OBJECT-TYPE
    SYNTAX      FarEndIfConfigEntry
    MAX-ACCESS  not-accessible
    STATUS      current
    DESCRIPTION   ""
    INDEX       {
                  entityIndex
                }
    ::=  { farEndIfConfigTable 1 }

FarEndIfConfigEntry ::=  SEQUENCE
  { farEndIfConfigAlias SnmpAdminString,
    farEndIfConfigLoopConfig LoopConfig }

farEndIfConfigAlias OBJECT-TYPE
    SYNTAX      SnmpAdminString
    MAX-ACCESS  read-write
    STATUS      current
    DESCRIPTION   "A string, configurable by the operator, containing a
         symbolic name for the trail which is terminated at this interface."
    ::=  { farEndIfConfigEntry 1 }

farEndIfConfigLoopConfig OBJECT-TYPE
    SYNTAX      LoopConfig
    MAX-ACCESS  read-write
    STATUS      current
    DESCRIPTION   "The configuration of the loopback function.
         - noLoop: no loop configuration on the interface.
         - lineLoop: the incoming signal is looped to the outgoing
         line on the interface. The incoming signal is sent in the
         downstream direction and processed as normal.
         - inwardLoop: the output signal is looped to the incoming line
         on the interface. The looped signal is transmitted unchanged on
         the optical output."
    ::=  { farEndIfConfigEntry 2 }

farEndIfConfigCapTable OBJECT-TYPE
    SYNTAX      SEQUENCE OF FarEndIfConfigCapEntry
    MAX-ACCESS  not-accessible
    STATUS      current
    DESCRIPTION   ""
    ::=  { interfaceConfigAndStatus 37 }

farEndIfConfigCapEntry OBJECT-TYPE
    SYNTAX      FarEndIfConfigCapEntry
    MAX-ACCESS  not-accessible
    STATUS      current
    DESCRIPTION   ""
    INDEX       {
                  entityIndex
                }
    ::=  { farEndIfConfigCapTable 1 }

FarEndIfConfigCapEntry ::=  SEQUENCE
  { farEndIfConfigCapLoopConfig LoopConfigCaps }

farEndIfConfigCapLoopConfig OBJECT-TYPE
    SYNTAX      LoopConfigCaps
    MAX-ACCESS  read-only
    STATUS      current
    DESCRIPTION
        "External or Facility Loopback" 
    ::=  { farEndIfConfigCapEntry 1 }

farEndIfDataTable OBJECT-TYPE
    SYNTAX      SEQUENCE OF FarEndIfDataEntry
    MAX-ACCESS  not-accessible
    STATUS      current
    DESCRIPTION   ""
    ::=  { interfaceConfigAndStatus 38 }

farEndIfDataEntry OBJECT-TYPE
    SYNTAX      FarEndIfDataEntry
    MAX-ACCESS  not-accessible
    STATUS      current
    DESCRIPTION   ""
    INDEX       {
                  entityIndex
                }
    ::=  { farEndIfDataTable 1 }

FarEndIfDataEntry ::=  SEQUENCE
  { farEndIfDataType FspR7InterfaceType,
    farEndIfDataTransmitChannel FspR7ChannelIdentifier,
    farEndIfDataTransmitWavelength Unsigned32,
    farEndIfDataTransmitFrequency Unsigned32,
    farEndIfDataReach FspR7OpticalInterfaceReach,
    farEndIfDataConnector FspR7ConnectorType,
    farEndIfDataFiberType FspR7OpticalFiberType,
    farEndIfDataConnectionType FspR7TypeConnection,
    farEndIfDataAdmin FspR7AdminState }

farEndIfDataType OBJECT-TYPE
    SYNTAX      FspR7InterfaceType
    MAX-ACCESS  read-only
    STATUS      current
    DESCRIPTION
        "The TYPE defines the transport service type as wrapper with wrapper layer termination OR else as payload" 
    ::=  { farEndIfDataEntry 1 }

farEndIfDataTransmitChannel OBJECT-TYPE
    SYNTAX      FspR7ChannelIdentifier
    MAX-ACCESS  read-only
    STATUS      current
    DESCRIPTION
        "Channel" 
    ::=  { farEndIfDataEntry 2 }

farEndIfDataTransmitWavelength OBJECT-TYPE
    SYNTAX      Unsigned32 
    UNITS       "0.01 nm"
    MAX-ACCESS  read-only
    STATUS      current
    DESCRIPTION
        "Wavelength of Optical Interface (unit: nm)" 
    ::=  { farEndIfDataEntry 3 }

farEndIfDataTransmitFrequency OBJECT-TYPE
    SYNTAX      Unsigned32 
    UNITS       "0.01 THz"
    MAX-ACCESS  read-only
    STATUS      current
    DESCRIPTION
        "Frequency of Optical Interface (unit: nm)" 
    ::=  { farEndIfDataEntry 4 }

farEndIfDataReach OBJECT-TYPE
    SYNTAX      FspR7OpticalInterfaceReach
    MAX-ACCESS  read-only
    STATUS      current
    DESCRIPTION
        "Reach" 
    ::=  { farEndIfDataEntry 5 }

farEndIfDataConnector OBJECT-TYPE
    SYNTAX      FspR7ConnectorType
    MAX-ACCESS  read-only
    STATUS      current
    DESCRIPTION   "The textual description of the external connector type
         provided for an interface (eg. SC, LC, RJ45, etc)."
    ::=  { farEndIfDataEntry 6 }

farEndIfDataFiberType OBJECT-TYPE
    SYNTAX      FspR7OpticalFiberType
    MAX-ACCESS  read-only
    STATUS      current
    DESCRIPTION   "The fiber type of this interface. For interface modules not
         supporting Fibre Channel Transmission, the value will be 'unspecified'."
    ::=  { farEndIfDataEntry 7 }

farEndIfDataConnectionType OBJECT-TYPE
    SYNTAX      FspR7TypeConnection
    MAX-ACCESS  read-only
    STATUS      current
    DESCRIPTION
        "Connectivity Parameters for Facilities" 
    ::=  { farEndIfDataEntry 8 }

farEndIfDataAdmin OBJECT-TYPE
    SYNTAX      FspR7AdminState
    MAX-ACCESS  read-only
    STATUS      current
    DESCRIPTION
        "Administrative State is displayed in the GUI and Craft. Transition to Unassigend requires the entity to be deleted." 
    ::=  { farEndIfDataEntry 9 }

interfaceConfigExternalVidCapsTable OBJECT-TYPE
    SYNTAX      SEQUENCE OF InterfaceConfigExternalVidCapsEntry
    MAX-ACCESS  not-accessible
    STATUS      current
    DESCRIPTION   "This table is used to get capabilities for EXTVID parameter. Regular
         cap tables including EXTVID show the length of output string.
         Value 0 in regular cap tables means 'no capabilities'.
         The second index (n) is used to devide the output string to n string blocks.
         Each block has a maximum of 512 bytes. n = output string / 512."
    ::=  { interfaceConfigAndStatus 39 }

interfaceConfigExternalVidCapsEntry OBJECT-TYPE
    SYNTAX      InterfaceConfigExternalVidCapsEntry
    MAX-ACCESS  not-accessible
    STATUS      current
    DESCRIPTION   ""
    INDEX       {
                  entityIndex,
                  deployProvDcnExternalVidCapsIndexCap
                }
    ::=  { interfaceConfigExternalVidCapsTable 1 }

InterfaceConfigExternalVidCapsEntry ::=  SEQUENCE
  { interfaceConfigExternalVidCapsStringCap SnmpAdminString }

interfaceConfigExternalVidCapsStringCap OBJECT-TYPE
    SYNTAX      SnmpAdminString
    MAX-ACCESS  read-only
    STATUS      current
    DESCRIPTION
        "" 
    ::=  { interfaceConfigExternalVidCapsEntry 1 }

interfaceConfigLanAidCapsTable OBJECT-TYPE
    SYNTAX      SEQUENCE OF InterfaceConfigLanAidCapsEntry
    MAX-ACCESS  not-accessible
    STATUS      current
    DESCRIPTION   ""
    ::=  { interfaceConfigAndStatus 40 }

interfaceConfigLanAidCapsEntry OBJECT-TYPE
    SYNTAX      InterfaceConfigLanAidCapsEntry
    MAX-ACCESS  not-accessible
    STATUS      current
    DESCRIPTION   ""
    INDEX       {
                  entityIndex,
                  interfaceConfigLanAidCapsIndex
                }
    ::=  { interfaceConfigLanAidCapsTable 1 }

InterfaceConfigLanAidCapsEntry ::=  SEQUENCE
  { interfaceConfigLanAidCapsIndex EntityIndex }

interfaceConfigLanAidCapsIndex OBJECT-TYPE
    SYNTAX      EntityIndex
    MAX-ACCESS  read-only
    STATUS      current
    DESCRIPTION
        "AID of LAN" 
    ::=  { interfaceConfigLanAidCapsEntry 1 }

neighborDiscoveryDataTable OBJECT-TYPE
    SYNTAX      SEQUENCE OF NeighborDiscoveryDataEntry
    MAX-ACCESS  not-accessible
    STATUS      current
    DESCRIPTION   ""
    ::=  { interfaceConfigAndStatus 41 }

neighborDiscoveryDataEntry OBJECT-TYPE
    SYNTAX      NeighborDiscoveryDataEntry
    MAX-ACCESS  not-accessible
    STATUS      current
    DESCRIPTION   ""
    INDEX       {
                  entityIndex
                }
    ::=  { neighborDiscoveryDataTable 1 }

NeighborDiscoveryDataEntry ::=  SEQUENCE
  { neighborDiscoveryDataFarEndIp IpAddress,
    neighborDiscoveryDataFarEndPort EntityIndex,
    neighborDiscoveryDataFarEndTid SnmpAdminString,
    neighborDiscoveryDataFarEndTranLayerTermPoint EntityIndex,
    neighborDiscoveryDataFarEndPortAid SnmpAdminString,
    neighborDiscoveryDataFarEndTranLayerTermPointAid SnmpAdminString }

neighborDiscoveryDataFarEndIp OBJECT-TYPE
    SYNTAX      IpAddress
    MAX-ACCESS  read-only
    STATUS      current
    DESCRIPTION   ""
    ::=  { neighborDiscoveryDataEntry 1 }

neighborDiscoveryDataFarEndPort OBJECT-TYPE
    SYNTAX      EntityIndex
    MAX-ACCESS  read-only
    STATUS      current
    DESCRIPTION   "Far End Port Aid - index of AID"
    ::=  { neighborDiscoveryDataEntry 2 }

neighborDiscoveryDataFarEndTid OBJECT-TYPE
    SYNTAX      SnmpAdminString
    MAX-ACCESS  read-only
    STATUS      current
    DESCRIPTION   ""
    ::=  { neighborDiscoveryDataEntry 3 }

neighborDiscoveryDataFarEndTranLayerTermPoint OBJECT-TYPE
    SYNTAX      EntityIndex
    MAX-ACCESS  read-only
    STATUS      current
    DESCRIPTION   "Far End Transport Layer Termination Point - index of AID"
    ::=  { neighborDiscoveryDataEntry 4 }

neighborDiscoveryDataFarEndPortAid OBJECT-TYPE
    SYNTAX      SnmpAdminString
    MAX-ACCESS  read-only
    STATUS      current
    DESCRIPTION   "Far End Port Aid - string of AID"
    ::=  { neighborDiscoveryDataEntry 5 }

neighborDiscoveryDataFarEndTranLayerTermPointAid OBJECT-TYPE
    SYNTAX      SnmpAdminString
    MAX-ACCESS  read-only
    STATUS      current
    DESCRIPTION   "Far End Transport Layer Termination Point - string of AID"
    ::=  { neighborDiscoveryDataEntry 6 }

exChannelConfigTable OBJECT-TYPE
    SYNTAX      SEQUENCE OF ExChannelConfigEntry
    MAX-ACCESS  not-accessible
    STATUS      current
    DESCRIPTION   "Contains entries for the external channels.
        "
    ::=  { interfaceConfigAndStatus 42 }

exChannelConfigEntry OBJECT-TYPE
    SYNTAX      ExChannelConfigEntry
    MAX-ACCESS  not-accessible
    STATUS      current
    DESCRIPTION   "Only external channels will have an entry in this table."
    INDEX       {
                  entityIndex
                }
    ::=  { exChannelConfigTable 1 }

ExChannelConfigEntry ::=  SEQUENCE
  { exChannelConfigAlias SnmpAdminString,
    exChannelConfigFarEndLocation SnmpAdminString,
    exChannelConfigBitrate Unsigned32,
    exChannelConfigFecType FspR7FecType,
    exChannelConfigLineCoding FspR7LineCoding,
    exChannelConfigFrameFormat FspR7FrameFormat,
    exChannelConfigOpticalPowerTx Integer32,
    exChannelConfigOSNRTransmit Unsigned32,
    exChannelConfigPMDTransmit Unsigned32,
    exChannelConfigChromaticDispersionTx Integer32,
    exChannelConfigMinimumOSNRRcv Unsigned32,
    exChannelConfigMinimumOpticalPowerRcv Integer32,
    exChannelConfigMaximumOpticalPowerRcv Integer32,
    exChannelConfigMaximumPMDRcv Unsigned32,
    exChannelConfigChromaticDispersionRcv Integer32,
    exChannelConfigMaxBitErrorRate FspR7MaxBitErrorRate,
    exChannelConfigMinChromaticDispersionRcv Integer32,
    exChannelConfigMaxChromaticDispersionRcv Integer32 }

exChannelConfigAlias OBJECT-TYPE
    SYNTAX      SnmpAdminString
    MAX-ACCESS  read-write
    STATUS      current
    DESCRIPTION
        "User Applied Descriptor" 
    ::=  { exChannelConfigEntry 1 }

exChannelConfigFarEndLocation OBJECT-TYPE
    SYNTAX      SnmpAdminString
    MAX-ACCESS  read-write
    STATUS      current
    DESCRIPTION   ""
    ::=  { exChannelConfigEntry 2 }

exChannelConfigBitrate OBJECT-TYPE
    SYNTAX      Unsigned32 
    UNITS       "Mbps"
    MAX-ACCESS  read-only
    STATUS      current
    DESCRIPTION   ""
    ::=  { exChannelConfigEntry 3 }

exChannelConfigFecType OBJECT-TYPE
    SYNTAX      FspR7FecType
    MAX-ACCESS  read-write
    STATUS      current
    DESCRIPTION   ""
    ::=  { exChannelConfigEntry 4 }

exChannelConfigLineCoding OBJECT-TYPE
    SYNTAX      FspR7LineCoding
    MAX-ACCESS  read-write
    STATUS      current
    DESCRIPTION   ""
    ::=  { exChannelConfigEntry 5 }

exChannelConfigFrameFormat OBJECT-TYPE
    SYNTAX      FspR7FrameFormat
    MAX-ACCESS  read-write
    STATUS      current
    DESCRIPTION   ""
    ::=  { exChannelConfigEntry 6 }

exChannelConfigOpticalPowerTx OBJECT-TYPE
    SYNTAX      Integer32 (-9900..600 | -2147483648) 
    UNITS       "0.1 dBm"
    MAX-ACCESS  read-write
    STATUS      current
    DESCRIPTION
        "Optical Power Transmit" 
    ::=  { exChannelConfigEntry 7 }

exChannelConfigOSNRTransmit OBJECT-TYPE
    SYNTAX      Unsigned32 (0..58 | 4294967295) 
    UNITS       "dB"
    MAX-ACCESS  read-write
    STATUS      current
    DESCRIPTION
        "Optical Signal to Noise Ratio Transmit" 
    ::=  { exChannelConfigEntry 8 }

exChannelConfigPMDTransmit OBJECT-TYPE
    SYNTAX      Unsigned32 (0..30 | 4294967295) 
    UNITS       "ps"
    MAX-ACCESS  read-write
    STATUS      current
    DESCRIPTION
        "Polarization Mode Dispersion Transmit" 
    ::=  { exChannelConfigEntry 9 }

exChannelConfigChromaticDispersionTx OBJECT-TYPE
    SYNTAX      Integer32 (-60000..60000 | -2147483648) 
    UNITS       "ps/nm"
    MAX-ACCESS  read-write
    STATUS      current
    DESCRIPTION
        "Chromatic Dispersion Transmit" 
    ::=  { exChannelConfigEntry 10 }

exChannelConfigMinimumOSNRRcv OBJECT-TYPE
    SYNTAX      Unsigned32 (10..58 | 4294967295) 
    UNITS       "dB"
    MAX-ACCESS  read-write
    STATUS      current
    DESCRIPTION
        "Minimum Optical Signal to Noise Ratio, Rcv" 
    ::=  { exChannelConfigEntry 11 }

exChannelConfigMinimumOpticalPowerRcv OBJECT-TYPE
    SYNTAX      Integer32 (-2500..1000 | -2147483648) 
    UNITS       "0.1 dBm"
    MAX-ACCESS  read-write
    STATUS      current
    DESCRIPTION
        "Minimum Optical Power Received" 
    ::=  { exChannelConfigEntry 12 }

exChannelConfigMaximumOpticalPowerRcv OBJECT-TYPE
    SYNTAX      Integer32 (-2500..1000 | -2147483648) 
    UNITS       "0.1 dBm"
    MAX-ACCESS  read-write
    STATUS      current
    DESCRIPTION
        "Maximum Optical Power Received" 
    ::=  { exChannelConfigEntry 13 }

exChannelConfigMaximumPMDRcv OBJECT-TYPE
    SYNTAX      Unsigned32 (0..30 | 4294967295) 
    UNITS       "ps"
    MAX-ACCESS  read-write
    STATUS      current
    DESCRIPTION
        "Maximum Polarization Mode Dispersion Rcv" 
    ::=  { exChannelConfigEntry 14 }

exChannelConfigChromaticDispersionRcv OBJECT-TYPE
    SYNTAX      Integer32 (-60000..60000 | -2147483648) 
    UNITS       "ps/nm"
    MAX-ACCESS  read-write
    STATUS      deprecated
    DESCRIPTION
        "Maximum Chromatic Dispersion Rcv" 
    ::=  { exChannelConfigEntry 15 }

exChannelConfigMaxBitErrorRate OBJECT-TYPE
    SYNTAX      FspR7MaxBitErrorRate
    MAX-ACCESS  read-write
    STATUS      current
    DESCRIPTION
        "Maximum Bit Error Rate" 
    ::=  { exChannelConfigEntry 16 }

exChannelConfigMinChromaticDispersionRcv OBJECT-TYPE
    SYNTAX      Integer32 (-60000..60000 | -2147483648) 
    UNITS       "ps/nm"
    MAX-ACCESS  read-write
    STATUS      current
    DESCRIPTION
        "Minimum Chromatic Dispersion Rcv" 
    ::=  { exChannelConfigEntry 17 }

exChannelConfigMaxChromaticDispersionRcv OBJECT-TYPE
    SYNTAX      Integer32 (-60000..60000 | -2147483648) 
    UNITS       "ps/nm"
    MAX-ACCESS  read-write
    STATUS      current
    DESCRIPTION
        "Maximum Chromatic Dispersion Rcv" 
    ::=  { exChannelConfigEntry 18 }

exChannelDataTable OBJECT-TYPE
    SYNTAX      SEQUENCE OF ExChannelDataEntry
    MAX-ACCESS  not-accessible
    STATUS      current
    DESCRIPTION   "Contains diagnostic entries for external interfaces.
        "
    ::=  { interfaceConfigAndStatus 43 }

exChannelDataEntry OBJECT-TYPE
    SYNTAX      ExChannelDataEntry
    MAX-ACCESS  not-accessible
    STATUS      current
    DESCRIPTION   ""
    INDEX       {
                  entityIndex
                }
    ::=  { exChannelDataTable 1 }

ExChannelDataEntry ::=  SEQUENCE
  { exChannelDataType FspR7InterfaceType,
    exChannelDataTransmitChannel FspR7ChannelIdentifier,
    exChannelDataChannelBandwidth FspR7ChannelBandwidth,
    exChannelDataConnectionState FspR7ConnectState }

exChannelDataType OBJECT-TYPE
    SYNTAX      FspR7InterfaceType
    MAX-ACCESS  read-only
    STATUS      current
    DESCRIPTION   ""
    ::=  { exChannelDataEntry 1 }

exChannelDataTransmitChannel OBJECT-TYPE
    SYNTAX      FspR7ChannelIdentifier
    MAX-ACCESS  read-write
    STATUS      current
    DESCRIPTION
        "Channel" 
    ::=  { exChannelDataEntry 2 }

exChannelDataChannelBandwidth OBJECT-TYPE
    SYNTAX      FspR7ChannelBandwidth
    MAX-ACCESS  read-write
    STATUS      current
    DESCRIPTION
        "Channel Bandwidth" 
    ::=  { exChannelDataEntry 3 }

exChannelDataConnectionState OBJECT-TYPE
    SYNTAX      FspR7ConnectState
    MAX-ACCESS  read-only
    STATUS      current
    DESCRIPTION
        "Connection State" 
    ::=  { exChannelDataEntry 4 }

vtpEntityDataTable OBJECT-TYPE
    SYNTAX      SEQUENCE OF VtpEntityDataEntry
    MAX-ACCESS  not-accessible
    STATUS      current
    DESCRIPTION   ""
    ::=  { interfaceConfigAndStatus 44 }

vtpEntityDataEntry OBJECT-TYPE
    SYNTAX      VtpEntityDataEntry
    MAX-ACCESS  not-accessible
    STATUS      current
    DESCRIPTION   ""
    INDEX       {
                  vtpEntityIndex
                }
    ::=  { vtpEntityDataTable 1 }

VtpEntityDataEntry ::=  SEQUENCE
  { vtpEntityDataConnEqptState FspR7ConnectState,
    vtpEntityDataChannelProvision FspR7ChannelIdentifier,
    vtpEntityDataLambda Unsigned32,
    vtpEntityDataFrequency Unsigned32,
    vtpEntityDataReach FspR7OpticalInterfaceReach,
    vtpEntityDataBandProvision FspR7OpticalBand,
    vtpEntityDataSubBandProvision FspR7OpticalSubBand,
    vtpEntityDataGroupProvision FspR7OpticalGroup,
    vtpEntityDataSfProvision FspR7SingleFiberLocation,
    vtpEntityDataConnector FspR7ConnectorType,
    vtpEntityDataFiber FspR7OpticalFiberType,
    vtpEntityDataDirection ApsDirection,
    vtpEntityDataLevel FspR7OpticalMultiplexLevel,
    vtpEntityDataFunction FspR7InterfaceFunction }

vtpEntityDataConnEqptState OBJECT-TYPE
    SYNTAX      FspR7ConnectState
    MAX-ACCESS  read-only
    STATUS      current
    DESCRIPTION   ""
    ::=  { vtpEntityDataEntry 1 }

vtpEntityDataChannelProvision OBJECT-TYPE
    SYNTAX      FspR7ChannelIdentifier
    MAX-ACCESS  read-only
    STATUS      current
    DESCRIPTION   ""
    ::=  { vtpEntityDataEntry 2 }

vtpEntityDataLambda OBJECT-TYPE
    SYNTAX      Unsigned32 
    UNITS       "0.01 nm"
    MAX-ACCESS  read-only
    STATUS      current
    DESCRIPTION   ""
    ::=  { vtpEntityDataEntry 3 }

vtpEntityDataFrequency OBJECT-TYPE
    SYNTAX      Unsigned32 
    UNITS       "0.01 THz"
    MAX-ACCESS  read-only
    STATUS      current
    DESCRIPTION   ""
    ::=  { vtpEntityDataEntry 4 }

vtpEntityDataReach OBJECT-TYPE
    SYNTAX      FspR7OpticalInterfaceReach
    MAX-ACCESS  read-only
    STATUS      current
    DESCRIPTION   ""
    ::=  { vtpEntityDataEntry 5 }

vtpEntityDataBandProvision OBJECT-TYPE
    SYNTAX      FspR7OpticalBand
    MAX-ACCESS  read-only
    STATUS      current
    DESCRIPTION   ""
    ::=  { vtpEntityDataEntry 6 }

vtpEntityDataSubBandProvision OBJECT-TYPE
    SYNTAX      FspR7OpticalSubBand
    MAX-ACCESS  read-only
    STATUS      current
    DESCRIPTION   ""
    ::=  { vtpEntityDataEntry 7 }

vtpEntityDataGroupProvision OBJECT-TYPE
    SYNTAX      FspR7OpticalGroup
    MAX-ACCESS  read-only
    STATUS      current
    DESCRIPTION   ""
    ::=  { vtpEntityDataEntry 8 }

vtpEntityDataSfProvision OBJECT-TYPE
    SYNTAX      FspR7SingleFiberLocation
    MAX-ACCESS  read-only
    STATUS      current
    DESCRIPTION   ""
    ::=  { vtpEntityDataEntry 9 }

vtpEntityDataConnector OBJECT-TYPE
    SYNTAX      FspR7ConnectorType
    MAX-ACCESS  read-only
    STATUS      current
    DESCRIPTION   ""
    ::=  { vtpEntityDataEntry 10 }

vtpEntityDataFiber OBJECT-TYPE
    SYNTAX      FspR7OpticalFiberType
    MAX-ACCESS  read-only
    STATUS      current
    DESCRIPTION   ""
    ::=  { vtpEntityDataEntry 11 }

vtpEntityDataDirection OBJECT-TYPE
    SYNTAX      ApsDirection
    MAX-ACCESS  read-only
    STATUS      current
    DESCRIPTION   ""
    ::=  { vtpEntityDataEntry 12 }

vtpEntityDataLevel OBJECT-TYPE
    SYNTAX      FspR7OpticalMultiplexLevel
    MAX-ACCESS  read-only
    STATUS      current
    DESCRIPTION   ""
    ::=  { vtpEntityDataEntry 13 }

vtpEntityDataFunction OBJECT-TYPE
    SYNTAX      FspR7InterfaceFunction
    MAX-ACCESS  read-only
    STATUS      current
    DESCRIPTION   ""
    ::=  { vtpEntityDataEntry 14 }

ptpEntityConfigTable OBJECT-TYPE
    SYNTAX      SEQUENCE OF PtpEntityConfigEntry
    MAX-ACCESS  not-accessible
    STATUS      current
    DESCRIPTION   ""
    ::=  { interfaceConfigAndStatus 45 }

ptpEntityConfigEntry OBJECT-TYPE
    SYNTAX      PtpEntityConfigEntry
    MAX-ACCESS  not-accessible
    STATUS      current
    DESCRIPTION   ""
    INDEX       {
                  ptpEntityIndex
                }
    ::=  { ptpEntityConfigTable 1 }

PtpEntityConfigEntry ::=  SEQUENCE
  { ptpEntityConfigAlias SnmpAdminString,
    ptpEntityConfigFiberDetect FspR7FiberDetect }

ptpEntityConfigAlias OBJECT-TYPE
    SYNTAX      SnmpAdminString
    MAX-ACCESS  read-write
    STATUS      current
    DESCRIPTION   ""
    ::=  { ptpEntityConfigEntry 1 }

ptpEntityConfigFiberDetect OBJECT-TYPE
    SYNTAX      FspR7FiberDetect
    MAX-ACCESS  read-write
    STATUS      current
    DESCRIPTION   ""
    ::=  { ptpEntityConfigEntry 2 }

ptpEntityConfigCapTable OBJECT-TYPE
    SYNTAX      SEQUENCE OF PtpEntityConfigCapEntry
    MAX-ACCESS  not-accessible
    STATUS      current
    DESCRIPTION   ""
    ::=  { interfaceConfigAndStatus 46 }

ptpEntityConfigCapEntry OBJECT-TYPE
    SYNTAX      PtpEntityConfigCapEntry
    MAX-ACCESS  not-accessible
    STATUS      current
    DESCRIPTION   ""
    INDEX       {
                  ptpEntityIndex
                }
    ::=  { ptpEntityConfigCapTable 1 }

PtpEntityConfigCapEntry ::=  SEQUENCE
  { ptpEntityConfigCapFiberDetect FspR7FiberDetectCaps }

ptpEntityConfigCapFiberDetect OBJECT-TYPE
    SYNTAX      FspR7FiberDetectCaps
    MAX-ACCESS  read-only
    STATUS      current
    DESCRIPTION   ""
    ::=  { ptpEntityConfigCapEntry 1 }

superChannelDataTable OBJECT-TYPE
    SYNTAX      SEQUENCE OF SuperChannelDataEntry
    MAX-ACCESS  not-accessible
    STATUS      current
    DESCRIPTION   ""
    ::=  { interfaceConfigAndStatus 47 }

superChannelDataEntry OBJECT-TYPE
    SYNTAX      SuperChannelDataEntry
    MAX-ACCESS  not-accessible
    STATUS      current
    DESCRIPTION   ""
    INDEX       {
                  entityIndex
                }
    ::=  { superChannelDataTable 1 }

SuperChannelDataEntry ::=  SEQUENCE
  { superChannelDataChannelSpacing FspR7ChannelSpacing,
    superChannelDataChannelBandwith FspR7ChannelBandwidth,
    superChannelDataLaneChannel1 FspR7ChannelIdentifier,
    superChannelDataLaneChannel2 FspR7ChannelIdentifier,
    superChannelDataLaneChannel3 FspR7ChannelIdentifier,
    superChannelDataLaneChannel4 FspR7ChannelIdentifier,
    superChannelDataFacilities SnmpAdminString,
    superChannelDataConnectionState FspR7ConnectState,
    superChannelDataLanes FspR7OpticalLanes,
    superChannelDataFacilitiesIndexes SnmpAdminString }

superChannelDataChannelSpacing OBJECT-TYPE
    SYNTAX      FspR7ChannelSpacing
    MAX-ACCESS  read-only
    STATUS      current
    DESCRIPTION
        "ITU Grid channel spacing" 
    ::=  { superChannelDataEntry 1 }

superChannelDataChannelBandwith OBJECT-TYPE
    SYNTAX      FspR7ChannelBandwidth
    MAX-ACCESS  read-only
    STATUS      current
    DESCRIPTION
        "Channel Bandwidth" 
    ::=  { superChannelDataEntry 2 }

superChannelDataLaneChannel1 OBJECT-TYPE
    SYNTAX      FspR7ChannelIdentifier
    MAX-ACCESS  read-only
    STATUS      current
    DESCRIPTION
        "Lane Channel" 
    ::=  { superChannelDataEntry 3 }

superChannelDataLaneChannel2 OBJECT-TYPE
    SYNTAX      FspR7ChannelIdentifier
    MAX-ACCESS  read-only
    STATUS      current
    DESCRIPTION
        "Lane Channel" 
    ::=  { superChannelDataEntry 4 }

superChannelDataLaneChannel3 OBJECT-TYPE
    SYNTAX      FspR7ChannelIdentifier
    MAX-ACCESS  read-only
    STATUS      current
    DESCRIPTION
        "Lane Channel" 
    ::=  { superChannelDataEntry 5 }

superChannelDataLaneChannel4 OBJECT-TYPE
    SYNTAX      FspR7ChannelIdentifier
    MAX-ACCESS  read-only
    STATUS      current
    DESCRIPTION
        "Lane Channel" 
    ::=  { superChannelDataEntry 6 }

superChannelDataFacilities OBJECT-TYPE
    SYNTAX      SnmpAdminString
    MAX-ACCESS  read-only
    STATUS      current
    DESCRIPTION
        "List of AIDs (CH, VCH or WCH) used by parent entity (Segment, Service, Optical Line or Super Channel)" 
    ::=  { superChannelDataEntry 7 }

superChannelDataConnectionState OBJECT-TYPE
    SYNTAX      FspR7ConnectState
    MAX-ACCESS  read-only
    STATUS      current
    DESCRIPTION
        "Connection State" 
    ::=  { superChannelDataEntry 8 }

superChannelDataLanes OBJECT-TYPE
    SYNTAX      FspR7OpticalLanes
    MAX-ACCESS  read-only
    STATUS      current
    DESCRIPTION
        "Number of Optical Transport Lanes in OTLG" 
    ::=  { superChannelDataEntry 9 }

superChannelDataFacilitiesIndexes OBJECT-TYPE
    SYNTAX      SnmpAdminString
    MAX-ACCESS  read-only
    STATUS      current
    DESCRIPTION
        "Facility AIDs represented as entityIndex." 
    ::=  { superChannelDataEntry 10 }

superChannelConfigTable OBJECT-TYPE
    SYNTAX      SEQUENCE OF SuperChannelConfigEntry
    MAX-ACCESS  not-accessible
    STATUS      current
    DESCRIPTION   ""
    ::=  { interfaceConfigAndStatus 48 }

superChannelConfigEntry OBJECT-TYPE
    SYNTAX      SuperChannelConfigEntry
    MAX-ACCESS  not-accessible
    STATUS      current
    DESCRIPTION   ""
    INDEX       {
                  entityIndex
                }
    ::=  { superChannelConfigTable 1 }

SuperChannelConfigEntry ::=  SEQUENCE
  { superChannelConfigEqlzAdmin FspR7EqlzAdminState,
    superChannelConfigAlias SnmpAdminString,
    superChannelConfigInitiateEqualization FspR7InitEqualization }

superChannelConfigEqlzAdmin OBJECT-TYPE
    SYNTAX      FspR7EqlzAdminState
    MAX-ACCESS  read-write
    STATUS      current
    DESCRIPTION
        "Scheduled Equalization Administration" 
    ::=  { superChannelConfigEntry 1 }

superChannelConfigAlias OBJECT-TYPE
    SYNTAX      SnmpAdminString
    MAX-ACCESS  read-write
    STATUS      current
    DESCRIPTION
        "User Applied Descriptor" 
    ::=  { superChannelConfigEntry 2 }

superChannelConfigInitiateEqualization OBJECT-TYPE
    SYNTAX      FspR7InitEqualization
    MAX-ACCESS  read-write
    STATUS      current
    DESCRIPTION
        "Initiate Equalization" 
    ::=  { superChannelConfigEntry 3 }

superChannelConfigCapTable OBJECT-TYPE
    SYNTAX      SEQUENCE OF SuperChannelConfigCapEntry
    MAX-ACCESS  not-accessible
    STATUS      current
    DESCRIPTION   ""
    ::=  { interfaceConfigAndStatus 49 }

superChannelConfigCapEntry OBJECT-TYPE
    SYNTAX      SuperChannelConfigCapEntry
    MAX-ACCESS  not-accessible
    STATUS      current
    DESCRIPTION   ""
    INDEX       {
                  entityIndex
                }
    ::=  { superChannelConfigCapTable 1 }

SuperChannelConfigCapEntry ::=  SEQUENCE
  { superChannelConfigCapEqlzAdmin FspR7EqlzAdminStateCaps,
    superChannelConfigCapInitiateEqualization FspR7InitEqualizationCaps }

superChannelConfigCapEqlzAdmin OBJECT-TYPE
    SYNTAX      FspR7EqlzAdminStateCaps
    MAX-ACCESS  read-only
    STATUS      current
    DESCRIPTION
        "Scheduled Equalization Administration" 
    ::=  { superChannelConfigCapEntry 1 }

superChannelConfigCapInitiateEqualization OBJECT-TYPE
    SYNTAX      FspR7InitEqualizationCaps
    MAX-ACCESS  read-only
    STATUS      current
    DESCRIPTION
        "Initiate Equalization" 
    ::=  { superChannelConfigCapEntry 2 }

vc4allocatedTable OBJECT-TYPE
    SYNTAX      SEQUENCE OF Vc4allocatedEntry
    MAX-ACCESS  not-accessible
    STATUS      current
    DESCRIPTION   "The higher order VC table for the configuration of an SDH/SONET Port.
         Only VC-4s allocated to a service are present in this table."
    ::=  { gfpServiceConfigAndStatus 1 }

vc4allocatedEntry OBJECT-TYPE
    SYNTAX      Vc4allocatedEntry
    MAX-ACCESS  not-accessible
    STATUS      current
    DESCRIPTION   "An entry in the higher order VC (HO-VC) table. Each entry in
         this table represents a higher order AU (VC)."
    INDEX       {
                  entityIndex
                }
    ::=  { vc4allocatedTable 1 }

Vc4allocatedEntry ::=  SEQUENCE
  { vc4allocatedContainer EntityIndex,
    vc4allocatedClassInstanceNumber Integer32,
    vc4allocatedSequenceNumber Unsigned32 }

vc4allocatedContainer OBJECT-TYPE
    SYNTAX      EntityIndex
    MAX-ACCESS  read-only
    STATUS      current
    DESCRIPTION   "The entityIndex of the VC-4 container."
    ::=  { vc4allocatedEntry 1 }

vc4allocatedClassInstanceNumber OBJECT-TYPE
    SYNTAX      Integer32 (1..32000 | -2147483648)
    MAX-ACCESS  read-only
    STATUS      current
    DESCRIPTION
        "The class instance number of this entity within the module(card)" 
    ::=  { vc4allocatedEntry 2 }

vc4allocatedSequenceNumber OBJECT-TYPE
    SYNTAX      Unsigned32
    MAX-ACCESS  read-only
    STATUS      current
    DESCRIPTION
        "Sequence number of an individual container within a Virtual Concatenated Group" 
    ::=  { vc4allocatedEntry 3 }

vc3allocatedTable OBJECT-TYPE
    SYNTAX      SEQUENCE OF Vc3allocatedEntry
    MAX-ACCESS  not-accessible
    STATUS      current
    DESCRIPTION   "The lower order VC table for the configuration of an SDH/SONET
         Port. Only VC-3s allocated to a service are present in this table."
    ::=  { gfpServiceConfigAndStatus 2 }

vc3allocatedEntry OBJECT-TYPE
    SYNTAX      Vc3allocatedEntry
    MAX-ACCESS  not-accessible
    STATUS      current
    DESCRIPTION   "An entry in the lower order VC (LO-VC) table. Each entry in
         this table represents a lower order path."
    INDEX       {
                  entityIndex
                }
    ::=  { vc3allocatedTable 1 }

Vc3allocatedEntry ::=  SEQUENCE
  { vc3allocatedContainer EntityIndex,
    vc3allocatedClassInstanceNumber Integer32,
    vc3allocatedSequenceNumber Unsigned32 }

vc3allocatedContainer OBJECT-TYPE
    SYNTAX      EntityIndex
    MAX-ACCESS  read-only
    STATUS      current
    DESCRIPTION   "The entityIndex of the VC-3 container."
    ::=  { vc3allocatedEntry 1 }

vc3allocatedClassInstanceNumber OBJECT-TYPE
    SYNTAX      Integer32 (1..32000 | -2147483648)
    MAX-ACCESS  read-only
    STATUS      current
    DESCRIPTION
        "The class instance number of this entity within the module(card)" 
    ::=  { vc3allocatedEntry 2 }

vc3allocatedSequenceNumber OBJECT-TYPE
    SYNTAX      Unsigned32
    MAX-ACCESS  read-only
    STATUS      current
    DESCRIPTION
        "Sequence number of an individual container within a Virtual Concatenated Group" 
    ::=  { vc3allocatedEntry 3 }

sts1allocatedTable OBJECT-TYPE
    SYNTAX      SEQUENCE OF Sts1allocatedEntry
    MAX-ACCESS  not-accessible
    STATUS      current
    DESCRIPTION   ""
    ::=  { gfpServiceConfigAndStatus 3 }

sts1allocatedEntry OBJECT-TYPE
    SYNTAX      Sts1allocatedEntry
    MAX-ACCESS  not-accessible
    STATUS      current
    DESCRIPTION   ""
    INDEX       {
                  entityIndex
                }
    ::=  { sts1allocatedTable 1 }

Sts1allocatedEntry ::=  SEQUENCE
  { sts1allocatedContainer EntityIndex,
    sts1allocatedClassInstanceNumber Integer32,
    sts1allocatedSequenceNumber Unsigned32 }

sts1allocatedContainer OBJECT-TYPE
    SYNTAX      EntityIndex
    MAX-ACCESS  read-only
    STATUS      current
    DESCRIPTION   "The entityIndex of the STS-1 container."
    ::=  { sts1allocatedEntry 1 }

sts1allocatedClassInstanceNumber OBJECT-TYPE
    SYNTAX      Integer32 (1..32000 | -2147483648)
    MAX-ACCESS  read-only
    STATUS      current
    DESCRIPTION
        "The class instance number of this entity within the module(card)" 
    ::=  { sts1allocatedEntry 2 }

sts1allocatedSequenceNumber OBJECT-TYPE
    SYNTAX      Unsigned32
    MAX-ACCESS  read-only
    STATUS      current
    DESCRIPTION
        "Sequence number of an individual container within a Virtual Concatenated Group" 
    ::=  { sts1allocatedEntry 3 }

vchConfigTable OBJECT-TYPE
    SYNTAX      SEQUENCE OF VchConfigEntry
    MAX-ACCESS  not-accessible
    STATUS      current
    DESCRIPTION   "Contains entries for the configuration of VCH interfaces.
         This table extends the entries in the opticalIfTable."
    ::=  { gfpServiceConfigAndStatus 4 }

vchConfigEntry OBJECT-TYPE
    SYNTAX      VchConfigEntry
    MAX-ACCESS  not-accessible
    STATUS      current
    DESCRIPTION   ""
    INDEX       {
                  entityIndex
                }
    ::=  { vchConfigTable 1 }

VchConfigEntry ::=  SEQUENCE
  { vchConfigBundle SonetVcBundleAllocation,
    vchConfigCir Unsigned32 }

vchConfigBundle OBJECT-TYPE
    SYNTAX      SonetVcBundleAllocation
    MAX-ACCESS  read-only
    STATUS      current
    DESCRIPTION
        "List of VC4/VC3/STS1/STS3c/STS24c/STS48c containers used in the BUNDLE" 
    ::=  { vchConfigEntry 1 }

vchConfigCir OBJECT-TYPE
    SYNTAX      Unsigned32 
    UNITS       "Mbps"
    MAX-ACCESS  read-write
    STATUS      current
    DESCRIPTION   "Comitted Information Rate of the virtual channel."
    ::=  { vchConfigEntry 2 }

vchDataTable OBJECT-TYPE
    SYNTAX      SEQUENCE OF VchDataEntry
    MAX-ACCESS  not-accessible
    STATUS      current
    DESCRIPTION   "Contains diagnostic entries for optical VCH interfaces.
         This table extends the entries in the opticalIfDataTable."
    ::=  { gfpServiceConfigAndStatus 5 }

vchDataEntry OBJECT-TYPE
    SYNTAX      VchDataEntry
    MAX-ACCESS  not-accessible
    STATUS      current
    DESCRIPTION   ""
    INDEX       {
                  entityIndex
                }
    ::=  { vchDataTable 1 }

VchDataEntry ::=  SEQUENCE
  { vchDataVcType VirtualContainerType,
    vchDataOpuPayloadType FspR7OpuPayloadType,
    vchDataOwnerAid EntityIndex }

vchDataVcType OBJECT-TYPE
    SYNTAX      VirtualContainerType
    MAX-ACCESS  read-only
    STATUS      current
    DESCRIPTION
        "Virtual Container Group Type" 
    ::=  { vchDataEntry 1 }

vchDataOpuPayloadType OBJECT-TYPE
    SYNTAX      FspR7OpuPayloadType
    MAX-ACCESS  read-only
    STATUS      current
    DESCRIPTION
        "OPU Payload Type Indicator" 
    ::=  { vchDataEntry 2 }

vchDataOwnerAid OBJECT-TYPE
    SYNTAX      EntityIndex
    MAX-ACCESS  read-only
    STATUS      current
    DESCRIPTION
        "Channel Group which is the parent (owner) of the channel" 
    ::=  { vchDataEntry 3 }

gfpServiceDefTable OBJECT-TYPE
    SYNTAX      SEQUENCE OF GfpServiceDefEntry
    MAX-ACCESS  not-accessible
    STATUS      current
    DESCRIPTION   "The GFP Service Default table provides default values for the
         configuration of GFP services."
    ::=  { gfpServiceConfigAndStatus 6 }

gfpServiceDefEntry OBJECT-TYPE
    SYNTAX      GfpServiceDefEntry
    MAX-ACCESS  not-accessible
    STATUS      current
    DESCRIPTION   "An entry in the GFP Service Default table. Each entry in
         this table represents a default service configuration for a
         data rate and protocol. These values may be used as suggested
         values by the management system when defining a new GFP Service.
         There is one entry in this table for each valid data rate
         and service mapping (refer also to Appendix 1)."
    INDEX       {
                  entityIndex
                }
    ::=  { gfpServiceDefTable 1 }

GfpServiceDefEntry ::=  SEQUENCE
  { gfpServiceDefBundleAllocation SonetVcBundleAllocation,
    gfpServiceDefBandwidth Unsigned32,
    gfpServiceDefVcType VirtualContainerType }

gfpServiceDefBundleAllocation OBJECT-TYPE
    SYNTAX      SonetVcBundleAllocation
    MAX-ACCESS  read-only
    STATUS      current
    DESCRIPTION   "The default allocation of VCs for the specified datarate and mapping."
    ::=  { gfpServiceDefEntry 1 }

gfpServiceDefBandwidth OBJECT-TYPE
    SYNTAX      Unsigned32 (0..1000 | 4294967295) 
    UNITS       "Mbps"
    MAX-ACCESS  read-only
    STATUS      current
    DESCRIPTION   "The default bandwidth rate throttling of the specified service,
         valid only for mapping: 'gfpframed' and DataRate mb1250 (GbE).
         When not applicable, the value 0 is returned."
    ::=  { gfpServiceDefEntry 2 }

gfpServiceDefVcType OBJECT-TYPE
    SYNTAX      VirtualContainerType
    MAX-ACCESS  read-only
    STATUS      current
    DESCRIPTION   "The type of VC allocation for the specified DataRate and Mapping
         and used together with BundleSize and Bandwidth:
         -- vc4Type(1): bundle of HO-VCs (VC4)
         -- vc3Au4Type(2): bundle of LO-VCs (VC4 + TUG3)
         The default is vc4Type(1)."
    ::=  { gfpServiceDefEntry 3 }

sts3callocatedTable OBJECT-TYPE
    SYNTAX      SEQUENCE OF Sts3callocatedEntry
    MAX-ACCESS  not-accessible
    STATUS      current
    DESCRIPTION   ""
    ::=  { gfpServiceConfigAndStatus 7 }

sts3callocatedEntry OBJECT-TYPE
    SYNTAX      Sts3callocatedEntry
    MAX-ACCESS  not-accessible
    STATUS      current
    DESCRIPTION   ""
    INDEX       {
                  entityIndex
                }
    ::=  { sts3callocatedTable 1 }

Sts3callocatedEntry ::=  SEQUENCE
  { sts3callocatedContainer EntityIndex,
    sts3callocatedClassInstanceNumber Integer32,
    sts3callocatedSequenceNumber Unsigned32 }

sts3callocatedContainer OBJECT-TYPE
    SYNTAX      EntityIndex
    MAX-ACCESS  read-only
    STATUS      current
    DESCRIPTION   "The entityIndex of the STS-3c container."
    ::=  { sts3callocatedEntry 1 }

sts3callocatedClassInstanceNumber OBJECT-TYPE
    SYNTAX      Integer32 (1..32000 | -2147483648)
    MAX-ACCESS  read-only
    STATUS      current
    DESCRIPTION
        "The class instance number of this entity within the module(card)" 
    ::=  { sts3callocatedEntry 2 }

sts3callocatedSequenceNumber OBJECT-TYPE
    SYNTAX      Unsigned32
    MAX-ACCESS  read-only
    STATUS      current
    DESCRIPTION
        "Sequence number of an individual container within a Virtual Concatenated Group" 
    ::=  { sts3callocatedEntry 3 }

vs1allocatedTable OBJECT-TYPE
    SYNTAX      SEQUENCE OF Vs1allocatedEntry
    MAX-ACCESS  not-accessible
    STATUS      current
    DESCRIPTION   ""
    ::=  { gfpServiceConfigAndStatus 8 }

vs1allocatedEntry OBJECT-TYPE
    SYNTAX      Vs1allocatedEntry
    MAX-ACCESS  not-accessible
    STATUS      current
    DESCRIPTION   ""
    INDEX       {
                  entityIndex
                }
    ::=  { vs1allocatedTable 1 }

Vs1allocatedEntry ::=  SEQUENCE
  { vs1allocatedContainer EntityIndex,
    vs1allocatedClassInstanceNumber Integer32,
    vs1allocatedSequenceNumber Unsigned32,
    vs1allocatedFacilityType FspR7InterfaceType }

vs1allocatedContainer OBJECT-TYPE
    SYNTAX      EntityIndex
    MAX-ACCESS  read-only
    STATUS      current
    DESCRIPTION   "The entityIndex of the VS-1 container."
    ::=  { vs1allocatedEntry 1 }

vs1allocatedClassInstanceNumber OBJECT-TYPE
    SYNTAX      Integer32 (1..32000 | -2147483648)
    MAX-ACCESS  read-only
    STATUS      current
    DESCRIPTION
        "The class instance number of this entity within the module(card)" 
    ::=  { vs1allocatedEntry 2 }

vs1allocatedSequenceNumber OBJECT-TYPE
    SYNTAX      Unsigned32
    MAX-ACCESS  read-only
    STATUS      current
    DESCRIPTION
        "Sequence number of an individual container within a Virtual Concatenated Group" 
    ::=  { vs1allocatedEntry 3 }

vs1allocatedFacilityType OBJECT-TYPE
    SYNTAX      FspR7InterfaceType
    MAX-ACCESS  read-only
    STATUS      current
    DESCRIPTION
        "The TYPE defines the transport service type as wrapper with wrapper layer termination OR else as payload" 
    ::=  { vs1allocatedEntry 4 }

sts24callocatedTable OBJECT-TYPE
    SYNTAX      SEQUENCE OF Sts24callocatedEntry
    MAX-ACCESS  not-accessible
    STATUS      current
    DESCRIPTION   ""
    ::=  { gfpServiceConfigAndStatus 9 }

sts24callocatedEntry OBJECT-TYPE
    SYNTAX      Sts24callocatedEntry
    MAX-ACCESS  not-accessible
    STATUS      current
    DESCRIPTION   ""
    INDEX       {
                  entityIndex
                }
    ::=  { sts24callocatedTable 1 }

Sts24callocatedEntry ::=  SEQUENCE
  { sts24callocatedContainer EntityIndex,
    sts24callocatedClassInstanceNumber Integer32,
    sts24callocatedSequenceNumber Unsigned32,
    sts24callocatedFacilityType FspR7InterfaceType }

sts24callocatedContainer OBJECT-TYPE
    SYNTAX      EntityIndex
    MAX-ACCESS  read-only
    STATUS      current
    DESCRIPTION   "The entityIndex of the STS24C container."
    ::=  { sts24callocatedEntry 1 }

sts24callocatedClassInstanceNumber OBJECT-TYPE
    SYNTAX      Integer32 (1..32000 | -2147483648)
    MAX-ACCESS  read-only
    STATUS      current
    DESCRIPTION
        "The class instance number of this entity within the module(card)" 
    ::=  { sts24callocatedEntry 2 }

sts24callocatedSequenceNumber OBJECT-TYPE
    SYNTAX      Unsigned32
    MAX-ACCESS  read-only
    STATUS      current
    DESCRIPTION
        "Sequence number of an individual container within a Virtual Concatenated Group" 
    ::=  { sts24callocatedEntry 3 }

sts24callocatedFacilityType OBJECT-TYPE
    SYNTAX      FspR7InterfaceType
    MAX-ACCESS  read-only
    STATUS      current
    DESCRIPTION
        "The TYPE defines the transport service type as wrapper with wrapper layer termination OR else as payload" 
    ::=  { sts24callocatedEntry 4 }

sts48callocatedTable OBJECT-TYPE
    SYNTAX      SEQUENCE OF Sts48callocatedEntry
    MAX-ACCESS  not-accessible
    STATUS      current
    DESCRIPTION   ""
    ::=  { gfpServiceConfigAndStatus 10 }

sts48callocatedEntry OBJECT-TYPE
    SYNTAX      Sts48callocatedEntry
    MAX-ACCESS  not-accessible
    STATUS      current
    DESCRIPTION   ""
    INDEX       {
                  entityIndex
                }
    ::=  { sts48callocatedTable 1 }

Sts48callocatedEntry ::=  SEQUENCE
  { sts48callocatedContainer EntityIndex,
    sts48callocatedClassInstanceNumber Integer32,
    sts48callocatedSequenceNumber Unsigned32,
    sts48callocatedFacilityType FspR7InterfaceType }

sts48callocatedContainer OBJECT-TYPE
    SYNTAX      EntityIndex
    MAX-ACCESS  read-only
    STATUS      current
    DESCRIPTION   "The entityIndex of the STS48C container."
    ::=  { sts48callocatedEntry 1 }

sts48callocatedClassInstanceNumber OBJECT-TYPE
    SYNTAX      Integer32 (1..32000 | -2147483648)
    MAX-ACCESS  read-only
    STATUS      current
    DESCRIPTION
        "The class instance number of this entity within the module(card)" 
    ::=  { sts48callocatedEntry 2 }

sts48callocatedSequenceNumber OBJECT-TYPE
    SYNTAX      Unsigned32
    MAX-ACCESS  read-only
    STATUS      current
    DESCRIPTION
        "Sequence number of an individual container within a Virtual Concatenated Group" 
    ::=  { sts48callocatedEntry 3 }

sts48callocatedFacilityType OBJECT-TYPE
    SYNTAX      FspR7InterfaceType
    MAX-ACCESS  read-only
    STATUS      current
    DESCRIPTION
        "The TYPE defines the transport service type as wrapper with wrapper layer termination OR else as payload" 
    ::=  { sts48callocatedEntry 4 }

vc4c8allocatedTable OBJECT-TYPE
    SYNTAX      SEQUENCE OF Vc4c8allocatedEntry
    MAX-ACCESS  not-accessible
    STATUS      current
    DESCRIPTION   ""
    ::=  { gfpServiceConfigAndStatus 12 }

vc4c8allocatedEntry OBJECT-TYPE
    SYNTAX      Vc4c8allocatedEntry
    MAX-ACCESS  not-accessible
    STATUS      current
    DESCRIPTION   ""
    INDEX       {
                  entityIndex
                }
    ::=  { vc4c8allocatedTable 1 }

Vc4c8allocatedEntry ::=  SEQUENCE
  { vc4c8allocatedContainer EntityIndex,
    vc4c8allocatedClassInstanceNumber Integer32,
    vc4c8allocatedSequenceNumber Unsigned32,
    vc4c8allocatedFacilityType FspR7InterfaceType }

vc4c8allocatedContainer OBJECT-TYPE
    SYNTAX      EntityIndex
    MAX-ACCESS  read-only
    STATUS      current
    DESCRIPTION   "The entityIndex of the VC4-8c container."
    ::=  { vc4c8allocatedEntry 1 }

vc4c8allocatedClassInstanceNumber OBJECT-TYPE
    SYNTAX      Integer32 (1..32000 | -2147483648)
    MAX-ACCESS  read-only
    STATUS      current
    DESCRIPTION
        "The class instance number of this entity within the module(card)" 
    ::=  { vc4c8allocatedEntry 2 }

vc4c8allocatedSequenceNumber OBJECT-TYPE
    SYNTAX      Unsigned32
    MAX-ACCESS  read-only
    STATUS      current
    DESCRIPTION
        "Sequence number of an individual container within a Virtual Concatenated Group" 
    ::=  { vc4c8allocatedEntry 3 }

vc4c8allocatedFacilityType OBJECT-TYPE
    SYNTAX      FspR7InterfaceType
    MAX-ACCESS  read-only
    STATUS      current
    DESCRIPTION
        "The TYPE defines the transport service type as wrapper with wrapper layer termination OR else as payload" 
    ::=  { vc4c8allocatedEntry 4 }

vs0allocatedTable OBJECT-TYPE
    SYNTAX      SEQUENCE OF Vs0allocatedEntry
    MAX-ACCESS  not-accessible
    STATUS      current
    DESCRIPTION   ""
    ::=  { gfpServiceConfigAndStatus 13 }

vs0allocatedEntry OBJECT-TYPE
    SYNTAX      Vs0allocatedEntry
    MAX-ACCESS  not-accessible
    STATUS      current
    DESCRIPTION   ""
    INDEX       {
                  entityIndex
                }
    ::=  { vs0allocatedTable 1 }

Vs0allocatedEntry ::=  SEQUENCE
  { vs0allocatedContainer EntityIndex,
    vs0allocatedClassInstanceNumber Integer32,
    vs0allocatedFacilityType FspR7InterfaceType }

vs0allocatedContainer OBJECT-TYPE
    SYNTAX      EntityIndex
    MAX-ACCESS  read-only
    STATUS      current
    DESCRIPTION   "The entityIndex of the VS-1 container."
    ::=  { vs0allocatedEntry 1 }

vs0allocatedClassInstanceNumber OBJECT-TYPE
    SYNTAX      Integer32 (1..32000 | -2147483648)
    MAX-ACCESS  read-only
    STATUS      current
    DESCRIPTION
        "The class instance number of this entity within the module(card)" 
    ::=  { vs0allocatedEntry 2 }

vs0allocatedFacilityType OBJECT-TYPE
    SYNTAX      FspR7InterfaceType
    MAX-ACCESS  read-only
    STATUS      current
    DESCRIPTION
        "The TYPE defines the transport service type as wrapper with wrapper layer termination OR else as payload" 
    ::=  { vs0allocatedEntry 3 }

vc4c16allocatedTable OBJECT-TYPE
    SYNTAX      SEQUENCE OF Vc4c16allocatedEntry
    MAX-ACCESS  not-accessible
    STATUS      current
    DESCRIPTION   ""
    ::=  { gfpServiceConfigAndStatus 14 }

vc4c16allocatedEntry OBJECT-TYPE
    SYNTAX      Vc4c16allocatedEntry
    MAX-ACCESS  not-accessible
    STATUS      current
    DESCRIPTION   ""
    INDEX       {
                  entityIndex
                }
    ::=  { vc4c16allocatedTable 1 }

Vc4c16allocatedEntry ::=  SEQUENCE
  { vc4c16allocatedContainer EntityIndex,
    vc4c16allocatedClassInstanceNumber Integer32,
    vc4c16allocatedFacilityType FspR7InterfaceType }

vc4c16allocatedContainer OBJECT-TYPE
    SYNTAX      EntityIndex
    MAX-ACCESS  read-only
    STATUS      current
    DESCRIPTION   "The entityIndex of the VC4-8c container."
    ::=  { vc4c16allocatedEntry 1 }

vc4c16allocatedClassInstanceNumber OBJECT-TYPE
    SYNTAX      Integer32 (1..32000 | -2147483648)
    MAX-ACCESS  read-only
    STATUS      current
    DESCRIPTION
        "The class instance number of this entity within the module(card)" 
    ::=  { vc4c16allocatedEntry 2 }

vc4c16allocatedFacilityType OBJECT-TYPE
    SYNTAX      FspR7InterfaceType
    MAX-ACCESS  read-only
    STATUS      current
    DESCRIPTION
        "The TYPE defines the transport service type as wrapper with wrapper layer termination OR else as payload" 
    ::=  { vc4c16allocatedEntry 3 }

intraNeConnectionsLastChanged OBJECT-TYPE
    SYNTAX      INTEGER
                {
                  undefined(0),
                  notYetDefined(1)
                }
    MAX-ACCESS  read-only
    STATUS      deprecated
    DESCRIPTION
        "NOT YET DEFINED"
    ::=  { connectionConfigAndStatus 2 }

intraNeConnectionsTable OBJECT-TYPE
    SYNTAX      SEQUENCE OF IntraNeConnectionsEntry
    MAX-ACCESS  not-accessible
    STATUS      current
    DESCRIPTION   "Table containing the physical internal NE Connectivity, i.e. optical fiber connections
         between modules in the same NE."
    ::=  { connectionConfigAndStatus 3 }

intraNeConnectionsEntry OBJECT-TYPE
    SYNTAX      IntraNeConnectionsEntry
    MAX-ACCESS  not-accessible
    STATUS      current
    DESCRIPTION   "Entries in the physical internal Connectivity table."
    INDEX       {
                  entityIndex
                }
    ::=  { intraNeConnectionsTable 1 }

IntraNeConnectionsEntry ::=  SEQUENCE
  { intraNeConnectionsType FspR7TypeConnection,
    intraNeConnectionsEndpointA EntityIndex,
    intraNeConnectionsEndpointB EntityIndex,
    intraNeConnectionsState FspR7StateConnection }

intraNeConnectionsType OBJECT-TYPE
    SYNTAX      FspR7TypeConnection
    MAX-ACCESS  read-only
    STATUS      current
    DESCRIPTION   "Ports can transport uni- or bidirectional traffic."
    ::=  { intraNeConnectionsEntry 1 }

intraNeConnectionsEndpointA OBJECT-TYPE
    SYNTAX      EntityIndex
    MAX-ACCESS  read-only
    STATUS      current
    DESCRIPTION
        "FROM-end of equipment connection (jumper). FROM direction is significant only for 1WAY connections." 
    ::=  { intraNeConnectionsEntry 2 }

intraNeConnectionsEndpointB OBJECT-TYPE
    SYNTAX      EntityIndex
    MAX-ACCESS  read-only
    STATUS      current
    DESCRIPTION
        "TO-end of equipment connection (jumper). TO direction is signaificant only for 1WAY" 
    ::=  { intraNeConnectionsEntry 3 }

intraNeConnectionsState OBJECT-TYPE
    SYNTAX      FspR7StateConnection
    MAX-ACCESS  read-only
    STATUS      current
    DESCRIPTION   "State of the physical connection."
    ::=  { intraNeConnectionsEntry 4 }

crsConnConfigTable OBJECT-TYPE
    SYNTAX      SEQUENCE OF CrsConnConfigEntry
    MAX-ACCESS  not-accessible
    STATUS      current
    DESCRIPTION   "Table cross-connections config."
    ::=  { connectionConfigAndStatus 4 }

crsConnConfigEntry OBJECT-TYPE
    SYNTAX      CrsConnConfigEntry
    MAX-ACCESS  not-accessible
    STATUS      current
    DESCRIPTION   ""
    INDEX       {
                  crsConnDeployProvFrom,
                  crsConnDeployProvTo
                }
    ::=  { crsConnConfigTable 1 }

CrsConnConfigEntry ::=  SEQUENCE
  { crsConnConfigAlias SnmpAdminString,
    crsConnConfigRedLineState FspR7RedLinedState,
    crsConnConfigType FspR7InterfaceType,
    crsConnConfigPathNode FspR7PathNode,
    crsConnConfigTunnelAid SnmpAdminString }

crsConnConfigAlias OBJECT-TYPE
    SYNTAX      SnmpAdminString
    MAX-ACCESS  read-write
    STATUS      current
    DESCRIPTION   ""
    ::=  { crsConnConfigEntry 1 }

crsConnConfigRedLineState OBJECT-TYPE
    SYNTAX      FspR7RedLinedState
    MAX-ACCESS  read-write
    STATUS      current
    DESCRIPTION   ""
    ::=  { crsConnConfigEntry 2 }

crsConnConfigType OBJECT-TYPE
    SYNTAX      FspR7InterfaceType
    MAX-ACCESS  read-write
    STATUS      deprecated
    DESCRIPTION   ""
    ::=  { crsConnConfigEntry 3 }

crsConnConfigPathNode OBJECT-TYPE
    SYNTAX      FspR7PathNode
    MAX-ACCESS  read-write
    STATUS      current
    DESCRIPTION   "Node count along a signal path on a unidirectional basis from the client signal
         ingress to egress"
    ::=  { crsConnConfigEntry 4 }

crsConnConfigTunnelAid OBJECT-TYPE
    SYNTAX      SnmpAdminString
    MAX-ACCESS  read-write
    STATUS      deprecated
    DESCRIPTION   ""
    ::=  { crsConnConfigEntry 5 }

crsConnDataTable OBJECT-TYPE
    SYNTAX      SEQUENCE OF CrsConnDataEntry
    MAX-ACCESS  not-accessible
    STATUS      current
    DESCRIPTION   "Table cross-connections data."
    ::=  { connectionConfigAndStatus 5 }

crsConnDataEntry OBJECT-TYPE
    SYNTAX      CrsConnDataEntry
    MAX-ACCESS  not-accessible
    STATUS      current
    DESCRIPTION   ""
    INDEX       {
                  crsConnDeployProvFrom,
                  crsConnDeployProvTo
                }
    ::=  { crsConnDataTable 1 }

CrsConnDataEntry ::=  SEQUENCE
  { crsConnDataCrsType FspR7TypeCrs,
    crsConnDataType FspR7InterfaceType,
    crsConnDataConn FspR7Conn,
    crsConnDataCrsFunction FspR7FunctionCrs,
    crsConnDataOper FspR7OperState,
    crsConnDataEntityOutage FspR7NoYes,
    crsConnDataTunnelId SnmpAdminString,
    crsConnDataTunnelAid SnmpAdminString,
    crsConnDataIngressTid SnmpAdminString,
    crsConnDataIngressNodeIp IpAddress,
    crsConnDataChannelSpacing FspR7ChannelSpacing }

crsConnDataCrsType OBJECT-TYPE
    SYNTAX      FspR7TypeCrs
    MAX-ACCESS  read-only
    STATUS      current
    DESCRIPTION   ""
    ::=  { crsConnDataEntry 1 }

crsConnDataType OBJECT-TYPE
    SYNTAX      FspR7InterfaceType
    MAX-ACCESS  read-only
    STATUS      current
    DESCRIPTION   ""
    ::=  { crsConnDataEntry 2 }

crsConnDataConn OBJECT-TYPE
    SYNTAX      FspR7Conn
    MAX-ACCESS  read-only
    STATUS      current
    DESCRIPTION   "Connection Direction"
    ::=  { crsConnDataEntry 3 }

crsConnDataCrsFunction OBJECT-TYPE
    SYNTAX      FspR7FunctionCrs
    MAX-ACCESS  read-only
    STATUS      current
    DESCRIPTION   ""
    ::=  { crsConnDataEntry 4 }

crsConnDataOper OBJECT-TYPE
    SYNTAX      FspR7OperState
    MAX-ACCESS  read-only
    STATUS      current
    DESCRIPTION   ""
    ::=  { crsConnDataEntry 5 }

crsConnDataEntityOutage OBJECT-TYPE
    SYNTAX      FspR7NoYes
    MAX-ACCESS  read-only
    STATUS      current
    DESCRIPTION   ""
    ::=  { crsConnDataEntry 6 }

crsConnDataTunnelId OBJECT-TYPE
    SYNTAX      SnmpAdminString
    MAX-ACCESS  read-only
    STATUS      current
    DESCRIPTION   ""
    ::=  { crsConnDataEntry 7 }

crsConnDataTunnelAid OBJECT-TYPE
    SYNTAX      SnmpAdminString
    MAX-ACCESS  read-only
    STATUS      current
    DESCRIPTION   ""
    ::=  { crsConnDataEntry 8 }

crsConnDataIngressTid OBJECT-TYPE
    SYNTAX      SnmpAdminString
    MAX-ACCESS  read-only
    STATUS      current
    DESCRIPTION   ""
    ::=  { crsConnDataEntry 9 }

crsConnDataIngressNodeIp OBJECT-TYPE
    SYNTAX      IpAddress
    MAX-ACCESS  read-only
    STATUS      current
    DESCRIPTION   ""
    ::=  { crsConnDataEntry 10 }

crsConnDataChannelSpacing OBJECT-TYPE
    SYNTAX      FspR7ChannelSpacing
    MAX-ACCESS  read-only
    STATUS      current
    DESCRIPTION
        "ITU Grid channel spacing" 
    ::=  { crsConnDataEntry 11 }

crsConnWdmConfigTable OBJECT-TYPE
    SYNTAX      SEQUENCE OF CrsConnWdmConfigEntry
    MAX-ACCESS  not-accessible
    STATUS      current
    DESCRIPTION   "Table cross-connections config."
    ::=  { connectionConfigAndStatus 6 }

crsConnWdmConfigEntry OBJECT-TYPE
    SYNTAX      CrsConnWdmConfigEntry
    MAX-ACCESS  not-accessible
    STATUS      current
    DESCRIPTION   ""
    INDEX       {
                  crsConnDeployProvFrom,
                  crsConnDeployProvTo
                }
    ::=  { crsConnWdmConfigTable 1 }

CrsConnWdmConfigEntry ::=  SEQUENCE
  { crsConnWdmConfigAlias SnmpAdminString,
    crsConnWdmConfigRedLineState FspR7RedLinedState,
    crsConnWdmConfigType FspR7InterfaceType,
    crsConnWdmConfigTunnelAid SnmpAdminString,
    crsConnWdmConfigPathNode FspR7PathNode }

crsConnWdmConfigAlias OBJECT-TYPE
    SYNTAX      SnmpAdminString
    MAX-ACCESS  read-write
    STATUS      current
    DESCRIPTION   ""
    ::=  { crsConnWdmConfigEntry 1 }

crsConnWdmConfigRedLineState OBJECT-TYPE
    SYNTAX      FspR7RedLinedState
    MAX-ACCESS  read-write
    STATUS      current
    DESCRIPTION   ""
    ::=  { crsConnWdmConfigEntry 2 }

crsConnWdmConfigType OBJECT-TYPE
    SYNTAX      FspR7InterfaceType
    MAX-ACCESS  read-write
    STATUS      current
    DESCRIPTION   ""
    ::=  { crsConnWdmConfigEntry 3 }

crsConnWdmConfigTunnelAid OBJECT-TYPE
    SYNTAX      SnmpAdminString
    MAX-ACCESS  read-write
    STATUS      deprecated
    DESCRIPTION   ""
    ::=  { crsConnWdmConfigEntry 4 }

crsConnWdmConfigPathNode OBJECT-TYPE
    SYNTAX      FspR7PathNode
    MAX-ACCESS  read-write
    STATUS      current
    DESCRIPTION   "Node count along a signal path on a unidirectional basis from the client signal
         ingress to egress"
    ::=  { crsConnWdmConfigEntry 5 }

crsConnWdmDataTable OBJECT-TYPE
    SYNTAX      SEQUENCE OF CrsConnWdmDataEntry
    MAX-ACCESS  not-accessible
    STATUS      current
    DESCRIPTION   "Table cross-connections data."
    ::=  { connectionConfigAndStatus 7 }

crsConnWdmDataEntry OBJECT-TYPE
    SYNTAX      CrsConnWdmDataEntry
    MAX-ACCESS  not-accessible
    STATUS      current
    DESCRIPTION   ""
    INDEX       {
                  crsConnDeployProvFrom,
                  crsConnDeployProvTo
                }
    ::=  { crsConnWdmDataTable 1 }

CrsConnWdmDataEntry ::=  SEQUENCE
  { crsConnWdmDataCrsType FspR7TypeCrs,
    crsConnWdmDataType FspR7InterfaceType,
    crsConnWdmDataConn FspR7Conn,
    crsConnWdmDataCrsFunction FspR7FunctionCrs,
    crsConnWdmDataOper FspR7OperState,
    crsConnWdmDataEntityOutage FspR7NoYes,
    crsConnWdmDataTunnelAid SnmpAdminString,
    crsConnWdmDataIngressTid SnmpAdminString,
    crsConnWdmDataIngressNodeIp IpAddress,
    crsConnWdmDataChannelSpacing FspR7ChannelSpacing }

crsConnWdmDataCrsType OBJECT-TYPE
    SYNTAX      FspR7TypeCrs
    MAX-ACCESS  read-only
    STATUS      current
    DESCRIPTION   ""
    ::=  { crsConnWdmDataEntry 1 }

crsConnWdmDataType OBJECT-TYPE
    SYNTAX      FspR7InterfaceType
    MAX-ACCESS  read-only
    STATUS      current
    DESCRIPTION   ""
    ::=  { crsConnWdmDataEntry 2 }

crsConnWdmDataConn OBJECT-TYPE
    SYNTAX      FspR7Conn
    MAX-ACCESS  read-only
    STATUS      current
    DESCRIPTION   "Connection Direction"
    ::=  { crsConnWdmDataEntry 3 }

crsConnWdmDataCrsFunction OBJECT-TYPE
    SYNTAX      FspR7FunctionCrs
    MAX-ACCESS  read-only
    STATUS      current
    DESCRIPTION   ""
    ::=  { crsConnWdmDataEntry 4 }

crsConnWdmDataOper OBJECT-TYPE
    SYNTAX      FspR7OperState
    MAX-ACCESS  read-only
    STATUS      current
    DESCRIPTION   ""
    ::=  { crsConnWdmDataEntry 5 }

crsConnWdmDataEntityOutage OBJECT-TYPE
    SYNTAX      FspR7NoYes
    MAX-ACCESS  read-only
    STATUS      current
    DESCRIPTION   ""
    ::=  { crsConnWdmDataEntry 6 }

crsConnWdmDataTunnelAid OBJECT-TYPE
    SYNTAX      SnmpAdminString
    MAX-ACCESS  read-only
    STATUS      current
    DESCRIPTION   ""
    ::=  { crsConnWdmDataEntry 7 }

crsConnWdmDataIngressTid OBJECT-TYPE
    SYNTAX      SnmpAdminString
    MAX-ACCESS  read-only
    STATUS      current
    DESCRIPTION   ""
    ::=  { crsConnWdmDataEntry 8 }

crsConnWdmDataIngressNodeIp OBJECT-TYPE
    SYNTAX      IpAddress
    MAX-ACCESS  read-only
    STATUS      current
    DESCRIPTION   ""
    ::=  { crsConnWdmDataEntry 9 }

crsConnWdmDataChannelSpacing OBJECT-TYPE
    SYNTAX      FspR7ChannelSpacing
    MAX-ACCESS  read-only
    STATUS      current
    DESCRIPTION
        "ITU Grid channel spacing" 
    ::=  { crsConnWdmDataEntry 10 }

physicalTerminationPointTable OBJECT-TYPE
    SYNTAX      SEQUENCE OF PhysicalTerminationPointEntry
    MAX-ACCESS  not-accessible
    STATUS      current
    DESCRIPTION   ""
    ::=  { connectionConfigAndStatus 8 }

physicalTerminationPointEntry OBJECT-TYPE
    SYNTAX      PhysicalTerminationPointEntry
    MAX-ACCESS  not-accessible
    STATUS      current
    DESCRIPTION   ""
    INDEX       {
                  entityIndex
                }
    ::=  { physicalTerminationPointTable 1 }

PhysicalTerminationPointEntry ::=  SEQUENCE
  { physicalTerminationPointIndex EntityIndex }

physicalTerminationPointIndex OBJECT-TYPE
    SYNTAX      EntityIndex
    MAX-ACCESS  read-only
    STATUS      current
    DESCRIPTION   ""
    ::=  { physicalTerminationPointEntry 1 }

controlPlaneWdmConfigTable OBJECT-TYPE
    SYNTAX      SEQUENCE OF ControlPlaneWdmConfigEntry
    MAX-ACCESS  not-accessible
    STATUS      current
    DESCRIPTION   ""
    ::=  { controlPlaneConfigAndStatus 1 }

controlPlaneWdmConfigEntry OBJECT-TYPE
    SYNTAX      ControlPlaneWdmConfigEntry
    MAX-ACCESS  not-accessible
    STATUS      current
    DESCRIPTION   ""
    INDEX       {
                  controlPlaneWdmEntityIndex
                }
    ::=  { controlPlaneWdmConfigTable 1 }

ControlPlaneWdmConfigEntry ::=  SEQUENCE
  { controlPlaneWdmConfigCtmConfigFlag Unsigned32,
    controlPlaneWdmConfigCtmTraceDetail Unsigned32,
    controlPlaneWdmConfigCtmSetupTimeout Unsigned32,
    controlPlaneWdmConfigCtmShutdownTimeout Unsigned32,
    controlPlaneWdmConfigCtmRetryWait Unsigned32,
    controlPlaneWdmConfigCtmRetryWaitMultiplier Unsigned32,
    controlPlaneWdmConfigCtmMaximumRetryWait Unsigned32,
    controlPlaneWdmConfigCtmMaximumRetryNumber Unsigned32,
    controlPlaneWdmConfigRaConfigFlag Unsigned32,
    controlPlaneWdmConfigRaTraceDetail Unsigned32,
    controlPlaneWdmConfigRaAlarmActivationTime Unsigned32,
    controlPlaneWdmConfigCmConfigFlag Unsigned32,
    controlPlaneWdmConfigCmTraceDetail Unsigned32,
    controlPlaneWdmConfigCmAlarmActivationTime Unsigned32,
    controlPlaneWdmConfigCmFisFrsTimeout Unsigned32,
    controlPlaneWdmConfigCmCrankBackTimeout Unsigned32,
    controlPlaneWdmConfigCdbConfigFlag Unsigned32,
    controlPlaneWdmConfigCdbDetail Unsigned32,
    controlPlaneWdmConfigCdbMaxSize Unsigned32,
    controlPlaneWdmConfigRsvpConfigFlag Unsigned32,
    controlPlaneWdmConfigRsvpMaxExpRestartTime Counter64String,
    controlPlaneWdmConfigRsvpMaxExpRecoveryTime Unsigned32,
    controlPlaneWdmConfigTedbConfigFlag Unsigned32,
    controlPlaneWdmConfigTedbTraceDetail Unsigned32,
    controlPlaneWdmConfigTedbMaxSize Unsigned32,
    controlPlaneWdmConfigTedbRouterId IpAddress,
    controlPlaneWdmConfigTedbMinAdvertWait Unsigned32,
    controlPlaneWdmConfigNaasConfigFlag Unsigned32,
    controlPlaneWdmConfigNaasTraceDetail Unsigned32,
    controlPlaneWdmConfigNaasMaxSize Unsigned32,
    controlPlaneWdmConfigNaasAdvertWait Unsigned32,
    controlPlaneWdmConfigPcConfigFlag Unsigned32,
    controlPlaneWdmConfigPcTraceDetail Unsigned32,
    controlPlaneWdmConfigCdConfigFlag Unsigned32,
    controlPlaneWdmConfigCdTraceDetail Unsigned32,
    controlPlaneWdmConfigCdResyncTimeout Unsigned32,
    controlPlaneWdmConfigRmConfigFlag Unsigned32,
    controlPlaneWdmConfigRmTraceDetail Unsigned32,
    controlPlaneWdmConfigRmTraceTarget Unsigned32,
    controlPlaneWdmConfigWaitToRestore Unsigned32 }

controlPlaneWdmConfigCtmConfigFlag OBJECT-TYPE
    SYNTAX      Unsigned32
    MAX-ACCESS  read-write
    STATUS      current
    DESCRIPTION   "Label Switched Path Edge Component' Configuration Bitfield"
    ::=  { controlPlaneWdmConfigEntry 1 }

controlPlaneWdmConfigCtmTraceDetail OBJECT-TYPE
    SYNTAX      Unsigned32
    MAX-ACCESS  read-write
    STATUS      current
    DESCRIPTION   "Label Switched Path Edge Component' Trace Detail"
    ::=  { controlPlaneWdmConfigEntry 2 }

controlPlaneWdmConfigCtmSetupTimeout OBJECT-TYPE
    SYNTAX      Unsigned32 
    UNITS       "s"
    MAX-ACCESS  read-write
    STATUS      current
    DESCRIPTION   "Label Switched Path Edge Component' Set-Up Timeout"
    ::=  { controlPlaneWdmConfigEntry 3 }

controlPlaneWdmConfigCtmShutdownTimeout OBJECT-TYPE
    SYNTAX      Unsigned32 
    UNITS       "s"
    MAX-ACCESS  read-write
    STATUS      current
    DESCRIPTION   "Label Switched Path Edge Component' Shut-Down Timeout"
    ::=  { controlPlaneWdmConfigEntry 4 }

controlPlaneWdmConfigCtmRetryWait OBJECT-TYPE
    SYNTAX      Unsigned32 
    UNITS       "s"
    MAX-ACCESS  read-write
    STATUS      current
    DESCRIPTION   "Label Switched Path Edge Component' Initialization Retry Wait"
    ::=  { controlPlaneWdmConfigEntry 5 }

controlPlaneWdmConfigCtmRetryWaitMultiplier OBJECT-TYPE
    SYNTAX      Unsigned32
    MAX-ACCESS  read-write
    STATUS      current
    DESCRIPTION   "Label Switched Path Edge Component' Initialization Retry Wait Multiplier"
    ::=  { controlPlaneWdmConfigEntry 6 }

controlPlaneWdmConfigCtmMaximumRetryWait OBJECT-TYPE
    SYNTAX      Unsigned32 
    UNITS       "s"
    MAX-ACCESS  read-write
    STATUS      current
    DESCRIPTION   "Label Switched Path Edge Component' Initialization Maximum Retry Wait"
    ::=  { controlPlaneWdmConfigEntry 7 }

controlPlaneWdmConfigCtmMaximumRetryNumber OBJECT-TYPE
    SYNTAX      Unsigned32
    MAX-ACCESS  read-write
    STATUS      current
    DESCRIPTION   "Label Switched Path Edge Component' Initialization Maximum Retry Number"
    ::=  { controlPlaneWdmConfigEntry 8 }

controlPlaneWdmConfigRaConfigFlag OBJECT-TYPE
    SYNTAX      Unsigned32
    MAX-ACCESS  read-write
    STATUS      current
    DESCRIPTION   "Resource Allocator Configuration Bitfield"
    ::=  { controlPlaneWdmConfigEntry 9 }

controlPlaneWdmConfigRaTraceDetail OBJECT-TYPE
    SYNTAX      Unsigned32
    MAX-ACCESS  read-write
    STATUS      current
    DESCRIPTION   "Resource Allocator Trace Detail"
    ::=  { controlPlaneWdmConfigEntry 10 }

controlPlaneWdmConfigRaAlarmActivationTime OBJECT-TYPE
    SYNTAX      Unsigned32 
    UNITS       "s"
    MAX-ACCESS  read-write
    STATUS      current
    DESCRIPTION   "Resource Allocator Alarm Activation Time"
    ::=  { controlPlaneWdmConfigEntry 11 }

controlPlaneWdmConfigCmConfigFlag OBJECT-TYPE
    SYNTAX      Unsigned32
    MAX-ACCESS  read-write
    STATUS      current
    DESCRIPTION   "GMPLS Tunnel Manager Component' Configuration Bitfield"
    ::=  { controlPlaneWdmConfigEntry 12 }

controlPlaneWdmConfigCmTraceDetail OBJECT-TYPE
    SYNTAX      Unsigned32
    MAX-ACCESS  read-write
    STATUS      current
    DESCRIPTION   "GMPLS Tunnel Manager Component' Trace Detail"
    ::=  { controlPlaneWdmConfigEntry 13 }

controlPlaneWdmConfigCmAlarmActivationTime OBJECT-TYPE
    SYNTAX      Unsigned32 
    UNITS       "s"
    MAX-ACCESS  read-write
    STATUS      current
    DESCRIPTION   "GMPLS Tunnel Manager Component' Alarm Activation Time"
    ::=  { controlPlaneWdmConfigEntry 14 }

controlPlaneWdmConfigCmFisFrsTimeout OBJECT-TYPE
    SYNTAX      Unsigned32 
    UNITS       "s"
    MAX-ACCESS  read-write
    STATUS      current
    DESCRIPTION   "GMPLS Tunnel Manager Component' FIS-FRS Timeout"
    ::=  { controlPlaneWdmConfigEntry 15 }

controlPlaneWdmConfigCmCrankBackTimeout OBJECT-TYPE
    SYNTAX      Unsigned32 
    UNITS       "s"
    MAX-ACCESS  read-write
    STATUS      current
    DESCRIPTION   "GMPLS Tunnel Manager Component' Crank-Back Timeout"
    ::=  { controlPlaneWdmConfigEntry 16 }

controlPlaneWdmConfigCdbConfigFlag OBJECT-TYPE
    SYNTAX      Unsigned32
    MAX-ACCESS  read-write
    STATUS      current
    DESCRIPTION   "Label Swithed Path Database Component' Configuration Bitfield"
    ::=  { controlPlaneWdmConfigEntry 17 }

controlPlaneWdmConfigCdbDetail OBJECT-TYPE
    SYNTAX      Unsigned32
    MAX-ACCESS  read-write
    STATUS      current
    DESCRIPTION   "Label Swithed Path Database Component' Trace Detail"
    ::=  { controlPlaneWdmConfigEntry 18 }

controlPlaneWdmConfigCdbMaxSize OBJECT-TYPE
    SYNTAX      Unsigned32
    MAX-ACCESS  read-write
    STATUS      current
    DESCRIPTION   "Label Swithed Path Database Component' Maximum Size; 0 impiles no limit"
    ::=  { controlPlaneWdmConfigEntry 19 }

controlPlaneWdmConfigRsvpConfigFlag OBJECT-TYPE
    SYNTAX      Unsigned32
    MAX-ACCESS  read-write
    STATUS      current
    DESCRIPTION   "Resource Reservation Protocol Component' Configuration Bitfield"
    ::=  { controlPlaneWdmConfigEntry 20 }

controlPlaneWdmConfigRsvpMaxExpRestartTime OBJECT-TYPE
    SYNTAX      Counter64String 
    UNITS       "ms"
    MAX-ACCESS  read-write
    STATUS      current
    DESCRIPTION   "Maximum Expected Resource Reservation Protocol Component' Restart Time"
    ::=  { controlPlaneWdmConfigEntry 21 }

controlPlaneWdmConfigRsvpMaxExpRecoveryTime OBJECT-TYPE
    SYNTAX      Unsigned32 
    UNITS       "ms"
    MAX-ACCESS  read-write
    STATUS      current
    DESCRIPTION   "Maximum Expected Resource Reservation Protocol Component' Recovery Time"
    ::=  { controlPlaneWdmConfigEntry 22 }

controlPlaneWdmConfigTedbConfigFlag OBJECT-TYPE
    SYNTAX      Unsigned32
    MAX-ACCESS  read-write
    STATUS      current
    DESCRIPTION   "Traffic Engineering Component' Database Configuration Bitfield"
    ::=  { controlPlaneWdmConfigEntry 23 }

controlPlaneWdmConfigTedbTraceDetail OBJECT-TYPE
    SYNTAX      Unsigned32
    MAX-ACCESS  read-write
    STATUS      current
    DESCRIPTION   "Traffic Engineering Component' Database Trace Detail"
    ::=  { controlPlaneWdmConfigEntry 24 }

controlPlaneWdmConfigTedbMaxSize OBJECT-TYPE
    SYNTAX      Unsigned32
    MAX-ACCESS  read-write
    STATUS      current
    DESCRIPTION   "Traffic Engineering Component' Database Maximum Size"
    ::=  { controlPlaneWdmConfigEntry 25 }

controlPlaneWdmConfigTedbRouterId OBJECT-TYPE
    SYNTAX      IpAddress
    MAX-ACCESS  read-write
    STATUS      current
    DESCRIPTION   "Traffic Engineering Component' Router ID"
    ::=  { controlPlaneWdmConfigEntry 26 }

controlPlaneWdmConfigTedbMinAdvertWait OBJECT-TYPE
    SYNTAX      Unsigned32 
    UNITS       "s"
    MAX-ACCESS  read-write
    STATUS      current
    DESCRIPTION   "Traffic Engineering Component' Minimum Advertisement Wait"
    ::=  { controlPlaneWdmConfigEntry 27 }

controlPlaneWdmConfigNaasConfigFlag OBJECT-TYPE
    SYNTAX      Unsigned32
    MAX-ACCESS  read-write
    STATUS      current
    DESCRIPTION   "Node Attribute Advertising Service Database Configuration Bitfield"
    ::=  { controlPlaneWdmConfigEntry 28 }

controlPlaneWdmConfigNaasTraceDetail OBJECT-TYPE
    SYNTAX      Unsigned32
    MAX-ACCESS  read-write
    STATUS      current
    DESCRIPTION   "Node Attribute Advertising Service Database Trace Detail"
    ::=  { controlPlaneWdmConfigEntry 29 }

controlPlaneWdmConfigNaasMaxSize OBJECT-TYPE
    SYNTAX      Unsigned32
    MAX-ACCESS  read-write
    STATUS      current
    DESCRIPTION   "Node Attribute Advertising Service Database Maximum Size"
    ::=  { controlPlaneWdmConfigEntry 30 }

controlPlaneWdmConfigNaasAdvertWait OBJECT-TYPE
    SYNTAX      Unsigned32 
    UNITS       "s"
    MAX-ACCESS  read-write
    STATUS      current
    DESCRIPTION   "Node Attribute Advertising Service Database Advertisement Wait"
    ::=  { controlPlaneWdmConfigEntry 31 }

controlPlaneWdmConfigPcConfigFlag OBJECT-TYPE
    SYNTAX      Unsigned32
    MAX-ACCESS  read-write
    STATUS      current
    DESCRIPTION   "Path Computation Component' Configuration Bitfield"
    ::=  { controlPlaneWdmConfigEntry 32 }

controlPlaneWdmConfigPcTraceDetail OBJECT-TYPE
    SYNTAX      Unsigned32
    MAX-ACCESS  read-write
    STATUS      current
    DESCRIPTION   "Path Computation Component' Trace Detail."
    ::=  { controlPlaneWdmConfigEntry 33 }

controlPlaneWdmConfigCdConfigFlag OBJECT-TYPE
    SYNTAX      Unsigned32
    MAX-ACCESS  read-write
    STATUS      current
    DESCRIPTION   "Configuration Data Component' Configuration Bitfield"
    ::=  { controlPlaneWdmConfigEntry 34 }

controlPlaneWdmConfigCdTraceDetail OBJECT-TYPE
    SYNTAX      Unsigned32
    MAX-ACCESS  read-write
    STATUS      current
    DESCRIPTION   "Configuration Data Component' Trace Detail"
    ::=  { controlPlaneWdmConfigEntry 35 }

controlPlaneWdmConfigCdResyncTimeout OBJECT-TYPE
    SYNTAX      Unsigned32
    MAX-ACCESS  read-write
    STATUS      current
    DESCRIPTION   "Configuration Data Component' Resync Timeout"
    ::=  { controlPlaneWdmConfigEntry 36 }

controlPlaneWdmConfigRmConfigFlag OBJECT-TYPE
    SYNTAX      Unsigned32
    MAX-ACCESS  read-write
    STATUS      current
    DESCRIPTION   "Resource Management Component' Configuration Bitfield"
    ::=  { controlPlaneWdmConfigEntry 37 }

controlPlaneWdmConfigRmTraceDetail OBJECT-TYPE
    SYNTAX      Unsigned32
    MAX-ACCESS  read-write
    STATUS      current
    DESCRIPTION   "Resource Management Component' Trace Detail"
    ::=  { controlPlaneWdmConfigEntry 38 }

controlPlaneWdmConfigRmTraceTarget OBJECT-TYPE
    SYNTAX      Unsigned32
    MAX-ACCESS  read-write
    STATUS      current
    DESCRIPTION   "Resource Management Component' Trace Target"
    ::=  { controlPlaneWdmConfigEntry 39 }

controlPlaneWdmConfigWaitToRestore OBJECT-TYPE
    SYNTAX      Unsigned32 (5..12 | 4294967295) 
    UNITS       "min"
    MAX-ACCESS  read-write
    STATUS      current
    DESCRIPTION
        "Wait to Restore Timer value" 
    ::=  { controlPlaneWdmConfigEntry 40 }

controlPlaneWdmDataTable OBJECT-TYPE
    SYNTAX      SEQUENCE OF ControlPlaneWdmDataEntry
    MAX-ACCESS  not-accessible
    STATUS      current
    DESCRIPTION   ""
    ::=  { controlPlaneConfigAndStatus 2 }

controlPlaneWdmDataEntry OBJECT-TYPE
    SYNTAX      ControlPlaneWdmDataEntry
    MAX-ACCESS  not-accessible
    STATUS      current
    DESCRIPTION   ""
    INDEX       {
                  controlPlaneWdmEntityIndex
                }
    ::=  { controlPlaneWdmDataTable 1 }

ControlPlaneWdmDataEntry ::=  SEQUENCE
  { controlPlaneWdmDataCtmAlias SnmpAdminString,
    controlPlaneWdmDataRaAlias SnmpAdminString,
    controlPlaneWdmDataCmAlias SnmpAdminString,
    controlPlaneWdmDataCdbAlias SnmpAdminString,
    controlPlaneWdmDataTedbAlias SnmpAdminString,
    controlPlaneWdmDataNaasAlias SnmpAdminString,
    controlPlaneWdmDataPcAlias SnmpAdminString,
    controlPlaneWdmDataRsvpAlias SnmpAdminString,
    controlPlaneWdmDataCdAlias SnmpAdminString,
    controlPlaneWdmDataRmAlias SnmpAdminString,
    controlPlaneWdmDataNodeNameSyntax FspR7NodeId }

controlPlaneWdmDataCtmAlias OBJECT-TYPE
    SYNTAX      SnmpAdminString
    MAX-ACCESS  read-only
    STATUS      current
    DESCRIPTION   "Label Switched Path Edge Component Component' Base Name"
    ::=  { controlPlaneWdmDataEntry 1 }

controlPlaneWdmDataRaAlias OBJECT-TYPE
    SYNTAX      SnmpAdminString
    MAX-ACCESS  read-only
    STATUS      current
    DESCRIPTION   "Resource Allocator Component' Base Name"
    ::=  { controlPlaneWdmDataEntry 2 }

controlPlaneWdmDataCmAlias OBJECT-TYPE
    SYNTAX      SnmpAdminString
    MAX-ACCESS  read-only
    STATUS      current
    DESCRIPTION   "GMPLS Tunnel Manager Component' Base Name"
    ::=  { controlPlaneWdmDataEntry 3 }

controlPlaneWdmDataCdbAlias OBJECT-TYPE
    SYNTAX      SnmpAdminString
    MAX-ACCESS  read-only
    STATUS      current
    DESCRIPTION   "Label Swithed Path Database Component' Base Name"
    ::=  { controlPlaneWdmDataEntry 4 }

controlPlaneWdmDataTedbAlias OBJECT-TYPE
    SYNTAX      SnmpAdminString
    MAX-ACCESS  read-only
    STATUS      current
    DESCRIPTION   "Traffic Engineering Component' Database Name"
    ::=  { controlPlaneWdmDataEntry 5 }

controlPlaneWdmDataNaasAlias OBJECT-TYPE
    SYNTAX      SnmpAdminString
    MAX-ACCESS  read-only
    STATUS      current
    DESCRIPTION   "Node Attribute Advertising Service Database Component' Base Name"
    ::=  { controlPlaneWdmDataEntry 6 }

controlPlaneWdmDataPcAlias OBJECT-TYPE
    SYNTAX      SnmpAdminString
    MAX-ACCESS  read-only
    STATUS      current
    DESCRIPTION   "Path Computation Engine Component' Base Name"
    ::=  { controlPlaneWdmDataEntry 7 }

controlPlaneWdmDataRsvpAlias OBJECT-TYPE
    SYNTAX      SnmpAdminString
    MAX-ACCESS  read-only
    STATUS      current
    DESCRIPTION   "Resource Reservation Protocol Component' Base Name"
    ::=  { controlPlaneWdmDataEntry 8 }

controlPlaneWdmDataCdAlias OBJECT-TYPE
    SYNTAX      SnmpAdminString
    MAX-ACCESS  read-only
    STATUS      current
    DESCRIPTION   "Configuration Data Component' Base Name"
    ::=  { controlPlaneWdmDataEntry 9 }

controlPlaneWdmDataRmAlias OBJECT-TYPE
    SYNTAX      SnmpAdminString
    MAX-ACCESS  read-only
    STATUS      current
    DESCRIPTION   "Resource Management Component' Base Name"
    ::=  { controlPlaneWdmDataEntry 10 }

controlPlaneWdmDataNodeNameSyntax OBJECT-TYPE
    SYNTAX      FspR7NodeId
    MAX-ACCESS  read-only
    STATUS      deprecated
    DESCRIPTION   "Node Name Syntax"
    ::=  { controlPlaneWdmDataEntry 11 }

tunnelWdmConfigTable OBJECT-TYPE
    SYNTAX      SEQUENCE OF TunnelWdmConfigEntry
    MAX-ACCESS  not-accessible
    STATUS      current
    DESCRIPTION   ""
    ::=  { controlPlaneConfigAndStatus 3 }

tunnelWdmConfigEntry OBJECT-TYPE
    SYNTAX      TunnelWdmConfigEntry
    MAX-ACCESS  not-accessible
    STATUS      current
    DESCRIPTION   ""
    INDEX       {
                  controlPlaneWdmEntityIndex
                }
    ::=  { tunnelWdmConfigTable 1 }

TunnelWdmConfigEntry ::=  SEQUENCE
  { tunnelWdmConfigAlias SnmpAdminString,
    tunnelWdmConfigFacilityType FspR7InterfaceType,
    tunnelWdmConfigTerminationLevel OhTerminationLevel,
    tunnelWdmConfigFecType FspR7FecType,
    tunnelWdmConfigStuff FspR7Stuff,
    tunnelWdmConfigProvisionedPaths SnmpAdminString,
    tunnelWdmConfigRecoveryType FspR7CpProtectionType,
    tunnelWdmConfigPin FspR7CpPinning,
    tunnelWdmConfigInitiateEqualization FspR7InitEqualization,
    tunnelWdmConfigAbortProcess FspR7CpAbortProcess,
    tunnelWdmConfigAdminModifier FspR7CommandModifier,
    tunnelWdmConfigCommand FspR7CpCommand,
    tunnelWdmConfigRestorationType FspR7CpRestorationType,
    tunnelWdmConfigSubLayer FspR7SubLayer,
    tunnelWdmConfigMonitorEntities FspR7EnableDisable,
    tunnelWdmConfigSubLayerEncoding FspR7SubLayerEncoding,
    tunnelWdmConfigPceMode FspR7PceMode,
    tunnelWdmConfigOperateReversion FspR7CpOperateReversion,
    tunnelWdmConfigReversionType FspR7CpReversionType,
    tunnelWdmConfigRestorationMode FspR7CpRestorationMode,
    tunnelWdmConfigRestPathsNoProv Unsigned32,
    tunnelWdmConfigRestorationPaths SnmpAdminString,
    tunnelWdmConfigRestorationPathsComputed SnmpAdminString,
    tunnelWdmConfigResetRetainedFailureIndications FspR7ResetRfi,
    tunnelWdmConfigExcludedPaths SnmpAdminString,
    tunnelWdmConfigSavePA FspR7NoYes,
    tunnelWdmConfigDvPaths SnmpAdminString,
    tunnelWdmConfigPreferPcs FspR7YesNo,
    tunnelWdmConfigEroScope SnmpAdminString,
    tunnelWdmConfigEroLifeCycle SnmpAdminString,
    tunnelWdmConfigXroScope SnmpAdminString,
    tunnelWdmConfigXroLifeCycle SnmpAdminString,
    tunnelWdmConfigFendTerm OhTerminationLevel }

tunnelWdmConfigAlias OBJECT-TYPE
    SYNTAX      SnmpAdminString
    MAX-ACCESS  read-write
    STATUS      current
    DESCRIPTION   "Alias."
    ::=  { tunnelWdmConfigEntry 1 }

tunnelWdmConfigFacilityType OBJECT-TYPE
    SYNTAX      FspR7InterfaceType
    MAX-ACCESS  read-write
    STATUS      current
    DESCRIPTION   ""
    ::=  { tunnelWdmConfigEntry 2 }

tunnelWdmConfigTerminationLevel OBJECT-TYPE
    SYNTAX      OhTerminationLevel
    MAX-ACCESS  read-write
    STATUS      current
    DESCRIPTION   ""
    ::=  { tunnelWdmConfigEntry 3 }

tunnelWdmConfigFecType OBJECT-TYPE
    SYNTAX      FspR7FecType
    MAX-ACCESS  read-write
    STATUS      current
    DESCRIPTION   ""
    ::=  { tunnelWdmConfigEntry 4 }

tunnelWdmConfigStuff OBJECT-TYPE
    SYNTAX      FspR7Stuff
    MAX-ACCESS  read-write
    STATUS      current
    DESCRIPTION   ""
    ::=  { tunnelWdmConfigEntry 5 }

tunnelWdmConfigProvisionedPaths OBJECT-TYPE
    SYNTAX      SnmpAdminString
    MAX-ACCESS  read-write
    STATUS      current
    DESCRIPTION   ""
    ::=  { tunnelWdmConfigEntry 6 }

tunnelWdmConfigRecoveryType OBJECT-TYPE
    SYNTAX      FspR7CpProtectionType
    MAX-ACCESS  read-write
    STATUS      current
    DESCRIPTION   ""
    ::=  { tunnelWdmConfigEntry 7 }

tunnelWdmConfigPin OBJECT-TYPE
    SYNTAX      FspR7CpPinning
    MAX-ACCESS  read-write
    STATUS      current
    DESCRIPTION   ""
    ::=  { tunnelWdmConfigEntry 8 }

tunnelWdmConfigInitiateEqualization OBJECT-TYPE
    SYNTAX      FspR7InitEqualization
    MAX-ACCESS  read-write
    STATUS      current
    DESCRIPTION   ""
    ::=  { tunnelWdmConfigEntry 9 }

tunnelWdmConfigAbortProcess OBJECT-TYPE
    SYNTAX      FspR7CpAbortProcess
    MAX-ACCESS  read-write
    STATUS      current
    DESCRIPTION   ""
    ::=  { tunnelWdmConfigEntry 10 }

tunnelWdmConfigAdminModifier OBJECT-TYPE
    SYNTAX      FspR7CommandModifier
    MAX-ACCESS  read-write
    STATUS      current
    DESCRIPTION   ""
    ::=  { tunnelWdmConfigEntry 11 }

tunnelWdmConfigCommand OBJECT-TYPE
    SYNTAX      FspR7CpCommand
    MAX-ACCESS  read-write
    STATUS      current
    DESCRIPTION   ""
    ::=  { tunnelWdmConfigEntry 12 }

tunnelWdmConfigRestorationType OBJECT-TYPE
    SYNTAX      FspR7CpRestorationType
    MAX-ACCESS  read-write
    STATUS      current
    DESCRIPTION   ""
    ::=  { tunnelWdmConfigEntry 13 }

tunnelWdmConfigSubLayer OBJECT-TYPE
    SYNTAX      FspR7SubLayer
    MAX-ACCESS  read-write
    STATUS      current
    DESCRIPTION   ""
    ::=  { tunnelWdmConfigEntry 14 }

tunnelWdmConfigMonitorEntities OBJECT-TYPE
    SYNTAX      FspR7EnableDisable
    MAX-ACCESS  read-write
    STATUS      current
    DESCRIPTION   ""
    ::=  { tunnelWdmConfigEntry 15 }

tunnelWdmConfigSubLayerEncoding OBJECT-TYPE
    SYNTAX      FspR7SubLayerEncoding
    MAX-ACCESS  read-write
    STATUS      current
    DESCRIPTION   ""
    ::=  { tunnelWdmConfigEntry 16 }

tunnelWdmConfigPceMode OBJECT-TYPE
    SYNTAX      FspR7PceMode
    MAX-ACCESS  read-write
    STATUS      current
    DESCRIPTION   ""
    ::=  { tunnelWdmConfigEntry 17 }

tunnelWdmConfigOperateReversion OBJECT-TYPE
    SYNTAX      FspR7CpOperateReversion
    MAX-ACCESS  read-write
    STATUS      current
    DESCRIPTION
        "Triggers the manual reversion to the nominal connection" 
    ::=  { tunnelWdmConfigEntry 18 }

tunnelWdmConfigReversionType OBJECT-TYPE
    SYNTAX      FspR7CpReversionType
    MAX-ACCESS  read-write
    STATUS      current
    DESCRIPTION
        "Manual Reversion, Automatic Reversion, or no reversion at all for tunnels supporting restoration" 
    ::=  { tunnelWdmConfigEntry 19 }

tunnelWdmConfigRestorationMode OBJECT-TYPE
    SYNTAX      FspR7CpRestorationMode
    MAX-ACCESS  read-write
    STATUS      current
    DESCRIPTION
        "Restoration Mode (replaces pinning)" 
    ::=  { tunnelWdmConfigEntry 20 }

tunnelWdmConfigRestPathsNoProv OBJECT-TYPE
    SYNTAX      Unsigned32
    MAX-ACCESS  read-write
    STATUS      current
    DESCRIPTION
        "Number of provisioned Guaranteed Restoration Paths" 
    ::=  { tunnelWdmConfigEntry 21 }

tunnelWdmConfigRestorationPaths OBJECT-TYPE
    SYNTAX      SnmpAdminString
    MAX-ACCESS  read-write
    STATUS      current
    DESCRIPTION
        "" 
    ::=  { tunnelWdmConfigEntry 22 }

tunnelWdmConfigRestorationPathsComputed OBJECT-TYPE
    SYNTAX      SnmpAdminString
    MAX-ACCESS  read-write
    STATUS      current
    DESCRIPTION
        "" 
    ::=  { tunnelWdmConfigEntry 23 }

tunnelWdmConfigResetRetainedFailureIndications OBJECT-TYPE
    SYNTAX      FspR7ResetRfi
    MAX-ACCESS  read-write
    STATUS      current
    DESCRIPTION
        "Resets Retained Failure Indications for restored Tunnels" 
    ::=  { tunnelWdmConfigEntry 24 }

tunnelWdmConfigExcludedPaths OBJECT-TYPE
    SYNTAX      SnmpAdminString
    MAX-ACCESS  read-write
    STATUS      current
    DESCRIPTION
        "Lists of Path Elements to be excluded" 
    ::=  { tunnelWdmConfigEntry 25 }

tunnelWdmConfigSavePA OBJECT-TYPE
    SYNTAX      FspR7NoYes
    MAX-ACCESS  read-write
    STATUS      current
    DESCRIPTION
        "Save Path Computation File to PADISK" 
    ::=  { tunnelWdmConfigEntry 26 }

tunnelWdmConfigDvPaths OBJECT-TYPE
    SYNTAX      SnmpAdminString
    MAX-ACCESS  read-write
    STATUS      current
    DESCRIPTION
        "Control Plane Diversity Reference Identifier (DV)" 
    ::=  { tunnelWdmConfigEntry 27 }

tunnelWdmConfigPreferPcs OBJECT-TYPE
    SYNTAX      FspR7YesNo
    MAX-ACCESS  read-write
    STATUS      current
    DESCRIPTION
        "Preferred Path Computation Engine (Server)" 
    ::=  { tunnelWdmConfigEntry 28 }

tunnelWdmConfigEroScope OBJECT-TYPE
    SYNTAX      SnmpAdminString
    MAX-ACCESS  read-write
    STATUS      current
    DESCRIPTION
        "Inclusion Route - Scope" 
    ::=  { tunnelWdmConfigEntry 29 }

tunnelWdmConfigEroLifeCycle OBJECT-TYPE
    SYNTAX      SnmpAdminString
    MAX-ACCESS  read-write
    STATUS      current
    DESCRIPTION
        "Inclusion Route - Life Cycle" 
    ::=  { tunnelWdmConfigEntry 30 }

tunnelWdmConfigXroScope OBJECT-TYPE
    SYNTAX      SnmpAdminString
    MAX-ACCESS  read-write
    STATUS      current
    DESCRIPTION
        "Exclusion Path Elements - Scope" 
    ::=  { tunnelWdmConfigEntry 31 }

tunnelWdmConfigXroLifeCycle OBJECT-TYPE
    SYNTAX      SnmpAdminString
    MAX-ACCESS  read-write
    STATUS      current
    DESCRIPTION
        "Exclusion Path Elements - Life Cycle" 
    ::=  { tunnelWdmConfigEntry 32 }

tunnelWdmConfigFendTerm OBJECT-TYPE
    SYNTAX      OhTerminationLevel
    MAX-ACCESS  read-write
    STATUS      current
    DESCRIPTION
        "Far End Termination Level" 
    ::=  { tunnelWdmConfigEntry 33 }

tunnelWdmDataTable OBJECT-TYPE
    SYNTAX      SEQUENCE OF TunnelWdmDataEntry
    MAX-ACCESS  not-accessible
    STATUS      current
    DESCRIPTION   ""
    ::=  { controlPlaneConfigAndStatus 4 }

tunnelWdmDataEntry OBJECT-TYPE
    SYNTAX      TunnelWdmDataEntry
    MAX-ACCESS  not-accessible
    STATUS      current
    DESCRIPTION   ""
    INDEX       {
                  controlPlaneWdmEntityIndex
                }
    ::=  { tunnelWdmDataTable 1 }

TunnelWdmDataEntry ::=  SEQUENCE
  { tunnelWdmDataTunnelId SnmpAdminString,
    tunnelWdmDataTunnelNo Unsigned32,
    tunnelWdmDataTunnelType FspR7CpTunnelType,
    tunnelWdmDataFromTid SnmpAdminString,
    tunnelWdmDataFromNodeIP IpAddress,
    tunnelWdmDataToTid SnmpAdminString,
    tunnelWdmDataToTidMonitor SnmpAdminString,
    tunnelWdmDataToNodeIp IpAddress,
    tunnelWdmDataToNodeIpMonitor IpAddress,
    tunnelWdmDataFromAid EntityIndex,
    tunnelWdmDataToAid EntityIndex,
    tunnelWdmDataConnectionDirection FspR7Conn,
    tunnelWdmDataBitrate Unsigned32,
    tunnelWdmDataEncode FspR7CpEncode,
    tunnelWdmDataComputedPaths SnmpAdminString,
    tunnelWdmDataComputationState FspR7CpCompState,
    tunnelWdmDataErrorMessage SnmpAdminString,
    tunnelWdmDataErrorCodeMajor Unsigned32,
    tunnelWdmDataErrorCodeMinor Integer32,
    tunnelWdmDataErrorIp IpAddress,
    tunnelWdmDataErrorTid SnmpAdminString,
    tunnelWdmDataErrorCategory FspR7CpErrorCategory,
    tunnelWdmDataSpecificErrorMessage SnmpAdminString,
    tunnelWdmDataTunnelScope FspR7CpTunnelScope,
    tunnelWdmDataLayer FspR7PacketsLayer,
    tunnelWdmDataLogicalIfAid EntityIndex,
    tunnelWdmDataOifUni FspR7YesNo,
    tunnelWdmDataTunnelNumberExtension Unsigned32,
    tunnelWdmDataRestorationState FspR7CpRestorationState,
    tunnelWdmDataTunnelTemplate FspR7YesNo,
    tunnelWdmDataRestPathsNoAvail Unsigned32,
    tunnelWdmDataReversionState FspR7CpReversionState,
    tunnelWdmDataMonitorEntitiesDerive FspR7EnableDisable,
    tunnelWdmDataRfiList SnmpAdminString,
    tunnelWdmDataFromAidString SnmpAdminString,
    tunnelWdmDataToAidString SnmpAdminString,
    tunnelWdmDataPaFileName SnmpAdminString,
    tunnelWdmDataPceNodeIp IpAddress,
    tunnelWdmDataPceNodeTid SnmpAdminString }

tunnelWdmDataTunnelId OBJECT-TYPE
    SYNTAX      SnmpAdminString
    MAX-ACCESS  read-only
    STATUS      current
    DESCRIPTION   ""
    ::=  { tunnelWdmDataEntry 1 }

tunnelWdmDataTunnelNo OBJECT-TYPE
    SYNTAX      Unsigned32
    MAX-ACCESS  read-only
    STATUS      current
    DESCRIPTION   ""
    ::=  { tunnelWdmDataEntry 2 }

tunnelWdmDataTunnelType OBJECT-TYPE
    SYNTAX      FspR7CpTunnelType
    MAX-ACCESS  read-only
    STATUS      current
    DESCRIPTION   ""
    ::=  { tunnelWdmDataEntry 3 }

tunnelWdmDataFromTid OBJECT-TYPE
    SYNTAX      SnmpAdminString
    MAX-ACCESS  read-only
    STATUS      current
    DESCRIPTION   ""
    ::=  { tunnelWdmDataEntry 4 }

tunnelWdmDataFromNodeIP OBJECT-TYPE
    SYNTAX      IpAddress
    MAX-ACCESS  read-only
    STATUS      current
    DESCRIPTION   ""
    ::=  { tunnelWdmDataEntry 5 }

tunnelWdmDataToTid OBJECT-TYPE
    SYNTAX      SnmpAdminString
    MAX-ACCESS  read-only
    STATUS      current
    DESCRIPTION   ""
    ::=  { tunnelWdmDataEntry 6 }

tunnelWdmDataToTidMonitor OBJECT-TYPE
    SYNTAX      SnmpAdminString
    MAX-ACCESS  read-only
    STATUS      current
    DESCRIPTION   ""
    ::=  { tunnelWdmDataEntry 7 }

tunnelWdmDataToNodeIp OBJECT-TYPE
    SYNTAX      IpAddress
    MAX-ACCESS  read-only
    STATUS      current
    DESCRIPTION   ""
    ::=  { tunnelWdmDataEntry 8 }

tunnelWdmDataToNodeIpMonitor OBJECT-TYPE
    SYNTAX      IpAddress
    MAX-ACCESS  read-only
    STATUS      current
    DESCRIPTION   ""
    ::=  { tunnelWdmDataEntry 9 }

tunnelWdmDataFromAid OBJECT-TYPE
    SYNTAX      EntityIndex
    MAX-ACCESS  read-only
    STATUS      current
    DESCRIPTION   ""
    ::=  { tunnelWdmDataEntry 10 }

tunnelWdmDataToAid OBJECT-TYPE
    SYNTAX      EntityIndex
    MAX-ACCESS  read-only
    STATUS      current
    DESCRIPTION   ""
    ::=  { tunnelWdmDataEntry 11 }

tunnelWdmDataConnectionDirection OBJECT-TYPE
    SYNTAX      FspR7Conn
    MAX-ACCESS  read-only
    STATUS      current
    DESCRIPTION   ""
    ::=  { tunnelWdmDataEntry 12 }

tunnelWdmDataBitrate OBJECT-TYPE
    SYNTAX      Unsigned32 
    UNITS       "Mbps"
    MAX-ACCESS  read-only
    STATUS      current
    DESCRIPTION   ""
    ::=  { tunnelWdmDataEntry 13 }

tunnelWdmDataEncode OBJECT-TYPE
    SYNTAX      FspR7CpEncode
    MAX-ACCESS  read-only
    STATUS      current
    DESCRIPTION   ""
    ::=  { tunnelWdmDataEntry 14 }

tunnelWdmDataComputedPaths OBJECT-TYPE
    SYNTAX      SnmpAdminString
    MAX-ACCESS  read-only
    STATUS      current
    DESCRIPTION   ""
    ::=  { tunnelWdmDataEntry 15 }

tunnelWdmDataComputationState OBJECT-TYPE
    SYNTAX      FspR7CpCompState
    MAX-ACCESS  read-only
    STATUS      current
    DESCRIPTION   ""
    ::=  { tunnelWdmDataEntry 16 }

tunnelWdmDataErrorMessage OBJECT-TYPE
    SYNTAX      SnmpAdminString
    MAX-ACCESS  read-only
    STATUS      current
    DESCRIPTION   ""
    ::=  { tunnelWdmDataEntry 17 }

tunnelWdmDataErrorCodeMajor OBJECT-TYPE
    SYNTAX      Unsigned32
    MAX-ACCESS  read-only
    STATUS      current
    DESCRIPTION
        "Errorcode Major" 
    ::=  { tunnelWdmDataEntry 18 }

tunnelWdmDataErrorCodeMinor OBJECT-TYPE
    SYNTAX      Integer32
    MAX-ACCESS  read-only
    STATUS      current
    DESCRIPTION
        "Errorcode Minor" 
    ::=  { tunnelWdmDataEntry 19 }

tunnelWdmDataErrorIp OBJECT-TYPE
    SYNTAX      IpAddress
    MAX-ACCESS  read-only
    STATUS      current
    DESCRIPTION
        "Error IP" 
    ::=  { tunnelWdmDataEntry 20 }

tunnelWdmDataErrorTid OBJECT-TYPE
    SYNTAX      SnmpAdminString
    MAX-ACCESS  read-only
    STATUS      current
    DESCRIPTION
        "Error TID" 
    ::=  { tunnelWdmDataEntry 21 }

tunnelWdmDataErrorCategory OBJECT-TYPE
    SYNTAX      FspR7CpErrorCategory
    MAX-ACCESS  read-only
    STATUS      current
    DESCRIPTION
        "CP Provisioning Failure Category" 
    ::=  { tunnelWdmDataEntry 22 }

tunnelWdmDataSpecificErrorMessage OBJECT-TYPE
    SYNTAX      SnmpAdminString
    MAX-ACCESS  read-only
    STATUS      current
    DESCRIPTION
        "Specific Error Message" 
    ::=  { tunnelWdmDataEntry 23 }

tunnelWdmDataTunnelScope OBJECT-TYPE
    SYNTAX      FspR7CpTunnelScope
    MAX-ACCESS  read-only
    STATUS      current
    DESCRIPTION
        "Service Scope extending over either Client or Network Ports of Modules or Links (UN or NR) for Connection Segements" 
    ::=  { tunnelWdmDataEntry 24 }

tunnelWdmDataLayer OBJECT-TYPE
    SYNTAX      FspR7PacketsLayer
    MAX-ACCESS  read-only
    STATUS      current
    DESCRIPTION
        "Notional Layer of Advertisement on Packets on the LIF" 
    ::=  { tunnelWdmDataEntry 25 }

tunnelWdmDataLogicalIfAid OBJECT-TYPE
    SYNTAX      EntityIndex
    MAX-ACCESS  read-only
    STATUS      current
    DESCRIPTION
        "Logical Interface AID" 
    ::=  { tunnelWdmDataEntry 26 }

tunnelWdmDataOifUni OBJECT-TYPE
    SYNTAX      FspR7YesNo
    MAX-ACCESS  read-only
    STATUS      current
    DESCRIPTION
        "OIF UNI Tunnel" 
    ::=  { tunnelWdmDataEntry 27 }

tunnelWdmDataTunnelNumberExtension OBJECT-TYPE
    SYNTAX      Unsigned32
    MAX-ACCESS  read-only
    STATUS      current
    DESCRIPTION
        "Tunnel Number Extension. (internal: serviceID.extTunnelID)" 
    ::=  { tunnelWdmDataEntry 28 }

tunnelWdmDataRestorationState OBJECT-TYPE
    SYNTAX      FspR7CpRestorationState
    MAX-ACCESS  read-only
    STATUS      current
    DESCRIPTION
        "Restoration Enumeration State" 
    ::=  { tunnelWdmDataEntry 29 }

tunnelWdmDataTunnelTemplate OBJECT-TYPE
    SYNTAX      FspR7YesNo
    MAX-ACCESS  read-only
    STATUS      current
    DESCRIPTION
        "Tunnel Template, can't be brought into service" 
    ::=  { tunnelWdmDataEntry 30 }

tunnelWdmDataRestPathsNoAvail OBJECT-TYPE
    SYNTAX      Unsigned32
    MAX-ACCESS  read-only
    STATUS      current
    DESCRIPTION
        "Number of current available Guaranteed Shared Restoration Paths" 
    ::=  { tunnelWdmDataEntry 31 }

tunnelWdmDataReversionState OBJECT-TYPE
    SYNTAX      FspR7CpReversionState
    MAX-ACCESS  read-only
    STATUS      current
    DESCRIPTION
        "Enumeration for Reversion States" 
    ::=  { tunnelWdmDataEntry 32 }

tunnelWdmDataMonitorEntitiesDerive OBJECT-TYPE
    SYNTAX      FspR7EnableDisable
    MAX-ACCESS  read-only
    STATUS      current
    DESCRIPTION   ""
    ::=  { tunnelWdmDataEntry 33 }

tunnelWdmDataRfiList OBJECT-TYPE
    SYNTAX      SnmpAdminString
    MAX-ACCESS  read-only
    STATUS      current
    DESCRIPTION   ""
    ::=  { tunnelWdmDataEntry 34 }

tunnelWdmDataFromAidString OBJECT-TYPE
    SYNTAX      SnmpAdminString
    MAX-ACCESS  read-only
    STATUS      current
    DESCRIPTION
        "" 
    ::=  { tunnelWdmDataEntry 35 }

tunnelWdmDataToAidString OBJECT-TYPE
    SYNTAX      SnmpAdminString
    MAX-ACCESS  read-only
    STATUS      current
    DESCRIPTION
        "" 
    ::=  { tunnelWdmDataEntry 36 }

tunnelWdmDataPaFileName OBJECT-TYPE
    SYNTAX      SnmpAdminString
    MAX-ACCESS  read-only
    STATUS      current
    DESCRIPTION
        "Path Analyzer File Name" 
    ::=  { tunnelWdmDataEntry 37 }

tunnelWdmDataPceNodeIp OBJECT-TYPE
    SYNTAX      IpAddress
    MAX-ACCESS  read-only
    STATUS      current
    DESCRIPTION
        "PCE Node IP" 
    ::=  { tunnelWdmDataEntry 38 }

tunnelWdmDataPceNodeTid OBJECT-TYPE
    SYNTAX      SnmpAdminString
    MAX-ACCESS  read-only
    STATUS      current
    DESCRIPTION
        "PCE Node Target ID" 
    ::=  { tunnelWdmDataEntry 39 }

pathWdmDataTable OBJECT-TYPE
    SYNTAX      SEQUENCE OF PathWdmDataEntry
    MAX-ACCESS  not-accessible
    STATUS      current
    DESCRIPTION   ""
    ::=  { controlPlaneConfigAndStatus 6 }

pathWdmDataEntry OBJECT-TYPE
    SYNTAX      PathWdmDataEntry
    MAX-ACCESS  not-accessible
    STATUS      current
    DESCRIPTION   ""
    INDEX       {
                  controlPlaneWdmEntityIndex
                }
    ::=  { pathWdmDataTable 1 }

PathWdmDataEntry ::=  SEQUENCE
  { pathWdmDataPathId SnmpAdminString,
    pathWdmDataPathType FspR7CpPathType,
    pathWdmDataConnectionTunnelAid EntityIndex,
    pathWdmDataRole FspR7CpRole }

pathWdmDataPathId OBJECT-TYPE
    SYNTAX      SnmpAdminString
    MAX-ACCESS  read-only
    STATUS      current
    DESCRIPTION   ""
    ::=  { pathWdmDataEntry 1 }

pathWdmDataPathType OBJECT-TYPE
    SYNTAX      FspR7CpPathType
    MAX-ACCESS  read-only
    STATUS      current
    DESCRIPTION   ""
    ::=  { pathWdmDataEntry 2 }

pathWdmDataConnectionTunnelAid OBJECT-TYPE
    SYNTAX      EntityIndex
    MAX-ACCESS  read-only
    STATUS      current
    DESCRIPTION   ""
    ::=  { pathWdmDataEntry 3 }

pathWdmDataRole OBJECT-TYPE
    SYNTAX      FspR7CpRole
    MAX-ACCESS  read-only
    STATUS      current
    DESCRIPTION   ""
    ::=  { pathWdmDataEntry 4 }

pathElementWdmDataTable OBJECT-TYPE
    SYNTAX      SEQUENCE OF PathElementWdmDataEntry
    MAX-ACCESS  not-accessible
    STATUS      current
    DESCRIPTION   ""
    ::=  { controlPlaneConfigAndStatus 8 }

pathElementWdmDataEntry OBJECT-TYPE
    SYNTAX      PathElementWdmDataEntry
    MAX-ACCESS  not-accessible
    STATUS      current
    DESCRIPTION   ""
    INDEX       {
                  controlPlaneWdmEntityIndex
                }
    ::=  { pathElementWdmDataTable 1 }

PathElementWdmDataEntry ::=  SEQUENCE
  { pathElementWdmDataPathId SnmpAdminString,
    pathElementWdmDataSequenceNumber Unsigned32,
    pathElementWdmDataPathType FspR7CpPathType,
    pathElementWdmDataTrafficEngineeringType FspR7CpTEType,
    pathElementWdmDataLifIp IpAddress,
    pathElementWdmDataNodeIp IpAddress,
    pathElementWdmDataNodeIpMonitor IpAddress,
    pathElementWdmDataTid SnmpAdminString,
    pathElementWdmDataTidMonitor SnmpAdminString,
    pathElementWdmDataLogicalInterfaceId Unsigned32,
    pathElementWdmDataTie FspR7CpTie,
    pathElementWdmDataChannelUp FspR7ChannelNumber,
    pathElementWdmDataChannelDown FspR7ChannelNumber,
    pathElementWdmDataLine EntityIndex,
    pathElementWdmDataUpstreamModuleAid EntityIndex,
    pathElementWdmDataDownstreamModuleAid EntityIndex,
    pathElementWdmDataComputedOnsrForward Integer32,
    pathElementWdmDataComputedOnsrReverse Integer32,
    pathElementWdmDataComputedOptPowerForward Integer32,
    pathElementWdmDataComputedOptPowerReverse Integer32,
    pathElementWdmDataLineString SnmpAdminString,
    pathElementWdmDataUpstreamModuleAidString SnmpAdminString,
    pathElementWdmDataDownstreamModuleAidString SnmpAdminString }

pathElementWdmDataPathId OBJECT-TYPE
    SYNTAX      SnmpAdminString
    MAX-ACCESS  read-only
    STATUS      current
    DESCRIPTION   ""
    ::=  { pathElementWdmDataEntry 1 }

pathElementWdmDataSequenceNumber OBJECT-TYPE
    SYNTAX      Unsigned32
    MAX-ACCESS  read-only
    STATUS      current
    DESCRIPTION   ""
    ::=  { pathElementWdmDataEntry 2 }

pathElementWdmDataPathType OBJECT-TYPE
    SYNTAX      FspR7CpPathType
    MAX-ACCESS  read-only
    STATUS      current
    DESCRIPTION   ""
    ::=  { pathElementWdmDataEntry 3 }

pathElementWdmDataTrafficEngineeringType OBJECT-TYPE
    SYNTAX      FspR7CpTEType
    MAX-ACCESS  read-only
    STATUS      current
    DESCRIPTION   ""
    ::=  { pathElementWdmDataEntry 4 }

pathElementWdmDataLifIp OBJECT-TYPE
    SYNTAX      IpAddress
    MAX-ACCESS  read-only
    STATUS      current
    DESCRIPTION   ""
    ::=  { pathElementWdmDataEntry 5 }

pathElementWdmDataNodeIp OBJECT-TYPE
    SYNTAX      IpAddress
    MAX-ACCESS  read-only
    STATUS      current
    DESCRIPTION   ""
    ::=  { pathElementWdmDataEntry 6 }

pathElementWdmDataNodeIpMonitor OBJECT-TYPE
    SYNTAX      IpAddress
    MAX-ACCESS  read-only
    STATUS      current
    DESCRIPTION   ""
    ::=  { pathElementWdmDataEntry 7 }

pathElementWdmDataTid OBJECT-TYPE
    SYNTAX      SnmpAdminString
    MAX-ACCESS  read-only
    STATUS      current
    DESCRIPTION   ""
    ::=  { pathElementWdmDataEntry 8 }

pathElementWdmDataTidMonitor OBJECT-TYPE
    SYNTAX      SnmpAdminString
    MAX-ACCESS  read-only
    STATUS      current
    DESCRIPTION   ""
    ::=  { pathElementWdmDataEntry 9 }

pathElementWdmDataLogicalInterfaceId OBJECT-TYPE
    SYNTAX      Unsigned32
    MAX-ACCESS  read-only
    STATUS      current
    DESCRIPTION   ""
    ::=  { pathElementWdmDataEntry 10 }

pathElementWdmDataTie OBJECT-TYPE
    SYNTAX      FspR7CpTie
    MAX-ACCESS  read-only
    STATUS      current
    DESCRIPTION   ""
    ::=  { pathElementWdmDataEntry 11 }

pathElementWdmDataChannelUp OBJECT-TYPE
    SYNTAX      FspR7ChannelNumber
    MAX-ACCESS  read-only
    STATUS      current
    DESCRIPTION   ""
    ::=  { pathElementWdmDataEntry 12 }

pathElementWdmDataChannelDown OBJECT-TYPE
    SYNTAX      FspR7ChannelNumber
    MAX-ACCESS  read-only
    STATUS      current
    DESCRIPTION   ""
    ::=  { pathElementWdmDataEntry 13 }

pathElementWdmDataLine OBJECT-TYPE
    SYNTAX      EntityIndex
    MAX-ACCESS  read-only
    STATUS      current
    DESCRIPTION   ""
    ::=  { pathElementWdmDataEntry 14 }

pathElementWdmDataUpstreamModuleAid OBJECT-TYPE
    SYNTAX      EntityIndex
    MAX-ACCESS  read-only
    STATUS      current
    DESCRIPTION   ""
    ::=  { pathElementWdmDataEntry 15 }

pathElementWdmDataDownstreamModuleAid OBJECT-TYPE
    SYNTAX      EntityIndex
    MAX-ACCESS  read-only
    STATUS      current
    DESCRIPTION   ""
    ::=  { pathElementWdmDataEntry 16 }

pathElementWdmDataComputedOnsrForward OBJECT-TYPE
    SYNTAX      Integer32 
    UNITS       "0.01 %"
    MAX-ACCESS  read-only
    STATUS      current
    DESCRIPTION   ""
    ::=  { pathElementWdmDataEntry 17 }

pathElementWdmDataComputedOnsrReverse OBJECT-TYPE
    SYNTAX      Integer32 
    UNITS       "0.01 %"
    MAX-ACCESS  read-only
    STATUS      current
    DESCRIPTION   ""
    ::=  { pathElementWdmDataEntry 18 }

pathElementWdmDataComputedOptPowerForward OBJECT-TYPE
    SYNTAX      Integer32 
    UNITS       "0.01 dBm"
    MAX-ACCESS  read-only
    STATUS      current
    DESCRIPTION   ""
    ::=  { pathElementWdmDataEntry 19 }

pathElementWdmDataComputedOptPowerReverse OBJECT-TYPE
    SYNTAX      Integer32 
    UNITS       "0.01 dBm"
    MAX-ACCESS  read-only
    STATUS      current
    DESCRIPTION   ""
    ::=  { pathElementWdmDataEntry 20 }

pathElementWdmDataLineString OBJECT-TYPE
    SYNTAX      SnmpAdminString
    MAX-ACCESS  read-only
    STATUS      current
    DESCRIPTION   ""
    ::=  { pathElementWdmDataEntry 21 }

pathElementWdmDataUpstreamModuleAidString OBJECT-TYPE
    SYNTAX      SnmpAdminString
    MAX-ACCESS  read-only
    STATUS      current
    DESCRIPTION   ""
    ::=  { pathElementWdmDataEntry 22 }

pathElementWdmDataDownstreamModuleAidString OBJECT-TYPE
    SYNTAX      SnmpAdminString
    MAX-ACCESS  read-only
    STATUS      current
    DESCRIPTION   ""
    ::=  { pathElementWdmDataEntry 23 }

connectionWdmConfigTable OBJECT-TYPE
    SYNTAX      SEQUENCE OF ConnectionWdmConfigEntry
    MAX-ACCESS  not-accessible
    STATUS      current
    DESCRIPTION   ""
    ::=  { controlPlaneConfigAndStatus 9 }

connectionWdmConfigEntry OBJECT-TYPE
    SYNTAX      ConnectionWdmConfigEntry
    MAX-ACCESS  not-accessible
    STATUS      current
    DESCRIPTION   ""
    INDEX       {
                  controlPlaneWdmEntityIndex
                }
    ::=  { connectionWdmConfigTable 1 }

ConnectionWdmConfigEntry ::=  SEQUENCE
  { connectionWdmConfigCancelConnEntities FspR7CpCancConnection,
    connectionWdmConfigCancelModifier FspR7CommandModifier }

connectionWdmConfigCancelConnEntities OBJECT-TYPE
    SYNTAX      FspR7CpCancConnection
    MAX-ACCESS  read-write
    STATUS      current
    DESCRIPTION   ""
    ::=  { connectionWdmConfigEntry 1 }

connectionWdmConfigCancelModifier OBJECT-TYPE
    SYNTAX      FspR7CommandModifier
    MAX-ACCESS  read-write
    STATUS      current
    DESCRIPTION   ""
    ::=  { connectionWdmConfigEntry 2 }

connectionWdmDataTable OBJECT-TYPE
    SYNTAX      SEQUENCE OF ConnectionWdmDataEntry
    MAX-ACCESS  not-accessible
    STATUS      current
    DESCRIPTION   ""
    ::=  { controlPlaneConfigAndStatus 10 }

connectionWdmDataEntry OBJECT-TYPE
    SYNTAX      ConnectionWdmDataEntry
    MAX-ACCESS  not-accessible
    STATUS      current
    DESCRIPTION   ""
    INDEX       {
                  controlPlaneWdmEntityIndex
                }
    ::=  { connectionWdmDataTable 1 }

ConnectionWdmDataEntry ::=  SEQUENCE
  { connectionWdmDataTunnelId SnmpAdminString,
    connectionWdmDataTunnelNo Unsigned32,
    connectionWdmDataTunnelType FspR7CpTunnelType,
    connectionWdmDataFromTid SnmpAdminString,
    connectionWdmDataFromNodeIp IpAddress,
    connectionWdmDataToTid SnmpAdminString,
    connectionWdmDataToNodeIp IpAddress,
    connectionWdmDataFromAid EntityIndex,
    connectionWdmDataToAid EntityIndex,
    connectionWdmDataConnectionDirection FspR7Conn,
    connectionWdmDataNetworkElementPosition FspR7CpNePosition,
    connectionWdmDataFacilityType FspR7InterfaceType,
    connectionWdmDataBitrate Unsigned32,
    connectionWdmDataEncode FspR7CpEncode,
    connectionWdmDataTerminationLevel OhTerminationLevel,
    connectionWdmDataFecType FspR7FecType,
    connectionWdmDataStuff FspR7Stuff,
    connectionWdmDataSignalledPaths SnmpAdminString,
    connectionWdmDataComputedPaths SnmpAdminString,
    connectionWdmDataRole FspR7CpRole,
    connectionWdmDataErrorMessage SnmpAdminString,
    connectionWdmDataActivationState FspR7CpActivState,
    connectionWdmDataRestorable FspR7FalseTrue,
    connectionWdmDataRestorationState FspR7CpRestorationState,
    connectionWdmDataEqualizationState FspR7CpCompState,
    connectionWdmDataModificationState FspR7CpCompState,
    connectionWdmDataMonitorEntities FspR7EnableDisable,
    connectionWdmDataTunnelScope FspR7CpTunnelScope,
    connectionWdmDataLayer FspR7PacketsLayer,
    connectionWdmDataSourceTna IpAddress,
    connectionWdmDataDestinationTna IpAddress,
    connectionWdmDataTunnelNumberExtension Unsigned32,
    connectionWdmDataTunnelInstance Unsigned32,
    connectionWdmDataConnectionNo Unsigned32,
    connectionWdmDataFromAidString SnmpAdminString,
    connectionWdmDataToAidString SnmpAdminString }

connectionWdmDataTunnelId OBJECT-TYPE
    SYNTAX      SnmpAdminString
    MAX-ACCESS  read-only
    STATUS      current
    DESCRIPTION   ""
    ::=  { connectionWdmDataEntry 1 }

connectionWdmDataTunnelNo OBJECT-TYPE
    SYNTAX      Unsigned32
    MAX-ACCESS  read-only
    STATUS      current
    DESCRIPTION   ""
    ::=  { connectionWdmDataEntry 2 }

connectionWdmDataTunnelType OBJECT-TYPE
    SYNTAX      FspR7CpTunnelType
    MAX-ACCESS  read-only
    STATUS      current
    DESCRIPTION   ""
    ::=  { connectionWdmDataEntry 3 }

connectionWdmDataFromTid OBJECT-TYPE
    SYNTAX      SnmpAdminString
    MAX-ACCESS  read-only
    STATUS      current
    DESCRIPTION   ""
    ::=  { connectionWdmDataEntry 4 }

connectionWdmDataFromNodeIp OBJECT-TYPE
    SYNTAX      IpAddress
    MAX-ACCESS  read-only
    STATUS      current
    DESCRIPTION   ""
    ::=  { connectionWdmDataEntry 5 }

connectionWdmDataToTid OBJECT-TYPE
    SYNTAX      SnmpAdminString
    MAX-ACCESS  read-only
    STATUS      current
    DESCRIPTION   ""
    ::=  { connectionWdmDataEntry 6 }

connectionWdmDataToNodeIp OBJECT-TYPE
    SYNTAX      IpAddress
    MAX-ACCESS  read-only
    STATUS      current
    DESCRIPTION   ""
    ::=  { connectionWdmDataEntry 7 }

connectionWdmDataFromAid OBJECT-TYPE
    SYNTAX      EntityIndex
    MAX-ACCESS  read-only
    STATUS      current
    DESCRIPTION   ""
    ::=  { connectionWdmDataEntry 8 }

connectionWdmDataToAid OBJECT-TYPE
    SYNTAX      EntityIndex
    MAX-ACCESS  read-only
    STATUS      current
    DESCRIPTION   ""
    ::=  { connectionWdmDataEntry 9 }

connectionWdmDataConnectionDirection OBJECT-TYPE
    SYNTAX      FspR7Conn
    MAX-ACCESS  read-only
    STATUS      current
    DESCRIPTION   ""
    ::=  { connectionWdmDataEntry 10 }

connectionWdmDataNetworkElementPosition OBJECT-TYPE
    SYNTAX      FspR7CpNePosition
    MAX-ACCESS  read-only
    STATUS      current
    DESCRIPTION   ""
    ::=  { connectionWdmDataEntry 11 }

connectionWdmDataFacilityType OBJECT-TYPE
    SYNTAX      FspR7InterfaceType
    MAX-ACCESS  read-only
    STATUS      current
    DESCRIPTION   ""
    ::=  { connectionWdmDataEntry 12 }

connectionWdmDataBitrate OBJECT-TYPE
    SYNTAX      Unsigned32 
    UNITS       "Mbps"
    MAX-ACCESS  read-only
    STATUS      current
    DESCRIPTION   ""
    ::=  { connectionWdmDataEntry 13 }

connectionWdmDataEncode OBJECT-TYPE
    SYNTAX      FspR7CpEncode
    MAX-ACCESS  read-only
    STATUS      current
    DESCRIPTION   ""
    ::=  { connectionWdmDataEntry 14 }

connectionWdmDataTerminationLevel OBJECT-TYPE
    SYNTAX      OhTerminationLevel
    MAX-ACCESS  read-only
    STATUS      current
    DESCRIPTION   ""
    ::=  { connectionWdmDataEntry 15 }

connectionWdmDataFecType OBJECT-TYPE
    SYNTAX      FspR7FecType
    MAX-ACCESS  read-only
    STATUS      current
    DESCRIPTION   ""
    ::=  { connectionWdmDataEntry 16 }

connectionWdmDataStuff OBJECT-TYPE
    SYNTAX      FspR7Stuff
    MAX-ACCESS  read-only
    STATUS      current
    DESCRIPTION   ""
    ::=  { connectionWdmDataEntry 17 }

connectionWdmDataSignalledPaths OBJECT-TYPE
    SYNTAX      SnmpAdminString
    MAX-ACCESS  read-only
    STATUS      current
    DESCRIPTION   ""
    ::=  { connectionWdmDataEntry 18 }

connectionWdmDataComputedPaths OBJECT-TYPE
    SYNTAX      SnmpAdminString
    MAX-ACCESS  read-only
    STATUS      current
    DESCRIPTION   ""
    ::=  { connectionWdmDataEntry 19 }

connectionWdmDataRole OBJECT-TYPE
    SYNTAX      FspR7CpRole
    MAX-ACCESS  read-only
    STATUS      current
    DESCRIPTION   ""
    ::=  { connectionWdmDataEntry 20 }

connectionWdmDataErrorMessage OBJECT-TYPE
    SYNTAX      SnmpAdminString
    MAX-ACCESS  read-only
    STATUS      current
    DESCRIPTION   ""
    ::=  { connectionWdmDataEntry 21 }

connectionWdmDataActivationState OBJECT-TYPE
    SYNTAX      FspR7CpActivState
    MAX-ACCESS  read-only
    STATUS      current
    DESCRIPTION   ""
    ::=  { connectionWdmDataEntry 22 }

connectionWdmDataRestorable OBJECT-TYPE
    SYNTAX      FspR7FalseTrue
    MAX-ACCESS  read-only
    STATUS      current
    DESCRIPTION   ""
    ::=  { connectionWdmDataEntry 23 }

connectionWdmDataRestorationState OBJECT-TYPE
    SYNTAX      FspR7CpRestorationState
    MAX-ACCESS  read-only
    STATUS      deprecated
    DESCRIPTION   ""
    ::=  { connectionWdmDataEntry 24 }

connectionWdmDataEqualizationState OBJECT-TYPE
    SYNTAX      FspR7CpCompState
    MAX-ACCESS  read-only
    STATUS      current
    DESCRIPTION   ""
    ::=  { connectionWdmDataEntry 25 }

connectionWdmDataModificationState OBJECT-TYPE
    SYNTAX      FspR7CpCompState
    MAX-ACCESS  read-only
    STATUS      current
    DESCRIPTION
        "Modification Enumeration State" 
    ::=  { connectionWdmDataEntry 26 }

connectionWdmDataMonitorEntities OBJECT-TYPE
    SYNTAX      FspR7EnableDisable
    MAX-ACCESS  read-only
    STATUS      deprecated
    DESCRIPTION   ""
    ::=  { connectionWdmDataEntry 27 }

connectionWdmDataTunnelScope OBJECT-TYPE
    SYNTAX      FspR7CpTunnelScope
    MAX-ACCESS  read-only
    STATUS      current
    DESCRIPTION
        "Service Scope extending over either Client or Network Ports of Modules or Links (UN or NR) for Connection Segements" 
    ::=  { connectionWdmDataEntry 28 }

connectionWdmDataLayer OBJECT-TYPE
    SYNTAX      FspR7PacketsLayer
    MAX-ACCESS  read-only
    STATUS      current
    DESCRIPTION
        "Notional Layer of Advertisement on Packets on the LIF" 
    ::=  { connectionWdmDataEntry 29 }

connectionWdmDataSourceTna OBJECT-TYPE
    SYNTAX      IpAddress
    MAX-ACCESS  read-only
    STATUS      current
    DESCRIPTION
        "Source Transport Network Assigned Name" 
    ::=  { connectionWdmDataEntry 30 }

connectionWdmDataDestinationTna OBJECT-TYPE
    SYNTAX      IpAddress
    MAX-ACCESS  read-only
    STATUS      current
    DESCRIPTION
        "Destination Transport Network Assigned Name" 
    ::=  { connectionWdmDataEntry 31 }

connectionWdmDataTunnelNumberExtension OBJECT-TYPE
    SYNTAX      Unsigned32
    MAX-ACCESS  read-only
    STATUS      current
    DESCRIPTION
        "Tunnel Number Extension. (internal: serviceID.extTunnelID)" 
    ::=  { connectionWdmDataEntry 32 }

connectionWdmDataTunnelInstance OBJECT-TYPE
    SYNTAX      Unsigned32
    MAX-ACCESS  read-only
    STATUS      current
    DESCRIPTION
        "Tunnel Instance also called Service Instance ID. This changes every time there is Make-Before-Break operation. (internal: serviceInstID.octpID)" 
    ::=  { connectionWdmDataEntry 33 }

connectionWdmDataConnectionNo OBJECT-TYPE
    SYNTAX      Unsigned32
    MAX-ACCESS  read-only
    STATUS      current
    DESCRIPTION
        "Connection Number also called Connection ID. This changes every time there is Make-Before-Break operation. Working and protection connection numbers are different. (internal: lsptID.octpID)" 
    ::=  { connectionWdmDataEntry 34 }

connectionWdmDataFromAidString OBJECT-TYPE
    SYNTAX      SnmpAdminString
    MAX-ACCESS  read-only
    STATUS      current
    DESCRIPTION   ""
    ::=  { connectionWdmDataEntry 35 }

connectionWdmDataToAidString OBJECT-TYPE
    SYNTAX      SnmpAdminString
    MAX-ACCESS  read-only
    STATUS      current
    DESCRIPTION   ""
    ::=  { connectionWdmDataEntry 36 }

logicalCpIfConfigTable OBJECT-TYPE
    SYNTAX      SEQUENCE OF LogicalCpIfConfigEntry
    MAX-ACCESS  not-accessible
    STATUS      current
    DESCRIPTION   ""
    ::=  { controlPlaneConfigAndStatus 11 }

logicalCpIfConfigEntry OBJECT-TYPE
    SYNTAX      LogicalCpIfConfigEntry
    MAX-ACCESS  not-accessible
    STATUS      current
    DESCRIPTION   ""
    INDEX       {
                  entityIndex
                }
    ::=  { logicalCpIfConfigTable 1 }

LogicalCpIfConfigEntry ::=  SEQUENCE
  { logicalCpIfConfigAlias SnmpAdminString,
    logicalCpIfConfigOspf FspR7OspfMode,
    logicalCpIfConfigLayer FspR7PacketsLayer,
    logicalCpIfConfigAreaId IpAddress,
    logicalCpIfConfigMetric Unsigned32,
    logicalCpIfConfigHelloInterval Unsigned32,
    logicalCpIfConfigDeadInterval Unsigned32,
    logicalCpIfConfigPrio Unsigned32,
    logicalCpIfConfigRetransmitInterval Unsigned32,
    logicalCpIfConfigAuthType FspR7CpAuthType,
    logicalCpIfConfigAuthString SnmpAdminString,
    logicalCpIfConfigCpType FspR7CpType,
    logicalCpIfConfigRefreshTimeout Unsigned32,
    logicalCpIfConfigRefreshMultiplier Unsigned32,
    logicalCpIfConfigTeMetric Unsigned32,
    logicalCpIfConfigTeAreaId IpAddress,
    logicalCpIfConfigLinkColor Unsigned32,
    logicalCpIfConfigPushedNearEndIpHeader IpAddress,
    logicalCpIfConfigPushedFarEndIpHeader IpAddress,
    logicalCpIfConfigTimeToLive Unsigned32 }

logicalCpIfConfigAlias OBJECT-TYPE
    SYNTAX      SnmpAdminString
    MAX-ACCESS  read-write
    STATUS      current
    DESCRIPTION   "Alias."
    ::=  { logicalCpIfConfigEntry 1 }

logicalCpIfConfigOspf OBJECT-TYPE
    SYNTAX      FspR7OspfMode
    MAX-ACCESS  read-write
    STATUS      current
    DESCRIPTION
        "OSPF Routing (Dynamic)" 
    ::=  { logicalCpIfConfigEntry 2 }

logicalCpIfConfigLayer OBJECT-TYPE
    SYNTAX      FspR7PacketsLayer
    MAX-ACCESS  read-write
    STATUS      current
    DESCRIPTION   "Layer of Packets on LIF."
    ::=  { logicalCpIfConfigEntry 3 }

logicalCpIfConfigAreaId OBJECT-TYPE
    SYNTAX      IpAddress
    MAX-ACCESS  read-write
    STATUS      current
    DESCRIPTION
        "OSPF Area ID for IP Interface" 
    ::=  { logicalCpIfConfigEntry 4 }

logicalCpIfConfigMetric OBJECT-TYPE
    SYNTAX      Unsigned32 (0..65535 | 4294967295)
    MAX-ACCESS  read-write
    STATUS      current
    DESCRIPTION
        "Routing Metric" 
    ::=  { logicalCpIfConfigEntry 5 }

logicalCpIfConfigHelloInterval OBJECT-TYPE
    SYNTAX      Unsigned32 (1..65535 | 4294967295) 
    UNITS       "s"
    MAX-ACCESS  read-write
    STATUS      current
    DESCRIPTION
        "Hello Interval" 
    ::=  { logicalCpIfConfigEntry 6 }

logicalCpIfConfigDeadInterval OBJECT-TYPE
    SYNTAX      Unsigned32 (1..65535 | 4294967295) 
    UNITS       "s"
    MAX-ACCESS  read-write
    STATUS      current
    DESCRIPTION
        "Dead Interval" 
    ::=  { logicalCpIfConfigEntry 7 }

logicalCpIfConfigPrio OBJECT-TYPE
    SYNTAX      Unsigned32 (0..255 | 4294967295)
    MAX-ACCESS  read-write
    STATUS      current
    DESCRIPTION
        "Priority" 
    ::=  { logicalCpIfConfigEntry 8 }

logicalCpIfConfigRetransmitInterval OBJECT-TYPE
    SYNTAX      Unsigned32 (0..3600 | 4294967295) 
    UNITS       "s"
    MAX-ACCESS  read-write
    STATUS      current
    DESCRIPTION
        "Retransmit Interval" 
    ::=  { logicalCpIfConfigEntry 9 }

logicalCpIfConfigAuthType OBJECT-TYPE
    SYNTAX      FspR7CpAuthType
    MAX-ACCESS  read-write
    STATUS      current
    DESCRIPTION
        "OSPF Authentication Type" 
    ::=  { logicalCpIfConfigEntry 10 }

logicalCpIfConfigAuthString OBJECT-TYPE
    SYNTAX      SnmpAdminString
    MAX-ACCESS  read-write
    STATUS      current
    DESCRIPTION
        "OSPF Authentication Key/String depending on Authentication Type" 
    ::=  { logicalCpIfConfigEntry 11 }

logicalCpIfConfigCpType OBJECT-TYPE
    SYNTAX      FspR7CpType
    MAX-ACCESS  read-write
    STATUS      current
    DESCRIPTION
        "Control Plane Type" 
    ::=  { logicalCpIfConfigEntry 12 }

logicalCpIfConfigRefreshTimeout OBJECT-TYPE
    SYNTAX      Unsigned32 (1..65535 | 4294967295) 
    UNITS       "s"
    MAX-ACCESS  read-write
    STATUS      current
    DESCRIPTION
        "Refresh Timeout" 
    ::=  { logicalCpIfConfigEntry 13 }

logicalCpIfConfigRefreshMultiplier OBJECT-TYPE
    SYNTAX      Unsigned32 (1..20 | 4294967295)
    MAX-ACCESS  read-write
    STATUS      current
    DESCRIPTION
        "Refresh Multiplier" 
    ::=  { logicalCpIfConfigEntry 14 }

logicalCpIfConfigTeMetric OBJECT-TYPE
    SYNTAX      Unsigned32 (0..65535 | 4294967295)
    MAX-ACCESS  read-write
    STATUS      current
    DESCRIPTION
        "Traffic Engineering Metric" 
    ::=  { logicalCpIfConfigEntry 15 }

logicalCpIfConfigTeAreaId OBJECT-TYPE
    SYNTAX      IpAddress
    MAX-ACCESS  read-write
    STATUS      current
    DESCRIPTION
        "OSPF Area ID for Traffic Engineering" 
    ::=  { logicalCpIfConfigEntry 16 }

logicalCpIfConfigLinkColor OBJECT-TYPE
    SYNTAX      Unsigned32
    MAX-ACCESS  read-write
    STATUS      current
    DESCRIPTION
        "Bitfield to express up to 32 colors" 
    ::=  { logicalCpIfConfigEntry 17 }

logicalCpIfConfigPushedNearEndIpHeader OBJECT-TYPE
    SYNTAX      IpAddress
    MAX-ACCESS  read-write
    STATUS      current
    DESCRIPTION
        "Pushed Near End IP address in encapsulating header" 
    ::=  { logicalCpIfConfigEntry 18 }

logicalCpIfConfigPushedFarEndIpHeader OBJECT-TYPE
    SYNTAX      IpAddress
    MAX-ACCESS  read-write
    STATUS      current
    DESCRIPTION
        "Pushed Far End IP address in encapsulating header" 
    ::=  { logicalCpIfConfigEntry 19 }

logicalCpIfConfigTimeToLive OBJECT-TYPE
    SYNTAX      Unsigned32 (1..255 | 4294967295)
    MAX-ACCESS  read-write
    STATUS      current
    DESCRIPTION
        "Time to Live" 
    ::=  { logicalCpIfConfigEntry 20 }

logicalCpIfDataTable OBJECT-TYPE
    SYNTAX      SEQUENCE OF LogicalCpIfDataEntry
    MAX-ACCESS  not-accessible
    STATUS      current
    DESCRIPTION   ""
    ::=  { controlPlaneConfigAndStatus 12 }

logicalCpIfDataEntry OBJECT-TYPE
    SYNTAX      LogicalCpIfDataEntry
    MAX-ACCESS  not-accessible
    STATUS      current
    DESCRIPTION   ""
    INDEX       {
                  entityIndex
                }
    ::=  { logicalCpIfDataTable 1 }

LogicalCpIfDataEntry ::=  SEQUENCE
  { logicalCpIfDataFacilityType FspR7InterfaceType,
    logicalCpIfDataDcnAid EntityIndex,
    logicalCpIfDataLanLinkAidDerived EntityIndex,
    logicalCpIfDataLogicalInterfaceId Unsigned32,
    logicalCpIfDataTransport SnmpAdminString,
    logicalCpIfDataFarEndLifId EntityIndex,
    logicalCpIfDataFarEndNodeIp IpAddress,
    logicalCpIfDataFarEndNodeIpMonitor IpAddress,
    logicalCpIfDataFarEndTid SnmpAdminString,
    logicalCpIfDataFarEndTidMonitor SnmpAdminString,
    logicalCpIfDataIpType FspR7IpType,
    logicalCpIfDataIpAddr IpAddress,
    logicalCpIfDataIpAddrMonitor IpAddress,
    logicalCpIfDataIpMask IpAddress,
    logicalCpIfDataIpMaskMonitor IpAddress,
    logicalCpIfDataOspf FspR7OspfMode,
    logicalCpIfDataEncapsulation FspR7CpEncapsulation,
    logicalCpIfDataNendTeLinkIdNum IpAddress,
    logicalCpIfDataFendTeLinkIdNum IpAddress,
    logicalCpIfDataFendDataLinkId Unsigned32,
    logicalCpIfDataNendTeLinkIdUnn Unsigned32,
    logicalCpIfDataFendTeLinkIdUnn Unsigned32,
    logicalCpIfDataPushedNearEndIpHeader IpAddress,
    logicalCpIfDataPushedFarEndIpHeader IpAddress,
    logicalCpIfDataEncoding FspR7CpEncode,
    logicalCpIfDataLayer FspR7PacketsLayer,
    logicalCpIfDataNendTeLinkAid EntityIndex,
    logicalCpIfDataFendTeLinkAid EntityIndex,
    logicalCpIfDataTunnelAid EntityIndex,
    logicalCpIfDataActivationState FspR7CpActivState,
    logicalCpIfDataExtAdvertised FspR7YesNo,
    logicalCpIfDataVTeType FspR7CpVTeType,
    logicalCpIfDataVNodeIp IpAddress,
    logicalCpIfDataVNodeTltp SnmpAdminString,
    logicalCpIfDataDcnAidString SnmpAdminString,
    logicalCpIfDataLanLinkAidDerivedString SnmpAdminString,
    logicalCpIfDataFarEndLifIdString SnmpAdminString,
    logicalCpIfDataNendTeLinkAidString SnmpAdminString,
    logicalCpIfDataFendTeLinkAidString SnmpAdminString,
    logicalCpIfDataTransportString SnmpAdminString,
    logicalCpIfDataMtu Unsigned32 }

logicalCpIfDataFacilityType OBJECT-TYPE
    SYNTAX      FspR7InterfaceType
    MAX-ACCESS  read-only
    STATUS      current
    DESCRIPTION   "Facility Type."
    ::=  { logicalCpIfDataEntry 1 }

logicalCpIfDataDcnAid OBJECT-TYPE
    SYNTAX      EntityIndex
    MAX-ACCESS  read-only
    STATUS      current
    DESCRIPTION   "Sup. DCN Facility AID."
    ::=  { logicalCpIfDataEntry 2 }

logicalCpIfDataLanLinkAidDerived OBJECT-TYPE
    SYNTAX      EntityIndex
    MAX-ACCESS  read-only
    STATUS      current
    DESCRIPTION   "Sup. DCN Facility AID."
    ::=  { logicalCpIfDataEntry 3 }

logicalCpIfDataLogicalInterfaceId OBJECT-TYPE
    SYNTAX      Unsigned32
    MAX-ACCESS  read-only
    STATUS      current
    DESCRIPTION   "Logical InterfaceId."
    ::=  { logicalCpIfDataEntry 4 }

logicalCpIfDataTransport OBJECT-TYPE
    SYNTAX      SnmpAdminString
    MAX-ACCESS  read-only
    STATUS      current
    DESCRIPTION
        "" 
    ::=  { logicalCpIfDataEntry 5 }

logicalCpIfDataFarEndLifId OBJECT-TYPE
    SYNTAX      EntityIndex
    MAX-ACCESS  read-only
    STATUS      current
    DESCRIPTION   "Far End Transport Layer Termination Point - index of AID"
    ::=  { logicalCpIfDataEntry 6 }

logicalCpIfDataFarEndNodeIp OBJECT-TYPE
    SYNTAX      IpAddress
    MAX-ACCESS  read-only
    STATUS      current
    DESCRIPTION   ""
    ::=  { logicalCpIfDataEntry 7 }

logicalCpIfDataFarEndNodeIpMonitor OBJECT-TYPE
    SYNTAX      IpAddress
    MAX-ACCESS  read-only
    STATUS      current
    DESCRIPTION   ""
    ::=  { logicalCpIfDataEntry 8 }

logicalCpIfDataFarEndTid OBJECT-TYPE
    SYNTAX      SnmpAdminString
    MAX-ACCESS  read-only
    STATUS      current
    DESCRIPTION   "Far End Tid."
    ::=  { logicalCpIfDataEntry 9 }

logicalCpIfDataFarEndTidMonitor OBJECT-TYPE
    SYNTAX      SnmpAdminString
    MAX-ACCESS  read-only
    STATUS      current
    DESCRIPTION   "Far End Tid."
    ::=  { logicalCpIfDataEntry 10 }

logicalCpIfDataIpType OBJECT-TYPE
    SYNTAX      FspR7IpType
    MAX-ACCESS  read-only
    STATUS      current
    DESCRIPTION
        "Type of IP configuration" 
    ::=  { logicalCpIfDataEntry 11 }

logicalCpIfDataIpAddr OBJECT-TYPE
    SYNTAX      IpAddress
    MAX-ACCESS  read-only
    STATUS      current
    DESCRIPTION
        "IP Address assigned to LAN IP Interface" 
    ::=  { logicalCpIfDataEntry 12 }

logicalCpIfDataIpAddrMonitor OBJECT-TYPE
    SYNTAX      IpAddress
    MAX-ACCESS  read-only
    STATUS      current
    DESCRIPTION
        "IP address assigned to LAN IP Interface" 
    ::=  { logicalCpIfDataEntry 13 }

logicalCpIfDataIpMask OBJECT-TYPE
    SYNTAX      IpAddress
    MAX-ACCESS  read-only
    STATUS      current
    DESCRIPTION
        "IP MASK assigned to LAN IP Interface" 
    ::=  { logicalCpIfDataEntry 14 }

logicalCpIfDataIpMaskMonitor OBJECT-TYPE
    SYNTAX      IpAddress
    MAX-ACCESS  read-only
    STATUS      current
    DESCRIPTION
        "IP mask assigned to LAN IP Interface" 
    ::=  { logicalCpIfDataEntry 15 }

logicalCpIfDataOspf OBJECT-TYPE
    SYNTAX      FspR7OspfMode
    MAX-ACCESS  read-only
    STATUS      current
    DESCRIPTION
        "OSPF Routing (Dynamic)" 
    ::=  { logicalCpIfDataEntry 16 }

logicalCpIfDataEncapsulation OBJECT-TYPE
    SYNTAX      FspR7CpEncapsulation
    MAX-ACCESS  read-only
    STATUS      current
    DESCRIPTION
        "Encapsulation" 
    ::=  { logicalCpIfDataEntry 17 }

logicalCpIfDataNendTeLinkIdNum OBJECT-TYPE
    SYNTAX      IpAddress
    MAX-ACCESS  read-only
    STATUS      current
    DESCRIPTION
        "Local Traffic Engineering Link Identifier for Numbered Link" 
    ::=  { logicalCpIfDataEntry 18 }

logicalCpIfDataFendTeLinkIdNum OBJECT-TYPE
    SYNTAX      IpAddress
    MAX-ACCESS  read-only
    STATUS      current
    DESCRIPTION
        "Remote Traffic Engineering Link Identifier for Numbered Link" 
    ::=  { logicalCpIfDataEntry 19 }

logicalCpIfDataFendDataLinkId OBJECT-TYPE
    SYNTAX      Unsigned32
    MAX-ACCESS  read-only
    STATUS      current
    DESCRIPTION
        "Remote physical link identifier" 
    ::=  { logicalCpIfDataEntry 20 }

logicalCpIfDataNendTeLinkIdUnn OBJECT-TYPE
    SYNTAX      Unsigned32
    MAX-ACCESS  read-only
    STATUS      current
    DESCRIPTION
        "Local Traffic Engineering Link Identifier for Unnumbered Link" 
    ::=  { logicalCpIfDataEntry 21 }

logicalCpIfDataFendTeLinkIdUnn OBJECT-TYPE
    SYNTAX      Unsigned32
    MAX-ACCESS  read-only
    STATUS      current
    DESCRIPTION
        "Remote Traffic Engineering Link Identifier for Unnumbered Link" 
    ::=  { logicalCpIfDataEntry 22 }

logicalCpIfDataPushedNearEndIpHeader OBJECT-TYPE
    SYNTAX      IpAddress
    MAX-ACCESS  read-only
    STATUS      current
    DESCRIPTION
        "Pushed Near End IP address in encapsulating header" 
    ::=  { logicalCpIfDataEntry 23 }

logicalCpIfDataPushedFarEndIpHeader OBJECT-TYPE
    SYNTAX      IpAddress
    MAX-ACCESS  read-only
    STATUS      current
    DESCRIPTION
        "Pushed Far End IP address in encapsulating header" 
    ::=  { logicalCpIfDataEntry 24 }

logicalCpIfDataEncoding OBJECT-TYPE
    SYNTAX      FspR7CpEncode
    MAX-ACCESS  read-only
    STATUS      current
    DESCRIPTION
        "Encoding" 
    ::=  { logicalCpIfDataEntry 25 }

logicalCpIfDataLayer OBJECT-TYPE
    SYNTAX      FspR7PacketsLayer
    MAX-ACCESS  read-only
    STATUS      current
    DESCRIPTION   "Layer of Packets on LIF."
    ::=  { logicalCpIfDataEntry 26 }

logicalCpIfDataNendTeLinkAid OBJECT-TYPE
    SYNTAX      EntityIndex
    MAX-ACCESS  read-only
    STATUS      current
    DESCRIPTION
        "Local Traffic Engineering Link Access Identifier" 
    ::=  { logicalCpIfDataEntry 27 }

logicalCpIfDataFendTeLinkAid OBJECT-TYPE
    SYNTAX      EntityIndex
    MAX-ACCESS  read-only
    STATUS      current
    DESCRIPTION
        "Remote Traffic Engineering Link Access Identifier" 
    ::=  { logicalCpIfDataEntry 28 }

logicalCpIfDataTunnelAid OBJECT-TYPE
    SYNTAX      EntityIndex
    MAX-ACCESS  read-only
    STATUS      current
    DESCRIPTION
        "Supporting Tunnel" 
    ::=  { logicalCpIfDataEntry 29 }

logicalCpIfDataActivationState OBJECT-TYPE
    SYNTAX      FspR7CpActivState
    MAX-ACCESS  read-only
    STATUS      current
    DESCRIPTION
        "Activation State" 
    ::=  { logicalCpIfDataEntry 30 }

logicalCpIfDataExtAdvertised OBJECT-TYPE
    SYNTAX      FspR7YesNo
    MAX-ACCESS  read-only
    STATUS      current
    DESCRIPTION
        "Externally Advertised TE Link" 
    ::=  { logicalCpIfDataEntry 31 }

logicalCpIfDataVTeType OBJECT-TYPE
    SYNTAX      FspR7CpVTeType
    MAX-ACCESS  read-only
    STATUS      current
    DESCRIPTION
        "Type of Virtual TE configuration" 
    ::=  { logicalCpIfDataEntry 32 }

logicalCpIfDataVNodeIp OBJECT-TYPE
    SYNTAX      IpAddress
    MAX-ACCESS  read-only
    STATUS      current
    DESCRIPTION
        "Virtual Node IP" 
    ::=  { logicalCpIfDataEntry 33 }

logicalCpIfDataVNodeTltp OBJECT-TYPE
    SYNTAX      SnmpAdminString
    MAX-ACCESS  read-only
    STATUS      current
    DESCRIPTION
        "Virtual Node Transport Layer Termination Point" 
    ::=  { logicalCpIfDataEntry 34 }

logicalCpIfDataDcnAidString OBJECT-TYPE
    SYNTAX      SnmpAdminString
    MAX-ACCESS  read-only
    STATUS      current
    DESCRIPTION   "Sup. DCN Facility AID. (displayed as AidString)"
    ::=  { logicalCpIfDataEntry 35 }

logicalCpIfDataLanLinkAidDerivedString OBJECT-TYPE
    SYNTAX      SnmpAdminString
    MAX-ACCESS  read-only
    STATUS      current
    DESCRIPTION   "Sup. DCN Facility AID."
    ::=  { logicalCpIfDataEntry 36 }

logicalCpIfDataFarEndLifIdString OBJECT-TYPE
    SYNTAX      SnmpAdminString
    MAX-ACCESS  read-only
    STATUS      current
    DESCRIPTION   "Far End Transport Layer Termination Point - index of AID"
    ::=  { logicalCpIfDataEntry 37 }

logicalCpIfDataNendTeLinkAidString OBJECT-TYPE
    SYNTAX      SnmpAdminString
    MAX-ACCESS  read-only
    STATUS      current
    DESCRIPTION
        "Local Traffic Engineering Link Access Identifier" 
    ::=  { logicalCpIfDataEntry 38 }

logicalCpIfDataFendTeLinkAidString OBJECT-TYPE
    SYNTAX      SnmpAdminString
    MAX-ACCESS  read-only
    STATUS      current
    DESCRIPTION
        "Remote Traffic Engineering Link Access Identifier" 
    ::=  { logicalCpIfDataEntry 39 }

logicalCpIfDataTransportString OBJECT-TYPE
    SYNTAX      SnmpAdminString
    MAX-ACCESS  read-only
    STATUS      current
    DESCRIPTION
        "Transport Layer Termination Point" 
    ::=  { logicalCpIfDataEntry 40 }

logicalCpIfDataMtu OBJECT-TYPE
    SYNTAX      Unsigned32 (1280..1500 | 4294967295) 
    UNITS       "Byte"
    MAX-ACCESS  read-only
    STATUS      current
    DESCRIPTION
        "Maximum Transmission Unit" 
    ::=  { logicalCpIfDataEntry 41 }

inventoryCpWdmDownDataTable OBJECT-TYPE
    SYNTAX      SEQUENCE OF InventoryCpWdmDownDataEntry
    MAX-ACCESS  not-accessible
    STATUS      current
    DESCRIPTION   ""
    ::=  { controlPlaneConfigAndStatus 13 }

inventoryCpWdmDownDataEntry OBJECT-TYPE
    SYNTAX      InventoryCpWdmDownDataEntry
    MAX-ACCESS  not-accessible
    STATUS      current
    DESCRIPTION   ""
    INDEX       {
                  controlPlaneWdmEntityIndex,
                  inventoryCpWdmDownDataNumber
                }
    ::=  { inventoryCpWdmDownDataTable 1 }

InventoryCpWdmDownDataEntry ::=  SEQUENCE
  { inventoryCpWdmDownDataNumber EntityIndex,
    inventoryCpWdmDownDataResources EntityIndex,
    inventoryCpWdmDownDataFacilities EntityIndex,
    inventoryCpWdmDownDataPhysicalTermPoints EntityIndex }

inventoryCpWdmDownDataNumber OBJECT-TYPE
    SYNTAX      EntityIndex
    MAX-ACCESS  not-accessible
    STATUS      current
    DESCRIPTION   ""
    ::=  { inventoryCpWdmDownDataEntry 1 }

inventoryCpWdmDownDataResources OBJECT-TYPE
    SYNTAX      EntityIndex
    MAX-ACCESS  read-only
    STATUS      current
    DESCRIPTION   ""
    ::=  { inventoryCpWdmDownDataEntry 2 }

inventoryCpWdmDownDataFacilities OBJECT-TYPE
    SYNTAX      EntityIndex
    MAX-ACCESS  read-only
    STATUS      current
    DESCRIPTION   ""
    ::=  { inventoryCpWdmDownDataEntry 3 }

inventoryCpWdmDownDataPhysicalTermPoints OBJECT-TYPE
    SYNTAX      EntityIndex
    MAX-ACCESS  read-only
    STATUS      current
    DESCRIPTION   ""
    ::=  { inventoryCpWdmDownDataEntry 4 }

inventoryCpWdmUpDataTable OBJECT-TYPE
    SYNTAX      SEQUENCE OF InventoryCpWdmUpDataEntry
    MAX-ACCESS  not-accessible
    STATUS      current
    DESCRIPTION   ""
    ::=  { controlPlaneConfigAndStatus 14 }

inventoryCpWdmUpDataEntry OBJECT-TYPE
    SYNTAX      InventoryCpWdmUpDataEntry
    MAX-ACCESS  not-accessible
    STATUS      current
    DESCRIPTION   ""
    INDEX       {
                  controlPlaneWdmEntityIndex,
                  inventoryCpWdmUpDataNumber
                }
    ::=  { inventoryCpWdmUpDataTable 1 }

InventoryCpWdmUpDataEntry ::=  SEQUENCE
  { inventoryCpWdmUpDataNumber EntityIndex,
    inventoryCpWdmUpDataResources EntityIndex,
    inventoryCpWdmUpDataFacilities EntityIndex,
    inventoryCpWdmUpDataPhysicalTermPoints EntityIndex }

inventoryCpWdmUpDataNumber OBJECT-TYPE
    SYNTAX      EntityIndex
    MAX-ACCESS  not-accessible
    STATUS      current
    DESCRIPTION   ""
    ::=  { inventoryCpWdmUpDataEntry 1 }

inventoryCpWdmUpDataResources OBJECT-TYPE
    SYNTAX      EntityIndex
    MAX-ACCESS  read-only
    STATUS      current
    DESCRIPTION   ""
    ::=  { inventoryCpWdmUpDataEntry 2 }

inventoryCpWdmUpDataFacilities OBJECT-TYPE
    SYNTAX      EntityIndex
    MAX-ACCESS  read-only
    STATUS      current
    DESCRIPTION   ""
    ::=  { inventoryCpWdmUpDataEntry 3 }

inventoryCpWdmUpDataPhysicalTermPoints OBJECT-TYPE
    SYNTAX      EntityIndex
    MAX-ACCESS  read-only
    STATUS      current
    DESCRIPTION   ""
    ::=  { inventoryCpWdmUpDataEntry 4 }

inventoryCpWdmCrsDownDataTable OBJECT-TYPE
    SYNTAX      SEQUENCE OF InventoryCpWdmCrsDownDataEntry
    MAX-ACCESS  not-accessible
    STATUS      current
    DESCRIPTION   ""
    ::=  { controlPlaneConfigAndStatus 15 }

inventoryCpWdmCrsDownDataEntry OBJECT-TYPE
    SYNTAX      InventoryCpWdmCrsDownDataEntry
    MAX-ACCESS  not-accessible
    STATUS      current
    DESCRIPTION   ""
    INDEX       {
                  controlPlaneWdmEntityIndex,
                  inventoryCpWdmCrsDownDataNumber,
                  entityIndex
                }
    ::=  { inventoryCpWdmCrsDownDataTable 1 }

InventoryCpWdmCrsDownDataEntry ::=  SEQUENCE
  { inventoryCpWdmCrsDownDataNumber EntityIndex,
    inventoryCpWdmCrsDownDataAids EntityIndex,
    inventoryCpWdmCrsDownDataAidsString SnmpAdminString }

inventoryCpWdmCrsDownDataNumber OBJECT-TYPE
    SYNTAX      EntityIndex
    MAX-ACCESS  not-accessible
    STATUS      current
    DESCRIPTION   ""
    ::=  { inventoryCpWdmCrsDownDataEntry 1 }

inventoryCpWdmCrsDownDataAids OBJECT-TYPE
    SYNTAX      EntityIndex
    MAX-ACCESS  read-only
    STATUS      current
    DESCRIPTION   ""
    ::=  { inventoryCpWdmCrsDownDataEntry 2 }

inventoryCpWdmCrsDownDataAidsString OBJECT-TYPE
    SYNTAX      SnmpAdminString
    MAX-ACCESS  read-only
    STATUS      current
    DESCRIPTION   ""
    ::=  { inventoryCpWdmCrsDownDataEntry 3 }

inventoryCpWdmCrsUpDataTable OBJECT-TYPE
    SYNTAX      SEQUENCE OF InventoryCpWdmCrsUpDataEntry
    MAX-ACCESS  not-accessible
    STATUS      current
    DESCRIPTION   ""
    ::=  { controlPlaneConfigAndStatus 16 }

inventoryCpWdmCrsUpDataEntry OBJECT-TYPE
    SYNTAX      InventoryCpWdmCrsUpDataEntry
    MAX-ACCESS  not-accessible
    STATUS      current
    DESCRIPTION   ""
    INDEX       {
                  controlPlaneWdmEntityIndex,
                  inventoryCpWdmCrsUpDataNumber,
                  entityIndex
                }
    ::=  { inventoryCpWdmCrsUpDataTable 1 }

InventoryCpWdmCrsUpDataEntry ::=  SEQUENCE
  { inventoryCpWdmCrsUpDataNumber EntityIndex,
    inventoryCpWdmCrsUpDataAids EntityIndex,
    inventoryCpWdmCrsUpDataAidsString SnmpAdminString }

inventoryCpWdmCrsUpDataNumber OBJECT-TYPE
    SYNTAX      EntityIndex
    MAX-ACCESS  not-accessible
    STATUS      current
    DESCRIPTION   ""
    ::=  { inventoryCpWdmCrsUpDataEntry 1 }

inventoryCpWdmCrsUpDataAids OBJECT-TYPE
    SYNTAX      EntityIndex
    MAX-ACCESS  read-only
    STATUS      current
    DESCRIPTION   ""
    ::=  { inventoryCpWdmCrsUpDataEntry 2 }

inventoryCpWdmCrsUpDataAidsString OBJECT-TYPE
    SYNTAX      SnmpAdminString
    MAX-ACCESS  read-only
    STATUS      current
    DESCRIPTION   ""
    ::=  { inventoryCpWdmCrsUpDataEntry 3 }

teRouterDataTable OBJECT-TYPE
    SYNTAX      SEQUENCE OF TeRouterDataEntry
    MAX-ACCESS  not-accessible
    STATUS      current
    DESCRIPTION   ""
    ::=  { controlPlaneConfigAndStatus 17 }

teRouterDataEntry OBJECT-TYPE
    SYNTAX      TeRouterDataEntry
    MAX-ACCESS  not-accessible
    STATUS      current
    DESCRIPTION   ""
    INDEX       {
                  teRouterDataIp
                }
    ::=  { teRouterDataTable 1 }

TeRouterDataEntry ::=  SEQUENCE
  { teRouterDataIp IpAddress,
    teRouterDataNodeIp IpAddress,
    teRouterDataNodeTid SnmpAdminString,
    teRouterDataInfo SnmpAdminString }

teRouterDataIp OBJECT-TYPE
    SYNTAX      IpAddress
    MAX-ACCESS  accessible-for-notify
    STATUS      current
    DESCRIPTION
        "IP index" 
    ::=  { teRouterDataEntry 1 }

teRouterDataNodeIp OBJECT-TYPE
    SYNTAX      IpAddress
    MAX-ACCESS  read-only
    STATUS      current
    DESCRIPTION   ""
    ::=  { teRouterDataEntry 2 }

teRouterDataNodeTid OBJECT-TYPE
    SYNTAX      SnmpAdminString
    MAX-ACCESS  read-only
    STATUS      current
    DESCRIPTION   ""
    ::=  { teRouterDataEntry 3 }

teRouterDataInfo OBJECT-TYPE
    SYNTAX      SnmpAdminString
    MAX-ACCESS  read-only
    STATUS      current
    DESCRIPTION   ""
    ::=  { teRouterDataEntry 4 }

teUnnumLinkWdmDataTable OBJECT-TYPE
    SYNTAX      SEQUENCE OF TeUnnumLinkWdmDataEntry
    MAX-ACCESS  not-accessible
    STATUS      current
    DESCRIPTION   ""
    ::=  { controlPlaneConfigAndStatus 18 }

teUnnumLinkWdmDataEntry OBJECT-TYPE
    SYNTAX      TeUnnumLinkWdmDataEntry
    MAX-ACCESS  not-accessible
    STATUS      current
    DESCRIPTION   ""
    INDEX       {
                  teRouterDataIp,
                  teUnnumLinkWdmDataNumber
                }
    ::=  { teUnnumLinkWdmDataTable 1 }

TeUnnumLinkWdmDataEntry ::=  SEQUENCE
  { teUnnumLinkWdmDataNumber Unsigned32,
    teUnnumLinkWdmDataNodeIp IpAddress,
    teUnnumLinkWdmDataNodeTid SnmpAdminString,
    teUnnumLinkWdmDataTeLinkId Unsigned32,
    teUnnumLinkWdmDataPhysicalLink Unsigned32,
    teUnnumLinkWdmDataSynchronization FspR7YesNo,
    teUnnumLinkWdmDataDiscarded FspR7YesNo,
    teUnnumLinkWdmDataFendNodeIp IpAddress,
    teUnnumLinkWdmDataFendTeLinkId Unsigned32,
    teUnnumLinkWdmDataInfo SnmpAdminString }

teUnnumLinkWdmDataNumber OBJECT-TYPE
    SYNTAX      Unsigned32
    MAX-ACCESS  not-accessible
    STATUS      current
    DESCRIPTION   ""
    ::=  { teUnnumLinkWdmDataEntry 1 }

teUnnumLinkWdmDataNodeIp OBJECT-TYPE
    SYNTAX      IpAddress
    MAX-ACCESS  read-only
    STATUS      current
    DESCRIPTION   ""
    ::=  { teUnnumLinkWdmDataEntry 2 }

teUnnumLinkWdmDataNodeTid OBJECT-TYPE
    SYNTAX      SnmpAdminString
    MAX-ACCESS  read-only
    STATUS      current
    DESCRIPTION   ""
    ::=  { teUnnumLinkWdmDataEntry 3 }

teUnnumLinkWdmDataTeLinkId OBJECT-TYPE
    SYNTAX      Unsigned32
    MAX-ACCESS  read-only
    STATUS      current
    DESCRIPTION   ""
    ::=  { teUnnumLinkWdmDataEntry 4 }

teUnnumLinkWdmDataPhysicalLink OBJECT-TYPE
    SYNTAX      Unsigned32
    MAX-ACCESS  read-only
    STATUS      current
    DESCRIPTION   ""
    ::=  { teUnnumLinkWdmDataEntry 5 }

teUnnumLinkWdmDataSynchronization OBJECT-TYPE
    SYNTAX      FspR7YesNo
    MAX-ACCESS  read-only
    STATUS      current
    DESCRIPTION   ""
    ::=  { teUnnumLinkWdmDataEntry 6 }

teUnnumLinkWdmDataDiscarded OBJECT-TYPE
    SYNTAX      FspR7YesNo
    MAX-ACCESS  read-only
    STATUS      current
    DESCRIPTION   ""
    ::=  { teUnnumLinkWdmDataEntry 7 }

teUnnumLinkWdmDataFendNodeIp OBJECT-TYPE
    SYNTAX      IpAddress
    MAX-ACCESS  read-only
    STATUS      current
    DESCRIPTION   ""
    ::=  { teUnnumLinkWdmDataEntry 8 }

teUnnumLinkWdmDataFendTeLinkId OBJECT-TYPE
    SYNTAX      Unsigned32
    MAX-ACCESS  read-only
    STATUS      current
    DESCRIPTION   ""
    ::=  { teUnnumLinkWdmDataEntry 9 }

teUnnumLinkWdmDataInfo OBJECT-TYPE
    SYNTAX      SnmpAdminString
    MAX-ACCESS  read-only
    STATUS      current
    DESCRIPTION   ""
    ::=  { teUnnumLinkWdmDataEntry 10 }

teNumLinkWdmDataTable OBJECT-TYPE
    SYNTAX      SEQUENCE OF TeNumLinkWdmDataEntry
    MAX-ACCESS  not-accessible
    STATUS      current
    DESCRIPTION   ""
    ::=  { controlPlaneConfigAndStatus 19 }

teNumLinkWdmDataEntry OBJECT-TYPE
    SYNTAX      TeNumLinkWdmDataEntry
    MAX-ACCESS  not-accessible
    STATUS      current
    DESCRIPTION   ""
    INDEX       {
                  teRouterDataIp
                }
    ::=  { teNumLinkWdmDataTable 1 }

TeNumLinkWdmDataEntry ::=  SEQUENCE
  { teNumLinkWdmDataNodeIp IpAddress,
    teNumLinkWdmDataNodeTid SnmpAdminString,
    teNumLinkWdmDataTeLinkIp IpAddress,
    teNumLinkWdmDataPhysicalLink Unsigned32,
    teNumLinkWdmDataSynchronization FspR7YesNo,
    teNumLinkWdmDataDiscarded FspR7YesNo,
    teNumLinkWdmDataFendNodeIp IpAddress,
    teNumLinkWdmDataFendTeLinkIp IpAddress,
    teNumLinkWdmDataInfo SnmpAdminString }

teNumLinkWdmDataNodeIp OBJECT-TYPE
    SYNTAX      IpAddress
    MAX-ACCESS  read-only
    STATUS      current
    DESCRIPTION   ""
    ::=  { teNumLinkWdmDataEntry 1 }

teNumLinkWdmDataNodeTid OBJECT-TYPE
    SYNTAX      SnmpAdminString
    MAX-ACCESS  read-only
    STATUS      current
    DESCRIPTION   ""
    ::=  { teNumLinkWdmDataEntry 2 }

teNumLinkWdmDataTeLinkIp OBJECT-TYPE
    SYNTAX      IpAddress
    MAX-ACCESS  read-only
    STATUS      current
    DESCRIPTION   ""
    ::=  { teNumLinkWdmDataEntry 3 }

teNumLinkWdmDataPhysicalLink OBJECT-TYPE
    SYNTAX      Unsigned32
    MAX-ACCESS  read-only
    STATUS      current
    DESCRIPTION   ""
    ::=  { teNumLinkWdmDataEntry 4 }

teNumLinkWdmDataSynchronization OBJECT-TYPE
    SYNTAX      FspR7YesNo
    MAX-ACCESS  read-only
    STATUS      current
    DESCRIPTION   ""
    ::=  { teNumLinkWdmDataEntry 5 }

teNumLinkWdmDataDiscarded OBJECT-TYPE
    SYNTAX      FspR7YesNo
    MAX-ACCESS  read-only
    STATUS      current
    DESCRIPTION   ""
    ::=  { teNumLinkWdmDataEntry 6 }

teNumLinkWdmDataFendNodeIp OBJECT-TYPE
    SYNTAX      IpAddress
    MAX-ACCESS  read-only
    STATUS      current
    DESCRIPTION   ""
    ::=  { teNumLinkWdmDataEntry 7 }

teNumLinkWdmDataFendTeLinkIp OBJECT-TYPE
    SYNTAX      IpAddress
    MAX-ACCESS  read-only
    STATUS      current
    DESCRIPTION   ""
    ::=  { teNumLinkWdmDataEntry 8 }

teNumLinkWdmDataInfo OBJECT-TYPE
    SYNTAX      SnmpAdminString
    MAX-ACCESS  read-only
    STATUS      current
    DESCRIPTION   ""
    ::=  { teNumLinkWdmDataEntry 9 }

tnaMapDataTable OBJECT-TYPE
    SYNTAX      SEQUENCE OF TnaMapDataEntry
    MAX-ACCESS  not-accessible
    STATUS      current
    DESCRIPTION   ""
    ::=  { controlPlaneConfigAndStatus 20 }

tnaMapDataEntry OBJECT-TYPE
    SYNTAX      TnaMapDataEntry
    MAX-ACCESS  not-accessible
    STATUS      current
    DESCRIPTION   ""
    INDEX       {
                  tnaMapDataNodeIp,
                  tnaMapDataRemoteTna
                }
    ::=  { tnaMapDataTable 1 }

TnaMapDataEntry ::=  SEQUENCE
  { tnaMapDataNodeIp IpAddress,
    tnaMapDataRemoteTna IpAddress,
    tnaMapDataRemoteTnaMask IpAddress,
    tnaMapDataLocalPort EntityIndex }

tnaMapDataNodeIp OBJECT-TYPE
    SYNTAX      IpAddress
    MAX-ACCESS  read-only
    STATUS      current
    DESCRIPTION
        "Node IP" 
    ::=  { tnaMapDataEntry 1 }

tnaMapDataRemoteTna OBJECT-TYPE
    SYNTAX      IpAddress
    MAX-ACCESS  read-only
    STATUS      current
    DESCRIPTION
        "Port Binding Remote Transport Network Assigned Name (OIF Signaling Interface)" 
    ::=  { tnaMapDataEntry 2 }

tnaMapDataRemoteTnaMask OBJECT-TYPE
    SYNTAX      IpAddress
    MAX-ACCESS  read-only
    STATUS      current
    DESCRIPTION
        "Port Binding Remote Transport Network Assigned Name Mask (OIF Signaling Interface)" 
    ::=  { tnaMapDataEntry 3 }

tnaMapDataLocalPort OBJECT-TYPE
    SYNTAX      EntityIndex
    MAX-ACCESS  read-only
    STATUS      current
    DESCRIPTION
        "Port Binding Local Port AID (OIF Signaling Interface)" 
    ::=  { tnaMapDataEntry 4 }

controlPlaneEthConfigTable OBJECT-TYPE
    SYNTAX      SEQUENCE OF ControlPlaneEthConfigEntry
    MAX-ACCESS  not-accessible
    STATUS      current
    DESCRIPTION   ""
    ::=  { controlPlaneConfigAndStatus 32 }

controlPlaneEthConfigEntry OBJECT-TYPE
    SYNTAX      ControlPlaneEthConfigEntry
    MAX-ACCESS  not-accessible
    STATUS      current
    DESCRIPTION   ""
    INDEX       {
                  controlPlaneEthEntityIndex
                }
    ::=  { controlPlaneEthConfigTable 1 }

ControlPlaneEthConfigEntry ::=  SEQUENCE
  { controlPlaneEthConfigCtmConfigFlag Unsigned32,
    controlPlaneEthConfigCtmTraceDetail Unsigned32,
    controlPlaneEthConfigCtmSetupTimeout Unsigned32,
    controlPlaneEthConfigCtmShutdownTimeout Unsigned32,
    controlPlaneEthConfigCtmRetryWait Unsigned32,
    controlPlaneEthConfigCtmRetryWaitMultiplier Unsigned32,
    controlPlaneEthConfigCtmMaximumRetryWait Unsigned32,
    controlPlaneEthConfigCtmMaximumRetryNumber Unsigned32,
    controlPlaneEthConfigRaConfigFlag Unsigned32,
    controlPlaneEthConfigRaTraceDetail Unsigned32,
    controlPlaneEthConfigRaAlarmActivationTime Unsigned32,
    controlPlaneEthConfigCmConfigFlag Unsigned32,
    controlPlaneEthConfigCmTraceDetail Unsigned32,
    controlPlaneEthConfigCmAlarmActivationTime Unsigned32,
    controlPlaneEthConfigCmFisFrsTimeout Unsigned32,
    controlPlaneEthConfigCmCrankBackTimeout Unsigned32,
    controlPlaneEthConfigCdbConfigFlag Unsigned32,
    controlPlaneEthConfigCdbDetail Unsigned32,
    controlPlaneEthConfigCdbMaxSize Unsigned32,
    controlPlaneEthConfigRsvpConfigFlag Unsigned32,
    controlPlaneEthConfigRsvpMaxExpRestartTime Counter64String,
    controlPlaneEthConfigRsvpMaxExpRecoveryTime Unsigned32,
    controlPlaneEthConfigTedbConfigFlag Unsigned32,
    controlPlaneEthConfigTedbTraceDetail Unsigned32,
    controlPlaneEthConfigTedbMaxSize Unsigned32,
    controlPlaneEthConfigTedbRouterId IpAddress,
    controlPlaneEthConfigTedbMinAdvertWait Unsigned32,
    controlPlaneEthConfigNaasConfigFlag Unsigned32,
    controlPlaneEthConfigNaasTraceDetail Unsigned32,
    controlPlaneEthConfigNaasMaxSize Unsigned32,
    controlPlaneEthConfigNaasAdvertWait Unsigned32,
    controlPlaneEthConfigPcConfigFlag Unsigned32,
    controlPlaneEthConfigPcTraceDetail Unsigned32,
    controlPlaneEthConfigCdConfigFlag Unsigned32,
    controlPlaneEthConfigCdTraceDetail Unsigned32,
    controlPlaneEthConfigCdResyncTimeout Unsigned32,
    controlPlaneEthConfigRmConfigFlag Unsigned32,
    controlPlaneEthConfigRmTraceDetail Unsigned32,
    controlPlaneEthConfigRmTraceTarget Unsigned32 }

controlPlaneEthConfigCtmConfigFlag OBJECT-TYPE
    SYNTAX      Unsigned32
    MAX-ACCESS  read-write
    STATUS      current
    DESCRIPTION   "Label Switched Path Edge Component' Configuration Bitfield"
    ::=  { controlPlaneEthConfigEntry 1 }

controlPlaneEthConfigCtmTraceDetail OBJECT-TYPE
    SYNTAX      Unsigned32
    MAX-ACCESS  read-write
    STATUS      current
    DESCRIPTION   "Label Switched Path Edge Component' Trace Detail"
    ::=  { controlPlaneEthConfigEntry 2 }

controlPlaneEthConfigCtmSetupTimeout OBJECT-TYPE
    SYNTAX      Unsigned32 
    UNITS       "s"
    MAX-ACCESS  read-write
    STATUS      current
    DESCRIPTION   "Label Switched Path Edge Component' Set-Up Timeout"
    ::=  { controlPlaneEthConfigEntry 3 }

controlPlaneEthConfigCtmShutdownTimeout OBJECT-TYPE
    SYNTAX      Unsigned32 
    UNITS       "s"
    MAX-ACCESS  read-write
    STATUS      current
    DESCRIPTION   "Label Switched Path Edge Component' Shut-Down Timeout"
    ::=  { controlPlaneEthConfigEntry 4 }

controlPlaneEthConfigCtmRetryWait OBJECT-TYPE
    SYNTAX      Unsigned32 
    UNITS       "s"
    MAX-ACCESS  read-write
    STATUS      current
    DESCRIPTION   "Label Switched Path Edge Component' Initialization Retry Wait"
    ::=  { controlPlaneEthConfigEntry 5 }

controlPlaneEthConfigCtmRetryWaitMultiplier OBJECT-TYPE
    SYNTAX      Unsigned32
    MAX-ACCESS  read-write
    STATUS      current
    DESCRIPTION   "Label Switched Path Edge Component' Initialization Retry Wait Multiplier"
    ::=  { controlPlaneEthConfigEntry 6 }

controlPlaneEthConfigCtmMaximumRetryWait OBJECT-TYPE
    SYNTAX      Unsigned32 
    UNITS       "s"
    MAX-ACCESS  read-write
    STATUS      current
    DESCRIPTION   "Label Switched Path Edge Component' Initialization Maximum Retry Wait"
    ::=  { controlPlaneEthConfigEntry 7 }

controlPlaneEthConfigCtmMaximumRetryNumber OBJECT-TYPE
    SYNTAX      Unsigned32
    MAX-ACCESS  read-write
    STATUS      current
    DESCRIPTION   "Label Switched Path Edge Component' Initialization Maximum Retry Number"
    ::=  { controlPlaneEthConfigEntry 8 }

controlPlaneEthConfigRaConfigFlag OBJECT-TYPE
    SYNTAX      Unsigned32
    MAX-ACCESS  read-write
    STATUS      current
    DESCRIPTION   "Resource Allocator Configuration Bitfield"
    ::=  { controlPlaneEthConfigEntry 9 }

controlPlaneEthConfigRaTraceDetail OBJECT-TYPE
    SYNTAX      Unsigned32
    MAX-ACCESS  read-write
    STATUS      current
    DESCRIPTION   "Resource Allocator Trace Detail"
    ::=  { controlPlaneEthConfigEntry 10 }

controlPlaneEthConfigRaAlarmActivationTime OBJECT-TYPE
    SYNTAX      Unsigned32 
    UNITS       "s"
    MAX-ACCESS  read-write
    STATUS      current
    DESCRIPTION   "Resource Allocator Alarm Activation Time"
    ::=  { controlPlaneEthConfigEntry 11 }

controlPlaneEthConfigCmConfigFlag OBJECT-TYPE
    SYNTAX      Unsigned32
    MAX-ACCESS  read-write
    STATUS      current
    DESCRIPTION   "GMPLS Tunnel Manager Component' Configuration Bitfield"
    ::=  { controlPlaneEthConfigEntry 12 }

controlPlaneEthConfigCmTraceDetail OBJECT-TYPE
    SYNTAX      Unsigned32
    MAX-ACCESS  read-write
    STATUS      current
    DESCRIPTION   "GMPLS Tunnel Manager Component' Trace Detail"
    ::=  { controlPlaneEthConfigEntry 13 }

controlPlaneEthConfigCmAlarmActivationTime OBJECT-TYPE
    SYNTAX      Unsigned32 
    UNITS       "s"
    MAX-ACCESS  read-write
    STATUS      current
    DESCRIPTION   "GMPLS Tunnel Manager Component' Alarm Activation Time"
    ::=  { controlPlaneEthConfigEntry 14 }

controlPlaneEthConfigCmFisFrsTimeout OBJECT-TYPE
    SYNTAX      Unsigned32 
    UNITS       "s"
    MAX-ACCESS  read-write
    STATUS      current
    DESCRIPTION   "GMPLS Tunnel Manager Component' FIS-FRS Timeout"
    ::=  { controlPlaneEthConfigEntry 15 }

controlPlaneEthConfigCmCrankBackTimeout OBJECT-TYPE
    SYNTAX      Unsigned32 
    UNITS       "s"
    MAX-ACCESS  read-write
    STATUS      current
    DESCRIPTION   "GMPLS Tunnel Manager Component' Crank-Back Timeout"
    ::=  { controlPlaneEthConfigEntry 16 }

controlPlaneEthConfigCdbConfigFlag OBJECT-TYPE
    SYNTAX      Unsigned32
    MAX-ACCESS  read-write
    STATUS      current
    DESCRIPTION   "Label Swithed Path Database Component' Configuration Bitfield"
    ::=  { controlPlaneEthConfigEntry 17 }

controlPlaneEthConfigCdbDetail OBJECT-TYPE
    SYNTAX      Unsigned32
    MAX-ACCESS  read-write
    STATUS      current
    DESCRIPTION   "Label Swithed Path Database Component' Trace Detail"
    ::=  { controlPlaneEthConfigEntry 18 }

controlPlaneEthConfigCdbMaxSize OBJECT-TYPE
    SYNTAX      Unsigned32
    MAX-ACCESS  read-write
    STATUS      current
    DESCRIPTION   "Label Swithed Path Database Component' Maximum Size; 0 impiles no limit"
    ::=  { controlPlaneEthConfigEntry 19 }

controlPlaneEthConfigRsvpConfigFlag OBJECT-TYPE
    SYNTAX      Unsigned32
    MAX-ACCESS  read-write
    STATUS      current
    DESCRIPTION   "Resource Reservation Protocol Component' Configuration Bitfield"
    ::=  { controlPlaneEthConfigEntry 20 }

controlPlaneEthConfigRsvpMaxExpRestartTime OBJECT-TYPE
    SYNTAX      Counter64String 
    UNITS       "ms"
    MAX-ACCESS  read-write
    STATUS      current
    DESCRIPTION   "Maximum Expected Resource Reservation Protocol Component' Restart Time"
    ::=  { controlPlaneEthConfigEntry 21 }

controlPlaneEthConfigRsvpMaxExpRecoveryTime OBJECT-TYPE
    SYNTAX      Unsigned32 
    UNITS       "ms"
    MAX-ACCESS  read-write
    STATUS      current
    DESCRIPTION   "Maximum Expected Resource Reservation Protocol Component' Recovery Time"
    ::=  { controlPlaneEthConfigEntry 22 }

controlPlaneEthConfigTedbConfigFlag OBJECT-TYPE
    SYNTAX      Unsigned32
    MAX-ACCESS  read-write
    STATUS      current
    DESCRIPTION   "Traffic Engineering Component' Database Configuration Bitfield"
    ::=  { controlPlaneEthConfigEntry 23 }

controlPlaneEthConfigTedbTraceDetail OBJECT-TYPE
    SYNTAX      Unsigned32
    MAX-ACCESS  read-write
    STATUS      current
    DESCRIPTION   "Traffic Engineering Component' Database Trace Detail"
    ::=  { controlPlaneEthConfigEntry 24 }

controlPlaneEthConfigTedbMaxSize OBJECT-TYPE
    SYNTAX      Unsigned32
    MAX-ACCESS  read-write
    STATUS      current
    DESCRIPTION   "Traffic Engineering Component' Database Maximum Size"
    ::=  { controlPlaneEthConfigEntry 25 }

controlPlaneEthConfigTedbRouterId OBJECT-TYPE
    SYNTAX      IpAddress
    MAX-ACCESS  read-write
    STATUS      current
    DESCRIPTION   "Traffic Engineering Component' Router ID"
    ::=  { controlPlaneEthConfigEntry 26 }

controlPlaneEthConfigTedbMinAdvertWait OBJECT-TYPE
    SYNTAX      Unsigned32 
    UNITS       "s"
    MAX-ACCESS  read-write
    STATUS      current
    DESCRIPTION   "Traffic Engineering Component' Minimum Advertisement Wait"
    ::=  { controlPlaneEthConfigEntry 27 }

controlPlaneEthConfigNaasConfigFlag OBJECT-TYPE
    SYNTAX      Unsigned32
    MAX-ACCESS  read-write
    STATUS      current
    DESCRIPTION   "Node Attribute Advertising Service Database Configuration Bitfield"
    ::=  { controlPlaneEthConfigEntry 28 }

controlPlaneEthConfigNaasTraceDetail OBJECT-TYPE
    SYNTAX      Unsigned32
    MAX-ACCESS  read-write
    STATUS      current
    DESCRIPTION   "Node Attribute Advertising Service Database Trace Detail"
    ::=  { controlPlaneEthConfigEntry 29 }

controlPlaneEthConfigNaasMaxSize OBJECT-TYPE
    SYNTAX      Unsigned32
    MAX-ACCESS  read-write
    STATUS      current
    DESCRIPTION   "Node Attribute Advertising Service Database Maximum Size"
    ::=  { controlPlaneEthConfigEntry 30 }

controlPlaneEthConfigNaasAdvertWait OBJECT-TYPE
    SYNTAX      Unsigned32 
    UNITS       "s"
    MAX-ACCESS  read-write
    STATUS      current
    DESCRIPTION   "Node Attribute Advertising Service Database Advertisement Wait"
    ::=  { controlPlaneEthConfigEntry 31 }

controlPlaneEthConfigPcConfigFlag OBJECT-TYPE
    SYNTAX      Unsigned32
    MAX-ACCESS  read-write
    STATUS      current
    DESCRIPTION   "Path Computation Component' Configuration Bitfield"
    ::=  { controlPlaneEthConfigEntry 32 }

controlPlaneEthConfigPcTraceDetail OBJECT-TYPE
    SYNTAX      Unsigned32
    MAX-ACCESS  read-write
    STATUS      current
    DESCRIPTION   "Path Computation Component' Trace Detail."
    ::=  { controlPlaneEthConfigEntry 33 }

controlPlaneEthConfigCdConfigFlag OBJECT-TYPE
    SYNTAX      Unsigned32
    MAX-ACCESS  read-write
    STATUS      current
    DESCRIPTION   "Configuration Data Component' Configuration Bitfield"
    ::=  { controlPlaneEthConfigEntry 34 }

controlPlaneEthConfigCdTraceDetail OBJECT-TYPE
    SYNTAX      Unsigned32
    MAX-ACCESS  read-write
    STATUS      current
    DESCRIPTION   "Configuration Data Component' Trace Detail"
    ::=  { controlPlaneEthConfigEntry 35 }

controlPlaneEthConfigCdResyncTimeout OBJECT-TYPE
    SYNTAX      Unsigned32
    MAX-ACCESS  read-write
    STATUS      current
    DESCRIPTION   "Configuration Data Component' Resync Timeout"
    ::=  { controlPlaneEthConfigEntry 36 }

controlPlaneEthConfigRmConfigFlag OBJECT-TYPE
    SYNTAX      Unsigned32
    MAX-ACCESS  read-write
    STATUS      current
    DESCRIPTION   "Resource Management Component' Configuration Bitfield"
    ::=  { controlPlaneEthConfigEntry 37 }

controlPlaneEthConfigRmTraceDetail OBJECT-TYPE
    SYNTAX      Unsigned32
    MAX-ACCESS  read-write
    STATUS      current
    DESCRIPTION   "Resource Management Component' Trace Detail"
    ::=  { controlPlaneEthConfigEntry 38 }

controlPlaneEthConfigRmTraceTarget OBJECT-TYPE
    SYNTAX      Unsigned32
    MAX-ACCESS  read-write
    STATUS      current
    DESCRIPTION   "Resource Management Component' Trace Target"
    ::=  { controlPlaneEthConfigEntry 39 }

controlPlaneEthDataTable OBJECT-TYPE
    SYNTAX      SEQUENCE OF ControlPlaneEthDataEntry
    MAX-ACCESS  not-accessible
    STATUS      current
    DESCRIPTION   ""
    ::=  { controlPlaneConfigAndStatus 33 }

controlPlaneEthDataEntry OBJECT-TYPE
    SYNTAX      ControlPlaneEthDataEntry
    MAX-ACCESS  not-accessible
    STATUS      current
    DESCRIPTION   ""
    INDEX       {
                  controlPlaneEthEntityIndex
                }
    ::=  { controlPlaneEthDataTable 1 }

ControlPlaneEthDataEntry ::=  SEQUENCE
  { controlPlaneEthDataCtmAlias SnmpAdminString,
    controlPlaneEthDataRaAlias SnmpAdminString,
    controlPlaneEthDataCmAlias SnmpAdminString,
    controlPlaneEthDataCdbAlias SnmpAdminString,
    controlPlaneEthDataTedbAlias SnmpAdminString,
    controlPlaneEthDataNaasAlias SnmpAdminString,
    controlPlaneEthDataPcAlias SnmpAdminString,
    controlPlaneEthDataRsvpAlias SnmpAdminString,
    controlPlaneEthDataCdAlias SnmpAdminString,
    controlPlaneEthDataRmAlias SnmpAdminString }

controlPlaneEthDataCtmAlias OBJECT-TYPE
    SYNTAX      SnmpAdminString
    MAX-ACCESS  read-only
    STATUS      current
    DESCRIPTION   "Label Switched Path Edge Component Component' Base Name"
    ::=  { controlPlaneEthDataEntry 1 }

controlPlaneEthDataRaAlias OBJECT-TYPE
    SYNTAX      SnmpAdminString
    MAX-ACCESS  read-only
    STATUS      current
    DESCRIPTION   "Resource Allocator Component' Base Name"
    ::=  { controlPlaneEthDataEntry 2 }

controlPlaneEthDataCmAlias OBJECT-TYPE
    SYNTAX      SnmpAdminString
    MAX-ACCESS  read-only
    STATUS      current
    DESCRIPTION   "GMPLS Tunnel Manager Component' Base Name"
    ::=  { controlPlaneEthDataEntry 3 }

controlPlaneEthDataCdbAlias OBJECT-TYPE
    SYNTAX      SnmpAdminString
    MAX-ACCESS  read-only
    STATUS      current
    DESCRIPTION   "Label Swithed Path Database Component' Base Name"
    ::=  { controlPlaneEthDataEntry 4 }

controlPlaneEthDataTedbAlias OBJECT-TYPE
    SYNTAX      SnmpAdminString
    MAX-ACCESS  read-only
    STATUS      current
    DESCRIPTION   "Traffic Engineering Component' Database Name"
    ::=  { controlPlaneEthDataEntry 5 }

controlPlaneEthDataNaasAlias OBJECT-TYPE
    SYNTAX      SnmpAdminString
    MAX-ACCESS  read-only
    STATUS      current
    DESCRIPTION   "Node Attribute Advertising Service Database Component' Base Name"
    ::=  { controlPlaneEthDataEntry 6 }

controlPlaneEthDataPcAlias OBJECT-TYPE
    SYNTAX      SnmpAdminString
    MAX-ACCESS  read-only
    STATUS      current
    DESCRIPTION   "Path Computation Engine Component' Base Name"
    ::=  { controlPlaneEthDataEntry 7 }

controlPlaneEthDataRsvpAlias OBJECT-TYPE
    SYNTAX      SnmpAdminString
    MAX-ACCESS  read-only
    STATUS      current
    DESCRIPTION   "Resource Reservation Protocol Component' Base Name"
    ::=  { controlPlaneEthDataEntry 8 }

controlPlaneEthDataCdAlias OBJECT-TYPE
    SYNTAX      SnmpAdminString
    MAX-ACCESS  read-only
    STATUS      current
    DESCRIPTION   "Configuration Data Component' Base Name"
    ::=  { controlPlaneEthDataEntry 9 }

controlPlaneEthDataRmAlias OBJECT-TYPE
    SYNTAX      SnmpAdminString
    MAX-ACCESS  read-only
    STATUS      current
    DESCRIPTION   "Resource Management Component' Base Name"
    ::=  { controlPlaneEthDataEntry 10 }

tunnelEthConfigTable OBJECT-TYPE
    SYNTAX      SEQUENCE OF TunnelEthConfigEntry
    MAX-ACCESS  not-accessible
    STATUS      current
    DESCRIPTION   ""
    ::=  { controlPlaneConfigAndStatus 34 }

tunnelEthConfigEntry OBJECT-TYPE
    SYNTAX      TunnelEthConfigEntry
    MAX-ACCESS  not-accessible
    STATUS      current
    DESCRIPTION   ""
    INDEX       {
                  controlPlaneEthEntityIndex
                }
    ::=  { tunnelEthConfigTable 1 }

TunnelEthConfigEntry ::=  SEQUENCE
  { tunnelEthConfigAlias SnmpAdminString,
    tunnelEthConfigProvisionedPaths SnmpAdminString,
    tunnelEthConfigPin FspR7CpPinning,
    tunnelEthConfigAbortProcess FspR7CpAbortProcess,
    tunnelEthConfigCommand FspR7CpCommand,
    tunnelEthConfigCirRcv Unsigned32,
    tunnelEthConfigCbsRcv Unsigned32,
    tunnelEthConfigProtectionType FspR7CpProtectionType,
    tunnelEthConfigRestorationType FspR7CpRestorationType,
    tunnelEthConfigMonitorEntities FspR7EnableDisable,
    tunnelEthConfigAdminModifier FspR7CommandModifier,
    tunnelEthConfigExcludedPaths SnmpAdminString,
    tunnelEthConfigPreferPcs FspR7YesNo,
    tunnelEthConfigEroScope SnmpAdminString,
    tunnelEthConfigEroLifeCycle SnmpAdminString,
    tunnelEthConfigXroScope SnmpAdminString,
    tunnelEthConfigXroLifeCycle SnmpAdminString }

tunnelEthConfigAlias OBJECT-TYPE
    SYNTAX      SnmpAdminString
    MAX-ACCESS  read-write
    STATUS      current
    DESCRIPTION   "Alias."
    ::=  { tunnelEthConfigEntry 1 }

tunnelEthConfigProvisionedPaths OBJECT-TYPE
    SYNTAX      SnmpAdminString
    MAX-ACCESS  read-write
    STATUS      current
    DESCRIPTION   ""
    ::=  { tunnelEthConfigEntry 2 }

tunnelEthConfigPin OBJECT-TYPE
    SYNTAX      FspR7CpPinning
    MAX-ACCESS  read-write
    STATUS      current
    DESCRIPTION   ""
    ::=  { tunnelEthConfigEntry 3 }

tunnelEthConfigAbortProcess OBJECT-TYPE
    SYNTAX      FspR7CpAbortProcess
    MAX-ACCESS  read-write
    STATUS      current
    DESCRIPTION   ""
    ::=  { tunnelEthConfigEntry 4 }

tunnelEthConfigCommand OBJECT-TYPE
    SYNTAX      FspR7CpCommand
    MAX-ACCESS  read-write
    STATUS      current
    DESCRIPTION   ""
    ::=  { tunnelEthConfigEntry 5 }

tunnelEthConfigCirRcv OBJECT-TYPE
    SYNTAX      Unsigned32 
    UNITS       "Mbps"
    MAX-ACCESS  read-write
    STATUS      current
    DESCRIPTION
        "CIR (Committed Information Rate ) is used on Ethernet Interfaces with a policing function" 
    ::=  { tunnelEthConfigEntry 6 }

tunnelEthConfigCbsRcv OBJECT-TYPE
    SYNTAX      Unsigned32 (0..26214400 | 4294967295) 
    UNITS       "Byte"
    MAX-ACCESS  read-write
    STATUS      current
    DESCRIPTION
        "Committed Burst Size" 
    ::=  { tunnelEthConfigEntry 7 }

tunnelEthConfigProtectionType OBJECT-TYPE
    SYNTAX      FspR7CpProtectionType
    MAX-ACCESS  read-write
    STATUS      current
    DESCRIPTION   ""
    ::=  { tunnelEthConfigEntry 8 }

tunnelEthConfigRestorationType OBJECT-TYPE
    SYNTAX      FspR7CpRestorationType
    MAX-ACCESS  read-write
    STATUS      current
    DESCRIPTION   ""
    ::=  { tunnelEthConfigEntry 9 }

tunnelEthConfigMonitorEntities OBJECT-TYPE
    SYNTAX      FspR7EnableDisable
    MAX-ACCESS  read-write
    STATUS      current
    DESCRIPTION   ""
    ::=  { tunnelEthConfigEntry 10 }

tunnelEthConfigAdminModifier OBJECT-TYPE
    SYNTAX      FspR7CommandModifier
    MAX-ACCESS  read-write
    STATUS      current
    DESCRIPTION   ""
    ::=  { tunnelEthConfigEntry 11 }

tunnelEthConfigExcludedPaths OBJECT-TYPE
    SYNTAX      SnmpAdminString
    MAX-ACCESS  read-write
    STATUS      current
    DESCRIPTION
        "Lists of Path Elements to be excluded" 
    ::=  { tunnelEthConfigEntry 12 }

tunnelEthConfigPreferPcs OBJECT-TYPE
    SYNTAX      FspR7YesNo
    MAX-ACCESS  read-write
    STATUS      current
    DESCRIPTION
        "Preferred Path Computation Engine (Server)" 
    ::=  { tunnelEthConfigEntry 13 }

tunnelEthConfigEroScope OBJECT-TYPE
    SYNTAX      SnmpAdminString
    MAX-ACCESS  read-write
    STATUS      current
    DESCRIPTION
        "Inclusion Route - Scope" 
    ::=  { tunnelEthConfigEntry 14 }

tunnelEthConfigEroLifeCycle OBJECT-TYPE
    SYNTAX      SnmpAdminString
    MAX-ACCESS  read-write
    STATUS      current
    DESCRIPTION
        "Inclusion Route - Life Cycle" 
    ::=  { tunnelEthConfigEntry 15 }

tunnelEthConfigXroScope OBJECT-TYPE
    SYNTAX      SnmpAdminString
    MAX-ACCESS  read-write
    STATUS      current
    DESCRIPTION
        "Exclusion Path Elements - Scope" 
    ::=  { tunnelEthConfigEntry 16 }

tunnelEthConfigXroLifeCycle OBJECT-TYPE
    SYNTAX      SnmpAdminString
    MAX-ACCESS  read-write
    STATUS      current
    DESCRIPTION
        "Exclusion Path Elements - Life Cycle" 
    ::=  { tunnelEthConfigEntry 17 }

tunnelEthDataTable OBJECT-TYPE
    SYNTAX      SEQUENCE OF TunnelEthDataEntry
    MAX-ACCESS  not-accessible
    STATUS      current
    DESCRIPTION   ""
    ::=  { controlPlaneConfigAndStatus 35 }

tunnelEthDataEntry OBJECT-TYPE
    SYNTAX      TunnelEthDataEntry
    MAX-ACCESS  not-accessible
    STATUS      current
    DESCRIPTION   ""
    INDEX       {
                  controlPlaneEthEntityIndex
                }
    ::=  { tunnelEthDataTable 1 }

TunnelEthDataEntry ::=  SEQUENCE
  { tunnelEthDataTunnelId SnmpAdminString,
    tunnelEthDataTunnelNo Unsigned32,
    tunnelEthDataTunnelType FspR7CpTunnelType,
    tunnelEthDataFromTid SnmpAdminString,
    tunnelEthDataFromNodeIP IpAddress,
    tunnelEthDataToTid SnmpAdminString,
    tunnelEthDataToTidMonitor SnmpAdminString,
    tunnelEthDataToNodeIp IpAddress,
    tunnelEthDataToNodeIpMonitor IpAddress,
    tunnelEthDataFromAid EntityIndex,
    tunnelEthDataToAid EntityIndex,
    tunnelEthDataConnectionDirection FspR7Conn,
    tunnelEthDataFacilityType FspR7InterfaceType,
    tunnelEthDataComputedPaths SnmpAdminString,
    tunnelEthDataComputationState FspR7CpCompState,
    tunnelEthDataErrorMessage SnmpAdminString,
    tunnelEthDataCirTrmt Unsigned32,
    tunnelEthDataCbsTrmt Unsigned32,
    tunnelEthDataErrorCodeMajor Unsigned32,
    tunnelEthDataErrorCodeMinor Integer32,
    tunnelEthDataErrorIp IpAddress,
    tunnelEthDataErrorTid SnmpAdminString,
    tunnelEthDataErrorCategory FspR7CpErrorCategory,
    tunnelEthDataSpecificErrorMessage SnmpAdminString,
    tunnelEthDataTunnelScope FspR7CpTunnelScope,
    tunnelEthDataLayer FspR7PacketsLayer,
    tunnelEthDataOifUni FspR7YesNo,
    tunnelEthDataTunnelNumberExtension Unsigned32,
    tunnelEthDataFromAidString SnmpAdminString,
    tunnelEthDataToAidString SnmpAdminString }

tunnelEthDataTunnelId OBJECT-TYPE
    SYNTAX      SnmpAdminString
    MAX-ACCESS  read-only
    STATUS      current
    DESCRIPTION   ""
    ::=  { tunnelEthDataEntry 1 }

tunnelEthDataTunnelNo OBJECT-TYPE
    SYNTAX      Unsigned32
    MAX-ACCESS  read-only
    STATUS      current
    DESCRIPTION   ""
    ::=  { tunnelEthDataEntry 2 }

tunnelEthDataTunnelType OBJECT-TYPE
    SYNTAX      FspR7CpTunnelType
    MAX-ACCESS  read-only
    STATUS      current
    DESCRIPTION   ""
    ::=  { tunnelEthDataEntry 3 }

tunnelEthDataFromTid OBJECT-TYPE
    SYNTAX      SnmpAdminString
    MAX-ACCESS  read-only
    STATUS      current
    DESCRIPTION   ""
    ::=  { tunnelEthDataEntry 4 }

tunnelEthDataFromNodeIP OBJECT-TYPE
    SYNTAX      IpAddress
    MAX-ACCESS  read-only
    STATUS      current
    DESCRIPTION   ""
    ::=  { tunnelEthDataEntry 5 }

tunnelEthDataToTid OBJECT-TYPE
    SYNTAX      SnmpAdminString
    MAX-ACCESS  read-only
    STATUS      current
    DESCRIPTION   ""
    ::=  { tunnelEthDataEntry 6 }

tunnelEthDataToTidMonitor OBJECT-TYPE
    SYNTAX      SnmpAdminString
    MAX-ACCESS  read-only
    STATUS      current
    DESCRIPTION   ""
    ::=  { tunnelEthDataEntry 7 }

tunnelEthDataToNodeIp OBJECT-TYPE
    SYNTAX      IpAddress
    MAX-ACCESS  read-only
    STATUS      current
    DESCRIPTION   ""
    ::=  { tunnelEthDataEntry 8 }

tunnelEthDataToNodeIpMonitor OBJECT-TYPE
    SYNTAX      IpAddress
    MAX-ACCESS  read-only
    STATUS      current
    DESCRIPTION   ""
    ::=  { tunnelEthDataEntry 9 }

tunnelEthDataFromAid OBJECT-TYPE
    SYNTAX      EntityIndex
    MAX-ACCESS  read-only
    STATUS      current
    DESCRIPTION   ""
    ::=  { tunnelEthDataEntry 10 }

tunnelEthDataToAid OBJECT-TYPE
    SYNTAX      EntityIndex
    MAX-ACCESS  read-only
    STATUS      current
    DESCRIPTION   ""
    ::=  { tunnelEthDataEntry 11 }

tunnelEthDataConnectionDirection OBJECT-TYPE
    SYNTAX      FspR7Conn
    MAX-ACCESS  read-only
    STATUS      current
    DESCRIPTION   ""
    ::=  { tunnelEthDataEntry 12 }

tunnelEthDataFacilityType OBJECT-TYPE
    SYNTAX      FspR7InterfaceType
    MAX-ACCESS  read-only
    STATUS      current
    DESCRIPTION   ""
    ::=  { tunnelEthDataEntry 13 }

tunnelEthDataComputedPaths OBJECT-TYPE
    SYNTAX      SnmpAdminString
    MAX-ACCESS  read-only
    STATUS      current
    DESCRIPTION   ""
    ::=  { tunnelEthDataEntry 14 }

tunnelEthDataComputationState OBJECT-TYPE
    SYNTAX      FspR7CpCompState
    MAX-ACCESS  read-only
    STATUS      current
    DESCRIPTION   ""
    ::=  { tunnelEthDataEntry 15 }

tunnelEthDataErrorMessage OBJECT-TYPE
    SYNTAX      SnmpAdminString
    MAX-ACCESS  read-only
    STATUS      current
    DESCRIPTION   ""
    ::=  { tunnelEthDataEntry 16 }

tunnelEthDataCirTrmt OBJECT-TYPE
    SYNTAX      Unsigned32 
    UNITS       "Mbps"
    MAX-ACCESS  read-only
    STATUS      current
    DESCRIPTION
        "CIR (Committed Information Rate ) is used on Ethernet Interfaces with a policing function" 
    ::=  { tunnelEthDataEntry 17 }

tunnelEthDataCbsTrmt OBJECT-TYPE
    SYNTAX      Unsigned32 (0..25600 | 4294967295) 
    UNITS       "kByte"
    MAX-ACCESS  read-only
    STATUS      current
    DESCRIPTION
        "Committed Burst Size" 
    ::=  { tunnelEthDataEntry 18 }

tunnelEthDataErrorCodeMajor OBJECT-TYPE
    SYNTAX      Unsigned32
    MAX-ACCESS  read-only
    STATUS      current
    DESCRIPTION
        "Errorcode Major" 
    ::=  { tunnelEthDataEntry 19 }

tunnelEthDataErrorCodeMinor OBJECT-TYPE
    SYNTAX      Integer32
    MAX-ACCESS  read-only
    STATUS      current
    DESCRIPTION
        "Errorcode Minor" 
    ::=  { tunnelEthDataEntry 20 }

tunnelEthDataErrorIp OBJECT-TYPE
    SYNTAX      IpAddress
    MAX-ACCESS  read-only
    STATUS      current
    DESCRIPTION
        "Error IP" 
    ::=  { tunnelEthDataEntry 21 }

tunnelEthDataErrorTid OBJECT-TYPE
    SYNTAX      SnmpAdminString
    MAX-ACCESS  read-only
    STATUS      current
    DESCRIPTION
        "Error TID" 
    ::=  { tunnelEthDataEntry 22 }

tunnelEthDataErrorCategory OBJECT-TYPE
    SYNTAX      FspR7CpErrorCategory
    MAX-ACCESS  read-only
    STATUS      current
    DESCRIPTION
        "CP Provisioning Failure Category" 
    ::=  { tunnelEthDataEntry 23 }

tunnelEthDataSpecificErrorMessage OBJECT-TYPE
    SYNTAX      SnmpAdminString
    MAX-ACCESS  read-only
    STATUS      current
    DESCRIPTION
        "Specific Error Message" 
    ::=  { tunnelEthDataEntry 24 }

tunnelEthDataTunnelScope OBJECT-TYPE
    SYNTAX      FspR7CpTunnelScope
    MAX-ACCESS  read-only
    STATUS      current
    DESCRIPTION
        "Service Scope extending over either Client or Network Ports of Modules or Links (UN or NR) for Connection Segements" 
    ::=  { tunnelEthDataEntry 25 }

tunnelEthDataLayer OBJECT-TYPE
    SYNTAX      FspR7PacketsLayer
    MAX-ACCESS  read-only
    STATUS      current
    DESCRIPTION
        "Notional Layer of Advertisement on Packets on the LIF" 
    ::=  { tunnelEthDataEntry 26 }

tunnelEthDataOifUni OBJECT-TYPE
    SYNTAX      FspR7YesNo
    MAX-ACCESS  read-only
    STATUS      current
    DESCRIPTION
        "OIF UNI Tunnel" 
    ::=  { tunnelEthDataEntry 27 }

tunnelEthDataTunnelNumberExtension OBJECT-TYPE
    SYNTAX      Unsigned32
    MAX-ACCESS  read-only
    STATUS      current
    DESCRIPTION
        "Tunnel Number Extension. (internal: serviceID.extTunnelID)" 
    ::=  { tunnelEthDataEntry 28 }

tunnelEthDataFromAidString OBJECT-TYPE
    SYNTAX      SnmpAdminString
    MAX-ACCESS  read-only
    STATUS      current
    DESCRIPTION
        "" 
    ::=  { tunnelEthDataEntry 29 }

tunnelEthDataToAidString OBJECT-TYPE
    SYNTAX      SnmpAdminString
    MAX-ACCESS  read-only
    STATUS      current
    DESCRIPTION
        "" 
    ::=  { tunnelEthDataEntry 30 }

connectionEthConfigTable OBJECT-TYPE
    SYNTAX      SEQUENCE OF ConnectionEthConfigEntry
    MAX-ACCESS  not-accessible
    STATUS      current
    DESCRIPTION   ""
    ::=  { controlPlaneConfigAndStatus 36 }

connectionEthConfigEntry OBJECT-TYPE
    SYNTAX      ConnectionEthConfigEntry
    MAX-ACCESS  not-accessible
    STATUS      current
    DESCRIPTION   ""
    INDEX       {
                  controlPlaneEthEntityIndex
                }
    ::=  { connectionEthConfigTable 1 }

ConnectionEthConfigEntry ::=  SEQUENCE
  { connectionEthConfigCancelConnEntities FspR7CpCancConnection }

connectionEthConfigCancelConnEntities OBJECT-TYPE
    SYNTAX      FspR7CpCancConnection
    MAX-ACCESS  read-write
    STATUS      current
    DESCRIPTION   ""
    ::=  { connectionEthConfigEntry 1 }

connectionEthDataTable OBJECT-TYPE
    SYNTAX      SEQUENCE OF ConnectionEthDataEntry
    MAX-ACCESS  not-accessible
    STATUS      current
    DESCRIPTION   ""
    ::=  { controlPlaneConfigAndStatus 37 }

connectionEthDataEntry OBJECT-TYPE
    SYNTAX      ConnectionEthDataEntry
    MAX-ACCESS  not-accessible
    STATUS      current
    DESCRIPTION   ""
    INDEX       {
                  controlPlaneEthEntityIndex
                }
    ::=  { connectionEthDataTable 1 }

ConnectionEthDataEntry ::=  SEQUENCE
  { connectionEthDataTunnelId SnmpAdminString,
    connectionEthDataTunnelNo Unsigned32,
    connectionEthDataTunnelType FspR7CpTunnelType,
    connectionEthDataFromTid SnmpAdminString,
    connectionEthDataFromNodeIp IpAddress,
    connectionEthDataToTid SnmpAdminString,
    connectionEthDataToNodeIp IpAddress,
    connectionEthDataFromAid EntityIndex,
    connectionEthDataToAid EntityIndex,
    connectionEthDataConnectionDirection FspR7Conn,
    connectionEthDataNetworkElementPosition FspR7CpNePosition,
    connectionEthDataSignalledPaths SnmpAdminString,
    connectionEthDataComputedPaths SnmpAdminString,
    connectionEthDataRole FspR7CpRole,
    connectionEthDataErrorMessage SnmpAdminString,
    connectionEthDataCirTrmt Unsigned32,
    connectionEthDataCbsTrmt Unsigned32,
    connectionEthDataCirRcv Unsigned32,
    connectionEthDataCbsRcv Unsigned32,
    connectionEthDataActivationState FspR7CpActivState,
    connectionEthDataRestorable FspR7FalseTrue,
    connectionEthDataModificationState FspR7CpCompState,
    connectionEthDataRestorationState FspR7CpRestorationState,
    connectionEthDataMonitorEntities FspR7EnableDisable,
    connectionEthDataTunnelScope FspR7CpTunnelScope,
    connectionEthDataLayer FspR7PacketsLayer,
    connectionEthDataSourceTna IpAddress,
    connectionEthDataDestinationTna IpAddress,
    connectionEthDataTunnelNumberExtension Unsigned32,
    connectionEthDataTunnelInstance Unsigned32,
    connectionEthDataConnectionNo Unsigned32,
    connectionEthDataFromAidString SnmpAdminString,
    connectionEthDataToAidString SnmpAdminString }

connectionEthDataTunnelId OBJECT-TYPE
    SYNTAX      SnmpAdminString
    MAX-ACCESS  read-only
    STATUS      current
    DESCRIPTION   ""
    ::=  { connectionEthDataEntry 1 }

connectionEthDataTunnelNo OBJECT-TYPE
    SYNTAX      Unsigned32
    MAX-ACCESS  read-only
    STATUS      current
    DESCRIPTION   ""
    ::=  { connectionEthDataEntry 2 }

connectionEthDataTunnelType OBJECT-TYPE
    SYNTAX      FspR7CpTunnelType
    MAX-ACCESS  read-only
    STATUS      current
    DESCRIPTION   ""
    ::=  { connectionEthDataEntry 3 }

connectionEthDataFromTid OBJECT-TYPE
    SYNTAX      SnmpAdminString
    MAX-ACCESS  read-only
    STATUS      current
    DESCRIPTION   ""
    ::=  { connectionEthDataEntry 4 }

connectionEthDataFromNodeIp OBJECT-TYPE
    SYNTAX      IpAddress
    MAX-ACCESS  read-only
    STATUS      current
    DESCRIPTION   ""
    ::=  { connectionEthDataEntry 5 }

connectionEthDataToTid OBJECT-TYPE
    SYNTAX      SnmpAdminString
    MAX-ACCESS  read-only
    STATUS      current
    DESCRIPTION   ""
    ::=  { connectionEthDataEntry 6 }

connectionEthDataToNodeIp OBJECT-TYPE
    SYNTAX      IpAddress
    MAX-ACCESS  read-only
    STATUS      current
    DESCRIPTION   ""
    ::=  { connectionEthDataEntry 7 }

connectionEthDataFromAid OBJECT-TYPE
    SYNTAX      EntityIndex
    MAX-ACCESS  read-only
    STATUS      current
    DESCRIPTION   ""
    ::=  { connectionEthDataEntry 8 }

connectionEthDataToAid OBJECT-TYPE
    SYNTAX      EntityIndex
    MAX-ACCESS  read-only
    STATUS      current
    DESCRIPTION   ""
    ::=  { connectionEthDataEntry 9 }

connectionEthDataConnectionDirection OBJECT-TYPE
    SYNTAX      FspR7Conn
    MAX-ACCESS  read-only
    STATUS      current
    DESCRIPTION   ""
    ::=  { connectionEthDataEntry 10 }

connectionEthDataNetworkElementPosition OBJECT-TYPE
    SYNTAX      FspR7CpNePosition
    MAX-ACCESS  read-only
    STATUS      current
    DESCRIPTION   ""
    ::=  { connectionEthDataEntry 11 }

connectionEthDataSignalledPaths OBJECT-TYPE
    SYNTAX      SnmpAdminString
    MAX-ACCESS  read-only
    STATUS      current
    DESCRIPTION   ""
    ::=  { connectionEthDataEntry 12 }

connectionEthDataComputedPaths OBJECT-TYPE
    SYNTAX      SnmpAdminString
    MAX-ACCESS  read-only
    STATUS      current
    DESCRIPTION   ""
    ::=  { connectionEthDataEntry 13 }

connectionEthDataRole OBJECT-TYPE
    SYNTAX      FspR7CpRole
    MAX-ACCESS  read-only
    STATUS      current
    DESCRIPTION   ""
    ::=  { connectionEthDataEntry 14 }

connectionEthDataErrorMessage OBJECT-TYPE
    SYNTAX      SnmpAdminString
    MAX-ACCESS  read-only
    STATUS      current
    DESCRIPTION   ""
    ::=  { connectionEthDataEntry 15 }

connectionEthDataCirTrmt OBJECT-TYPE
    SYNTAX      Unsigned32 
    UNITS       "Mbps"
    MAX-ACCESS  read-only
    STATUS      current
    DESCRIPTION
        "CIR (Committed Information Rate ) is used on Ethernet Interfaces with a policing function" 
    ::=  { connectionEthDataEntry 16 }

connectionEthDataCbsTrmt OBJECT-TYPE
    SYNTAX      Unsigned32 (0..25600 | 4294967295) 
    UNITS       "kByte"
    MAX-ACCESS  read-only
    STATUS      current
    DESCRIPTION
        "Committed Burst Size" 
    ::=  { connectionEthDataEntry 17 }

connectionEthDataCirRcv OBJECT-TYPE
    SYNTAX      Unsigned32 
    UNITS       "Mbps"
    MAX-ACCESS  read-only
    STATUS      current
    DESCRIPTION
        "CIR (Committed Information Rate ) is used on Ethernet Interfaces with a policing function" 
    ::=  { connectionEthDataEntry 18 }

connectionEthDataCbsRcv OBJECT-TYPE
    SYNTAX      Unsigned32 (0..26214400 | 4294967295) 
    UNITS       "Byte"
    MAX-ACCESS  read-only
    STATUS      current
    DESCRIPTION
        "Committed Burst Size" 
    ::=  { connectionEthDataEntry 19 }

connectionEthDataActivationState OBJECT-TYPE
    SYNTAX      FspR7CpActivState
    MAX-ACCESS  read-only
    STATUS      current
    DESCRIPTION   ""
    ::=  { connectionEthDataEntry 20 }

connectionEthDataRestorable OBJECT-TYPE
    SYNTAX      FspR7FalseTrue
    MAX-ACCESS  read-only
    STATUS      current
    DESCRIPTION   ""
    ::=  { connectionEthDataEntry 21 }

connectionEthDataModificationState OBJECT-TYPE
    SYNTAX      FspR7CpCompState
    MAX-ACCESS  read-only
    STATUS      current
    DESCRIPTION
        "Modification Enumeration State" 
    ::=  { connectionEthDataEntry 22 }

connectionEthDataRestorationState OBJECT-TYPE
    SYNTAX      FspR7CpRestorationState
    MAX-ACCESS  read-only
    STATUS      current
    DESCRIPTION   ""
    ::=  { connectionEthDataEntry 23 }

connectionEthDataMonitorEntities OBJECT-TYPE
    SYNTAX      FspR7EnableDisable
    MAX-ACCESS  read-only
    STATUS      current
    DESCRIPTION   ""
    ::=  { connectionEthDataEntry 24 }

connectionEthDataTunnelScope OBJECT-TYPE
    SYNTAX      FspR7CpTunnelScope
    MAX-ACCESS  read-only
    STATUS      current
    DESCRIPTION
        "Service Scope extending over either Client or Network Ports of Modules or Links (UN or NR) for Connection Segements" 
    ::=  { connectionEthDataEntry 25 }

connectionEthDataLayer OBJECT-TYPE
    SYNTAX      FspR7PacketsLayer
    MAX-ACCESS  read-only
    STATUS      current
    DESCRIPTION
        "Notional Layer of Advertisement on Packets on the LIF" 
    ::=  { connectionEthDataEntry 26 }

connectionEthDataSourceTna OBJECT-TYPE
    SYNTAX      IpAddress
    MAX-ACCESS  read-only
    STATUS      current
    DESCRIPTION
        "Source Transport Network Assigned Name" 
    ::=  { connectionEthDataEntry 27 }

connectionEthDataDestinationTna OBJECT-TYPE
    SYNTAX      IpAddress
    MAX-ACCESS  read-only
    STATUS      current
    DESCRIPTION
        "Destination Transport Network Assigned Name" 
    ::=  { connectionEthDataEntry 28 }

connectionEthDataTunnelNumberExtension OBJECT-TYPE
    SYNTAX      Unsigned32
    MAX-ACCESS  read-only
    STATUS      current
    DESCRIPTION
        "Tunnel Number Extension. (internal: serviceID.extTunnelID)" 
    ::=  { connectionEthDataEntry 29 }

connectionEthDataTunnelInstance OBJECT-TYPE
    SYNTAX      Unsigned32
    MAX-ACCESS  read-only
    STATUS      current
    DESCRIPTION
        "Tunnel Instance also called Service Instance ID. This changes every time there is Make-Before-Break operation. (internal: serviceInstID.octpID)" 
    ::=  { connectionEthDataEntry 30 }

connectionEthDataConnectionNo OBJECT-TYPE
    SYNTAX      Unsigned32
    MAX-ACCESS  read-only
    STATUS      current
    DESCRIPTION
        "Connection Number also called Connection ID. This changes every time there is Make-Before-Break operation. Working and protection connection numbers are different. (internal: lsptID.octpID)" 
    ::=  { connectionEthDataEntry 31 }

connectionEthDataFromAidString OBJECT-TYPE
    SYNTAX      SnmpAdminString
    MAX-ACCESS  read-only
    STATUS      current
    DESCRIPTION   ""
    ::=  { connectionEthDataEntry 32 }

connectionEthDataToAidString OBJECT-TYPE
    SYNTAX      SnmpAdminString
    MAX-ACCESS  read-only
    STATUS      current
    DESCRIPTION   ""
    ::=  { connectionEthDataEntry 33 }

pathEthDataTable OBJECT-TYPE
    SYNTAX      SEQUENCE OF PathEthDataEntry
    MAX-ACCESS  not-accessible
    STATUS      current
    DESCRIPTION   ""
    ::=  { controlPlaneConfigAndStatus 38 }

pathEthDataEntry OBJECT-TYPE
    SYNTAX      PathEthDataEntry
    MAX-ACCESS  not-accessible
    STATUS      current
    DESCRIPTION   ""
    INDEX       {
                  controlPlaneEthEntityIndex
                }
    ::=  { pathEthDataTable 1 }

PathEthDataEntry ::=  SEQUENCE
  { pathEthDataPathId SnmpAdminString,
    pathEthDataPathType FspR7CpPathType,
    pathEthDataConnectionTunnelAid EntityIndex,
    pathEthDataRole FspR7CpRole }

pathEthDataPathId OBJECT-TYPE
    SYNTAX      SnmpAdminString
    MAX-ACCESS  read-only
    STATUS      current
    DESCRIPTION   ""
    ::=  { pathEthDataEntry 1 }

pathEthDataPathType OBJECT-TYPE
    SYNTAX      FspR7CpPathType
    MAX-ACCESS  read-only
    STATUS      current
    DESCRIPTION   ""
    ::=  { pathEthDataEntry 2 }

pathEthDataConnectionTunnelAid OBJECT-TYPE
    SYNTAX      EntityIndex
    MAX-ACCESS  read-only
    STATUS      current
    DESCRIPTION   ""
    ::=  { pathEthDataEntry 3 }

pathEthDataRole OBJECT-TYPE
    SYNTAX      FspR7CpRole
    MAX-ACCESS  read-only
    STATUS      current
    DESCRIPTION   ""
    ::=  { pathEthDataEntry 4 }

pathElementEthDataTable OBJECT-TYPE
    SYNTAX      SEQUENCE OF PathElementEthDataEntry
    MAX-ACCESS  not-accessible
    STATUS      current
    DESCRIPTION   ""
    ::=  { controlPlaneConfigAndStatus 39 }

pathElementEthDataEntry OBJECT-TYPE
    SYNTAX      PathElementEthDataEntry
    MAX-ACCESS  not-accessible
    STATUS      current
    DESCRIPTION   ""
    INDEX       {
                  controlPlaneEthEntityIndex
                }
    ::=  { pathElementEthDataTable 1 }

PathElementEthDataEntry ::=  SEQUENCE
  { pathElementEthDataPathId SnmpAdminString,
    pathElementEthDataSequenceNumber Unsigned32,
    pathElementEthDataPathType FspR7CpPathType,
    pathElementEthDataTrafficEngineeringType FspR7CpTEType,
    pathElementEthDataLifIp IpAddress,
    pathElementEthDataNodeIp IpAddress,
    pathElementEthDataNodeIpMonitor IpAddress,
    pathElementEthDataTid SnmpAdminString,
    pathElementEthDataTidMonitor SnmpAdminString,
    pathElementEthDataLogicalInterfaceId Unsigned32,
    pathElementEthDataTie FspR7CpTie,
    pathElementEthDataUpstreamSvid Unsigned32,
    pathElementEthDataDownstreamSvid Unsigned32 }

pathElementEthDataPathId OBJECT-TYPE
    SYNTAX      SnmpAdminString
    MAX-ACCESS  read-only
    STATUS      current
    DESCRIPTION   ""
    ::=  { pathElementEthDataEntry 1 }

pathElementEthDataSequenceNumber OBJECT-TYPE
    SYNTAX      Unsigned32
    MAX-ACCESS  read-only
    STATUS      current
    DESCRIPTION   ""
    ::=  { pathElementEthDataEntry 2 }

pathElementEthDataPathType OBJECT-TYPE
    SYNTAX      FspR7CpPathType
    MAX-ACCESS  read-only
    STATUS      current
    DESCRIPTION   ""
    ::=  { pathElementEthDataEntry 3 }

pathElementEthDataTrafficEngineeringType OBJECT-TYPE
    SYNTAX      FspR7CpTEType
    MAX-ACCESS  read-only
    STATUS      current
    DESCRIPTION   ""
    ::=  { pathElementEthDataEntry 4 }

pathElementEthDataLifIp OBJECT-TYPE
    SYNTAX      IpAddress
    MAX-ACCESS  read-only
    STATUS      current
    DESCRIPTION   ""
    ::=  { pathElementEthDataEntry 5 }

pathElementEthDataNodeIp OBJECT-TYPE
    SYNTAX      IpAddress
    MAX-ACCESS  read-only
    STATUS      current
    DESCRIPTION   ""
    ::=  { pathElementEthDataEntry 6 }

pathElementEthDataNodeIpMonitor OBJECT-TYPE
    SYNTAX      IpAddress
    MAX-ACCESS  read-only
    STATUS      current
    DESCRIPTION   ""
    ::=  { pathElementEthDataEntry 7 }

pathElementEthDataTid OBJECT-TYPE
    SYNTAX      SnmpAdminString
    MAX-ACCESS  read-only
    STATUS      current
    DESCRIPTION   ""
    ::=  { pathElementEthDataEntry 8 }

pathElementEthDataTidMonitor OBJECT-TYPE
    SYNTAX      SnmpAdminString
    MAX-ACCESS  read-only
    STATUS      current
    DESCRIPTION   ""
    ::=  { pathElementEthDataEntry 9 }

pathElementEthDataLogicalInterfaceId OBJECT-TYPE
    SYNTAX      Unsigned32
    MAX-ACCESS  read-only
    STATUS      current
    DESCRIPTION   ""
    ::=  { pathElementEthDataEntry 10 }

pathElementEthDataTie OBJECT-TYPE
    SYNTAX      FspR7CpTie
    MAX-ACCESS  read-only
    STATUS      current
    DESCRIPTION   ""
    ::=  { pathElementEthDataEntry 11 }

pathElementEthDataUpstreamSvid OBJECT-TYPE
    SYNTAX      Unsigned32
    MAX-ACCESS  read-only
    STATUS      current
    DESCRIPTION   ""
    ::=  { pathElementEthDataEntry 12 }

pathElementEthDataDownstreamSvid OBJECT-TYPE
    SYNTAX      Unsigned32
    MAX-ACCESS  read-only
    STATUS      current
    DESCRIPTION   ""
    ::=  { pathElementEthDataEntry 13 }

inventoryCpEthDownDataTable OBJECT-TYPE
    SYNTAX      SEQUENCE OF InventoryCpEthDownDataEntry
    MAX-ACCESS  not-accessible
    STATUS      current
    DESCRIPTION   "Does not show flow entities as facilities on connection.
         inventoryCpEthDownFlowDataTable is a extension of the table. It contains only
         flow entities as a facility on connectioncon"
    ::=  { controlPlaneConfigAndStatus 40 }

inventoryCpEthDownDataEntry OBJECT-TYPE
    SYNTAX      InventoryCpEthDownDataEntry
    MAX-ACCESS  not-accessible
    STATUS      current
    DESCRIPTION   ""
    INDEX       {
                  controlPlaneEthEntityIndex,
                  inventoryCpEthDownDataNumber
                }
    ::=  { inventoryCpEthDownDataTable 1 }

InventoryCpEthDownDataEntry ::=  SEQUENCE
  { inventoryCpEthDownDataNumber EntityIndex,
    inventoryCpEthDownDataResources EntityIndex,
    inventoryCpEthDownDataFacilities EntityIndex }

inventoryCpEthDownDataNumber OBJECT-TYPE
    SYNTAX      EntityIndex
    MAX-ACCESS  not-accessible
    STATUS      current
    DESCRIPTION   ""
    ::=  { inventoryCpEthDownDataEntry 1 }

inventoryCpEthDownDataResources OBJECT-TYPE
    SYNTAX      EntityIndex
    MAX-ACCESS  read-only
    STATUS      current
    DESCRIPTION   ""
    ::=  { inventoryCpEthDownDataEntry 2 }

inventoryCpEthDownDataFacilities OBJECT-TYPE
    SYNTAX      EntityIndex
    MAX-ACCESS  read-only
    STATUS      current
    DESCRIPTION   ""
    ::=  { inventoryCpEthDownDataEntry 3 }

inventoryCpEthUpDataTable OBJECT-TYPE
    SYNTAX      SEQUENCE OF InventoryCpEthUpDataEntry
    MAX-ACCESS  not-accessible
    STATUS      current
    DESCRIPTION   "Does not show flow entities as facilities on connection.
         inventoryCpEthDownFlowUpTable is a extension of the table. It contains only
         flow entities as a facility on connectioncon"
    ::=  { controlPlaneConfigAndStatus 41 }

inventoryCpEthUpDataEntry OBJECT-TYPE
    SYNTAX      InventoryCpEthUpDataEntry
    MAX-ACCESS  not-accessible
    STATUS      current
    DESCRIPTION   ""
    INDEX       {
                  controlPlaneEthEntityIndex,
                  inventoryCpEthUpDataNumber
                }
    ::=  { inventoryCpEthUpDataTable 1 }

InventoryCpEthUpDataEntry ::=  SEQUENCE
  { inventoryCpEthUpDataNumber EntityIndex,
    inventoryCpEthUpDataResources EntityIndex,
    inventoryCpEthUpDataFacilities EntityIndex }

inventoryCpEthUpDataNumber OBJECT-TYPE
    SYNTAX      EntityIndex
    MAX-ACCESS  not-accessible
    STATUS      current
    DESCRIPTION   ""
    ::=  { inventoryCpEthUpDataEntry 1 }

inventoryCpEthUpDataResources OBJECT-TYPE
    SYNTAX      EntityIndex
    MAX-ACCESS  read-only
    STATUS      current
    DESCRIPTION   ""
    ::=  { inventoryCpEthUpDataEntry 2 }

inventoryCpEthUpDataFacilities OBJECT-TYPE
    SYNTAX      EntityIndex
    MAX-ACCESS  read-only
    STATUS      current
    DESCRIPTION   ""
    ::=  { inventoryCpEthUpDataEntry 3 }

inventoryCpEthCrsDownDataTable OBJECT-TYPE
    SYNTAX      SEQUENCE OF InventoryCpEthCrsDownDataEntry
    MAX-ACCESS  not-accessible
    STATUS      current
    DESCRIPTION   "Contains cross entries for connection eth."
    ::=  { controlPlaneConfigAndStatus 42 }

inventoryCpEthCrsDownDataEntry OBJECT-TYPE
    SYNTAX      InventoryCpEthCrsDownDataEntry
    MAX-ACCESS  not-accessible
    STATUS      current
    DESCRIPTION   ""
    INDEX       {
                  controlPlaneEthEntityIndex,
                  inventoryCpEthCrsDownDataNumber,
                  inventoryCpEthCrsDownDataIndexEthFrom,
                  inventoryCpEthCrsDownDataIndexFlowFrom,
                  inventoryCpEthCrsDownDataIndexEthTo
                }
    ::=  { inventoryCpEthCrsDownDataTable 1 }

InventoryCpEthCrsDownDataEntry ::=  SEQUENCE
  { inventoryCpEthCrsDownDataNumber EntityIndex,
    inventoryCpEthCrsDownDataIndexEthFrom EntityIndex,
    inventoryCpEthCrsDownDataIndexFlowFrom EntityIndex,
    inventoryCpEthCrsDownDataIndexEthTo EntityIndex,
    inventoryCpEthCrsDownDataAids EntityIndex,
    inventoryCpEthCrsDownDataAidsString SnmpAdminString }

inventoryCpEthCrsDownDataNumber OBJECT-TYPE
    SYNTAX      EntityIndex
    MAX-ACCESS  not-accessible
    STATUS      current
    DESCRIPTION   ""
    ::=  { inventoryCpEthCrsDownDataEntry 1 }

inventoryCpEthCrsDownDataIndexEthFrom OBJECT-TYPE
    SYNTAX      EntityIndex
    MAX-ACCESS  accessible-for-notify
    STATUS      current
    DESCRIPTION   "First index of a flow entity referencing to eth entity (parent)."
    ::=  { inventoryCpEthCrsDownDataEntry 2 }

inventoryCpEthCrsDownDataIndexFlowFrom OBJECT-TYPE
    SYNTAX      EntityIndex
    MAX-ACCESS  accessible-for-notify
    STATUS      current
    DESCRIPTION   "Second index of a flow entity referencing to svid value."
    ::=  { inventoryCpEthCrsDownDataEntry 3 }

inventoryCpEthCrsDownDataIndexEthTo OBJECT-TYPE
    SYNTAX      EntityIndex
    MAX-ACCESS  accessible-for-notify
    STATUS      current
    DESCRIPTION   "First index of a flow entity referencing to eth entity (parent)."
    ::=  { inventoryCpEthCrsDownDataEntry 4 }

inventoryCpEthCrsDownDataAids OBJECT-TYPE
    SYNTAX      EntityIndex
    MAX-ACCESS  read-only
    STATUS      current
    DESCRIPTION   ""
    ::=  { inventoryCpEthCrsDownDataEntry 5 }

inventoryCpEthCrsDownDataAidsString OBJECT-TYPE
    SYNTAX      SnmpAdminString
    MAX-ACCESS  read-only
    STATUS      current
    DESCRIPTION   ""
    ::=  { inventoryCpEthCrsDownDataEntry 6 }

inventoryCpEthCrsUpDataTable OBJECT-TYPE
    SYNTAX      SEQUENCE OF InventoryCpEthCrsUpDataEntry
    MAX-ACCESS  not-accessible
    STATUS      current
    DESCRIPTION   "Contains cross entries for connection eth"
    ::=  { controlPlaneConfigAndStatus 43 }

inventoryCpEthCrsUpDataEntry OBJECT-TYPE
    SYNTAX      InventoryCpEthCrsUpDataEntry
    MAX-ACCESS  not-accessible
    STATUS      current
    DESCRIPTION   ""
    INDEX       {
                  controlPlaneEthEntityIndex,
                  inventoryCpEthCrsUpDataNumber,
                  inventoryCpEthCrsDownDataIndexEthFrom,
                  inventoryCpEthCrsDownDataIndexFlowFrom,
                  inventoryCpEthCrsDownDataIndexEthTo
                }
    ::=  { inventoryCpEthCrsUpDataTable 1 }

InventoryCpEthCrsUpDataEntry ::=  SEQUENCE
  { inventoryCpEthCrsUpDataNumber EntityIndex,
    inventoryCpEthCrsUpDataAids EntityIndex,
    inventoryCpEthCrsUpDataAidsString SnmpAdminString }

inventoryCpEthCrsUpDataNumber OBJECT-TYPE
    SYNTAX      EntityIndex
    MAX-ACCESS  not-accessible
    STATUS      current
    DESCRIPTION   ""
    ::=  { inventoryCpEthCrsUpDataEntry 1 }

inventoryCpEthCrsUpDataAids OBJECT-TYPE
    SYNTAX      EntityIndex
    MAX-ACCESS  read-only
    STATUS      current
    DESCRIPTION   ""
    ::=  { inventoryCpEthCrsUpDataEntry 2 }

inventoryCpEthCrsUpDataAidsString OBJECT-TYPE
    SYNTAX      SnmpAdminString
    MAX-ACCESS  read-only
    STATUS      current
    DESCRIPTION   ""
    ::=  { inventoryCpEthCrsUpDataEntry 3 }

teUnnumLinkEthDataTable OBJECT-TYPE
    SYNTAX      SEQUENCE OF TeUnnumLinkEthDataEntry
    MAX-ACCESS  not-accessible
    STATUS      current
    DESCRIPTION   ""
    ::=  { controlPlaneConfigAndStatus 44 }

teUnnumLinkEthDataEntry OBJECT-TYPE
    SYNTAX      TeUnnumLinkEthDataEntry
    MAX-ACCESS  not-accessible
    STATUS      current
    DESCRIPTION   ""
    INDEX       {
                  teRouterDataIp,
                  teUnnumLinkEthDataNumber
                }
    ::=  { teUnnumLinkEthDataTable 1 }

TeUnnumLinkEthDataEntry ::=  SEQUENCE
  { teUnnumLinkEthDataNumber Unsigned32,
    teUnnumLinkEthDataNodeIp IpAddress,
    teUnnumLinkEthDataNodeTid SnmpAdminString,
    teUnnumLinkEthDataTeLinkId Unsigned32,
    teUnnumLinkEthDataPhysicalLink Unsigned32,
    teUnnumLinkEthDataSynchronization FspR7YesNo,
    teUnnumLinkEthDataDiscarded FspR7YesNo,
    teUnnumLinkEthDataFendNodeIp IpAddress,
    teUnnumLinkEthDataFendTeLinkId Unsigned32,
    teUnnumLinkEthDataInfo SnmpAdminString }

teUnnumLinkEthDataNumber OBJECT-TYPE
    SYNTAX      Unsigned32
    MAX-ACCESS  not-accessible
    STATUS      current
    DESCRIPTION   ""
    ::=  { teUnnumLinkEthDataEntry 1 }

teUnnumLinkEthDataNodeIp OBJECT-TYPE
    SYNTAX      IpAddress
    MAX-ACCESS  read-only
    STATUS      current
    DESCRIPTION   ""
    ::=  { teUnnumLinkEthDataEntry 2 }

teUnnumLinkEthDataNodeTid OBJECT-TYPE
    SYNTAX      SnmpAdminString
    MAX-ACCESS  read-only
    STATUS      current
    DESCRIPTION   ""
    ::=  { teUnnumLinkEthDataEntry 3 }

teUnnumLinkEthDataTeLinkId OBJECT-TYPE
    SYNTAX      Unsigned32
    MAX-ACCESS  read-only
    STATUS      current
    DESCRIPTION   ""
    ::=  { teUnnumLinkEthDataEntry 4 }

teUnnumLinkEthDataPhysicalLink OBJECT-TYPE
    SYNTAX      Unsigned32
    MAX-ACCESS  read-only
    STATUS      current
    DESCRIPTION   ""
    ::=  { teUnnumLinkEthDataEntry 5 }

teUnnumLinkEthDataSynchronization OBJECT-TYPE
    SYNTAX      FspR7YesNo
    MAX-ACCESS  read-only
    STATUS      current
    DESCRIPTION   ""
    ::=  { teUnnumLinkEthDataEntry 6 }

teUnnumLinkEthDataDiscarded OBJECT-TYPE
    SYNTAX      FspR7YesNo
    MAX-ACCESS  read-only
    STATUS      current
    DESCRIPTION   ""
    ::=  { teUnnumLinkEthDataEntry 7 }

teUnnumLinkEthDataFendNodeIp OBJECT-TYPE
    SYNTAX      IpAddress
    MAX-ACCESS  read-only
    STATUS      current
    DESCRIPTION   ""
    ::=  { teUnnumLinkEthDataEntry 8 }

teUnnumLinkEthDataFendTeLinkId OBJECT-TYPE
    SYNTAX      Unsigned32
    MAX-ACCESS  read-only
    STATUS      current
    DESCRIPTION   ""
    ::=  { teUnnumLinkEthDataEntry 9 }

teUnnumLinkEthDataInfo OBJECT-TYPE
    SYNTAX      SnmpAdminString
    MAX-ACCESS  read-only
    STATUS      current
    DESCRIPTION   ""
    ::=  { teUnnumLinkEthDataEntry 10 }

teNumLinkEthDataTable OBJECT-TYPE
    SYNTAX      SEQUENCE OF TeNumLinkEthDataEntry
    MAX-ACCESS  not-accessible
    STATUS      current
    DESCRIPTION   ""
    ::=  { controlPlaneConfigAndStatus 45 }

teNumLinkEthDataEntry OBJECT-TYPE
    SYNTAX      TeNumLinkEthDataEntry
    MAX-ACCESS  not-accessible
    STATUS      current
    DESCRIPTION   ""
    INDEX       {
                  teRouterDataIp
                }
    ::=  { teNumLinkEthDataTable 1 }

TeNumLinkEthDataEntry ::=  SEQUENCE
  { teNumLinkEthDataNodeIp IpAddress,
    teNumLinkEthDataNodeTid SnmpAdminString,
    teNumLinkEthDataTeLinkIp IpAddress,
    teNumLinkEthDataPhysicalLink Unsigned32,
    teNumLinkEthDataSynchronization FspR7YesNo,
    teNumLinkEthDataDiscarded FspR7YesNo,
    teNumLinkEthDataFendNodeIp IpAddress,
    teNumLinkEthDataFendTeLinkIp IpAddress,
    teNumLinkEthDataInfo SnmpAdminString }

teNumLinkEthDataNodeIp OBJECT-TYPE
    SYNTAX      IpAddress
    MAX-ACCESS  read-only
    STATUS      current
    DESCRIPTION   ""
    ::=  { teNumLinkEthDataEntry 1 }

teNumLinkEthDataNodeTid OBJECT-TYPE
    SYNTAX      SnmpAdminString
    MAX-ACCESS  read-only
    STATUS      current
    DESCRIPTION   ""
    ::=  { teNumLinkEthDataEntry 2 }

teNumLinkEthDataTeLinkIp OBJECT-TYPE
    SYNTAX      IpAddress
    MAX-ACCESS  read-only
    STATUS      current
    DESCRIPTION   ""
    ::=  { teNumLinkEthDataEntry 3 }

teNumLinkEthDataPhysicalLink OBJECT-TYPE
    SYNTAX      Unsigned32
    MAX-ACCESS  read-only
    STATUS      current
    DESCRIPTION   ""
    ::=  { teNumLinkEthDataEntry 4 }

teNumLinkEthDataSynchronization OBJECT-TYPE
    SYNTAX      FspR7YesNo
    MAX-ACCESS  read-only
    STATUS      current
    DESCRIPTION   ""
    ::=  { teNumLinkEthDataEntry 5 }

teNumLinkEthDataDiscarded OBJECT-TYPE
    SYNTAX      FspR7YesNo
    MAX-ACCESS  read-only
    STATUS      current
    DESCRIPTION   ""
    ::=  { teNumLinkEthDataEntry 6 }

teNumLinkEthDataFendNodeIp OBJECT-TYPE
    SYNTAX      IpAddress
    MAX-ACCESS  read-only
    STATUS      current
    DESCRIPTION   ""
    ::=  { teNumLinkEthDataEntry 7 }

teNumLinkEthDataFendTeLinkIp OBJECT-TYPE
    SYNTAX      IpAddress
    MAX-ACCESS  read-only
    STATUS      current
    DESCRIPTION   ""
    ::=  { teNumLinkEthDataEntry 8 }

teNumLinkEthDataInfo OBJECT-TYPE
    SYNTAX      SnmpAdminString
    MAX-ACCESS  read-only
    STATUS      current
    DESCRIPTION   ""
    ::=  { teNumLinkEthDataEntry 9 }

remoteAlarmCpDataTable OBJECT-TYPE
    SYNTAX      SEQUENCE OF RemoteAlarmCpDataEntry
    MAX-ACCESS  not-accessible
    STATUS      current
    DESCRIPTION   ""
    ::=  { controlPlaneConfigAndStatus 46 }

remoteAlarmCpDataEntry OBJECT-TYPE
    SYNTAX      RemoteAlarmCpDataEntry
    MAX-ACCESS  not-accessible
    STATUS      current
    DESCRIPTION   ""
    INDEX       {
                  controlPlaneWdmEntityIndex,
                  controlPlaneWdmEntityIndex
                }
    ::=  { remoteAlarmCpDataTable 1 }

RemoteAlarmCpDataEntry ::=  SEQUENCE
  { remoteAlarmCpDataNumber EntityIndex,
    remoteAlarmCpDataNodeTid SnmpAdminString,
    remoteAlarmCpDataNodeIp IpAddress,
    remoteAlarmCpDataSource EntityIndex,
    remoteAlarmCpDataType FspR7RemoteAlarmType,
    remoteAlarmCpDataDate FspR7Date,
    remoteAlarmCpDataTime FspR7Time,
    remoteAlarmCpDataPath FspR7RemoteAlarmPath,
    remoteAlarmCpDataSourceString SnmpAdminString }

remoteAlarmCpDataNumber OBJECT-TYPE
    SYNTAX      EntityIndex
    MAX-ACCESS  not-accessible
    STATUS      current
    DESCRIPTION   ""
    ::=  { remoteAlarmCpDataEntry 1 }

remoteAlarmCpDataNodeTid OBJECT-TYPE
    SYNTAX      SnmpAdminString
    MAX-ACCESS  read-only
    STATUS      current
    DESCRIPTION   ""
    ::=  { remoteAlarmCpDataEntry 2 }

remoteAlarmCpDataNodeIp OBJECT-TYPE
    SYNTAX      IpAddress
    MAX-ACCESS  read-only
    STATUS      current
    DESCRIPTION   ""
    ::=  { remoteAlarmCpDataEntry 3 }

remoteAlarmCpDataSource OBJECT-TYPE
    SYNTAX      EntityIndex
    MAX-ACCESS  read-only
    STATUS      current
    DESCRIPTION   ""
    ::=  { remoteAlarmCpDataEntry 4 }

remoteAlarmCpDataType OBJECT-TYPE
    SYNTAX      FspR7RemoteAlarmType
    MAX-ACCESS  read-only
    STATUS      current
    DESCRIPTION   ""
    ::=  { remoteAlarmCpDataEntry 5 }

remoteAlarmCpDataDate OBJECT-TYPE
    SYNTAX      FspR7Date
    MAX-ACCESS  read-only
    STATUS      current
    DESCRIPTION   ""
    ::=  { remoteAlarmCpDataEntry 6 }

remoteAlarmCpDataTime OBJECT-TYPE
    SYNTAX      FspR7Time
    MAX-ACCESS  read-only
    STATUS      current
    DESCRIPTION   ""
    ::=  { remoteAlarmCpDataEntry 7 }

remoteAlarmCpDataPath OBJECT-TYPE
    SYNTAX      FspR7RemoteAlarmPath
    MAX-ACCESS  read-only
    STATUS      current
    DESCRIPTION   ""
    ::=  { remoteAlarmCpDataEntry 8 }

remoteAlarmCpDataSourceString OBJECT-TYPE
    SYNTAX      SnmpAdminString
    MAX-ACCESS  read-only
    STATUS      current
    DESCRIPTION   ""
    ::=  { remoteAlarmCpDataEntry 9 }

inventoryCpEthDownFlowDataTable OBJECT-TYPE
    SYNTAX      SEQUENCE OF InventoryCpEthDownFlowDataEntry
    MAX-ACCESS  not-accessible
    STATUS      current
    DESCRIPTION   "Contains only flow entities as a facility on connection."
    ::=  { controlPlaneConfigAndStatus 47 }

inventoryCpEthDownFlowDataEntry OBJECT-TYPE
    SYNTAX      InventoryCpEthDownFlowDataEntry
    MAX-ACCESS  not-accessible
    STATUS      current
    DESCRIPTION   ""
    INDEX       {
                  controlPlaneEthEntityIndex,
                  inventoryCpEthDownDataNumber,
                  inventoryCpEthDownFlowDataIndexEth
                }
    ::=  { inventoryCpEthDownFlowDataTable 1 }

InventoryCpEthDownFlowDataEntry ::=  SEQUENCE
  { inventoryCpEthDownFlowDataIndexEth EntityIndex,
    inventoryCpEthDownFlowDataFacilities EntityIndex,
    inventoryCpEthDownFlowDataFacilitiesString SnmpAdminString }

inventoryCpEthDownFlowDataIndexEth OBJECT-TYPE
    SYNTAX      EntityIndex
    MAX-ACCESS  accessible-for-notify
    STATUS      current
    DESCRIPTION   "First index of a flow entity referencing to eth entity (parent)."
    ::=  { inventoryCpEthDownFlowDataEntry 1 }

inventoryCpEthDownFlowDataFacilities OBJECT-TYPE
    SYNTAX      EntityIndex
    MAX-ACCESS  read-only
    STATUS      current
    DESCRIPTION   ""
    ::=  { inventoryCpEthDownFlowDataEntry 2 }

inventoryCpEthDownFlowDataFacilitiesString OBJECT-TYPE
    SYNTAX      SnmpAdminString
    MAX-ACCESS  read-only
    STATUS      current
    DESCRIPTION   ""
    ::=  { inventoryCpEthDownFlowDataEntry 3 }

inventoryCpEthUpFlowDataTable OBJECT-TYPE
    SYNTAX      SEQUENCE OF InventoryCpEthUpFlowDataEntry
    MAX-ACCESS  not-accessible
    STATUS      current
    DESCRIPTION   "Contains only flow entities as a facility on connection."
    ::=  { controlPlaneConfigAndStatus 48 }

inventoryCpEthUpFlowDataEntry OBJECT-TYPE
    SYNTAX      InventoryCpEthUpFlowDataEntry
    MAX-ACCESS  not-accessible
    STATUS      current
    DESCRIPTION   ""
    INDEX       {
                  controlPlaneEthEntityIndex,
                  inventoryCpEthUpDataNumber,
                  inventoryCpEthUpFlowDataIndexEth
                }
    ::=  { inventoryCpEthUpFlowDataTable 1 }

InventoryCpEthUpFlowDataEntry ::=  SEQUENCE
  { inventoryCpEthUpFlowDataIndexEth EntityIndex,
    inventoryCpEthUpFlowDataFacilities EntityIndex,
    inventoryCpEthUpFlowDataFacilitiesString SnmpAdminString }

inventoryCpEthUpFlowDataIndexEth OBJECT-TYPE
    SYNTAX      EntityIndex
    MAX-ACCESS  accessible-for-notify
    STATUS      current
    DESCRIPTION   "First index of a flow entity referencing to eth entity (parent)."
    ::=  { inventoryCpEthUpFlowDataEntry 1 }

inventoryCpEthUpFlowDataFacilities OBJECT-TYPE
    SYNTAX      EntityIndex
    MAX-ACCESS  read-only
    STATUS      current
    DESCRIPTION   ""
    ::=  { inventoryCpEthUpFlowDataEntry 2 }

inventoryCpEthUpFlowDataFacilitiesString OBJECT-TYPE
    SYNTAX      SnmpAdminString
    MAX-ACCESS  read-only
    STATUS      current
    DESCRIPTION   ""
    ::=  { inventoryCpEthUpFlowDataEntry 3 }

portBindingDataTable OBJECT-TYPE
    SYNTAX      SEQUENCE OF PortBindingDataEntry
    MAX-ACCESS  not-accessible
    STATUS      current
    DESCRIPTION   ""
    ::=  { controlPlaneConfigAndStatus 51 }

portBindingDataEntry OBJECT-TYPE
    SYNTAX      PortBindingDataEntry
    MAX-ACCESS  not-accessible
    STATUS      current
    DESCRIPTION   ""
    INDEX       {
                  entityIndex
                }
    ::=  { portBindingDataTable 1 }

PortBindingDataEntry ::=  SEQUENCE
  { portBindingDataLogicalIfAid EntityIndex,
    portBindingDataLocalPort EntityIndex,
    portBindingDataLocalTna IpAddress,
    portBindingDataRemotePort Unsigned32,
    portBindingDataRemoteTna IpAddress,
    portBindingDataRemoteTnaMask IpAddress,
    portBindingDataRemoteNodeIp IpAddress,
    portBindingDataRemoteScn IpAddress,
    portBindingDataRemoteScPc IpAddress,
    portBindingDataLayer FspR7PacketsLayer,
    portBindingDataLocalPortString SnmpAdminString }

portBindingDataLogicalIfAid OBJECT-TYPE
    SYNTAX      EntityIndex
    MAX-ACCESS  read-only
    STATUS      current
    DESCRIPTION
        "Logical Interface AID" 
    ::=  { portBindingDataEntry 1 }

portBindingDataLocalPort OBJECT-TYPE
    SYNTAX      EntityIndex
    MAX-ACCESS  read-only
    STATUS      current
    DESCRIPTION
        "Port Binding Local Port AID (OIF Signaling Interface)" 
    ::=  { portBindingDataEntry 2 }

portBindingDataLocalTna OBJECT-TYPE
    SYNTAX      IpAddress
    MAX-ACCESS  read-only
    STATUS      current
    DESCRIPTION
        "Port Binding Local Transport Network Assigned Name (OIF Signaling Interface)" 
    ::=  { portBindingDataEntry 3 }

portBindingDataRemotePort OBJECT-TYPE
    SYNTAX      Unsigned32
    MAX-ACCESS  read-only
    STATUS      current
    DESCRIPTION
        "Port Binding Remote Port Identifier (OIF Signaling Interface)" 
    ::=  { portBindingDataEntry 4 }

portBindingDataRemoteTna OBJECT-TYPE
    SYNTAX      IpAddress
    MAX-ACCESS  read-only
    STATUS      current
    DESCRIPTION
        "Port Binding Remote Transport Network Assigned Name (OIF Signaling Interface)" 
    ::=  { portBindingDataEntry 5 }

portBindingDataRemoteTnaMask OBJECT-TYPE
    SYNTAX      IpAddress
    MAX-ACCESS  read-only
    STATUS      current
    DESCRIPTION
        "Port Binding Remote Transport Network Assigned Name Mask (OIF Signaling Interface)" 
    ::=  { portBindingDataEntry 6 }

portBindingDataRemoteNodeIp OBJECT-TYPE
    SYNTAX      IpAddress
    MAX-ACCESS  read-only
    STATUS      current
    DESCRIPTION
        "Port Binding Remote Node IP (OIF Signaling Interface)" 
    ::=  { portBindingDataEntry 7 }

portBindingDataRemoteScn OBJECT-TYPE
    SYNTAX      IpAddress
    MAX-ACCESS  read-only
    STATUS      current
    DESCRIPTION
        "Port Binding Remote Signaling Connection Network Address (OIF Signaling Interface)" 
    ::=  { portBindingDataEntry 8 }

portBindingDataRemoteScPc OBJECT-TYPE
    SYNTAX      IpAddress
    MAX-ACCESS  read-only
    STATUS      current
    DESCRIPTION
        "Port Binding Remote Signaling Controller Protocol Controller Identifier (OIF Signaling Interface)" 
    ::=  { portBindingDataEntry 9 }

portBindingDataLayer OBJECT-TYPE
    SYNTAX      FspR7PacketsLayer
    MAX-ACCESS  read-only
    STATUS      current
    DESCRIPTION
        "Notional Layer of Advertisement on Packets on the LIF" 
    ::=  { portBindingDataEntry 10 }

portBindingDataLocalPortString OBJECT-TYPE
    SYNTAX      SnmpAdminString
    MAX-ACCESS  read-only
    STATUS      current
    DESCRIPTION
        "Port Binding Local Port AID (OIF Signaling Interface)" 
    ::=  { portBindingDataEntry 11 }

portBindingLifAidTable OBJECT-TYPE
    SYNTAX      SEQUENCE OF PortBindingLifAidEntry
    MAX-ACCESS  not-accessible
    STATUS      current
    DESCRIPTION   ""
    ::=  { controlPlaneConfigAndStatus 52 }

portBindingLifAidEntry OBJECT-TYPE
    SYNTAX      PortBindingLifAidEntry
    MAX-ACCESS  not-accessible
    STATUS      current
    DESCRIPTION   ""
    INDEX       {
                  controlPlaneWdmEntityIndex,
                  portBindingLifAidIndex
                }
    ::=  { portBindingLifAidTable 1 }

PortBindingLifAidEntry ::=  SEQUENCE
  { portBindingLifAidIndex EntityIndex,
    portBindingLifAidValue Integer32 }

portBindingLifAidIndex OBJECT-TYPE
    SYNTAX      EntityIndex
    MAX-ACCESS  not-accessible
    STATUS      current
    DESCRIPTION
        "" 
    ::=  { portBindingLifAidEntry 1 }

portBindingLifAidValue OBJECT-TYPE
    SYNTAX      Integer32
    MAX-ACCESS  read-only
    STATUS      current
    DESCRIPTION
        "List of Port Bindings attached to LIF-CP" 
    ::=  { portBindingLifAidEntry 2 }

reservationCpDataTable OBJECT-TYPE
    SYNTAX      SEQUENCE OF ReservationCpDataEntry
    MAX-ACCESS  not-accessible
    STATUS      current
    DESCRIPTION   "This table contains all Reservation entities on each LIF-CP. First index represents the LIF-CP
         entity, the second represents the Reservation entity."
    ::=  { controlPlaneConfigAndStatus 53 }

reservationCpDataEntry OBJECT-TYPE
    SYNTAX      ReservationCpDataEntry
    MAX-ACCESS  not-accessible
    STATUS      current
    DESCRIPTION   ""
    INDEX       {
                  controlPlaneWdmEntityIndex,
                  controlPlaneWdmEntityIndex
                }
    ::=  { reservationCpDataTable 1 }

ReservationCpDataEntry ::=  SEQUENCE
  { reservationCpDataSeqNumber Unsigned32,
    reservationCpDataTunnelNo Unsigned32,
    reservationCpDataTunnelInstance Unsigned32,
    reservationCpDataIngressTid SnmpAdminString,
    reservationCpDataIngressNodeIp IpAddress,
    reservationCpDataChannelUp FspR7ChannelNumber,
    reservationCpDataChannelDown FspR7ChannelNumber }

reservationCpDataSeqNumber OBJECT-TYPE
    SYNTAX      Unsigned32
    MAX-ACCESS  read-only
    STATUS      current
    DESCRIPTION
        "Sequence number of an individual container within a Virtual Concatenated Group" 
    ::=  { reservationCpDataEntry 1 }

reservationCpDataTunnelNo OBJECT-TYPE
    SYNTAX      Unsigned32
    MAX-ACCESS  read-only
    STATUS      current
    DESCRIPTION
        "Tunnel Number also called Service ID. This never changes while the tunnel is in service. (internal: serviceID.tunnelID)" 
    ::=  { reservationCpDataEntry 2 }

reservationCpDataTunnelInstance OBJECT-TYPE
    SYNTAX      Unsigned32
    MAX-ACCESS  read-only
    STATUS      current
    DESCRIPTION
        "Tunnel Instance also called Service Instance ID. This changes every time there is Make-Before-Break operation. (internal: serviceInstID.octpID)" 
    ::=  { reservationCpDataEntry 3 }

reservationCpDataIngressTid OBJECT-TYPE
    SYNTAX      SnmpAdminString
    MAX-ACCESS  read-only
    STATUS      current
    DESCRIPTION
        "Ingress Target ID" 
    ::=  { reservationCpDataEntry 4 }

reservationCpDataIngressNodeIp OBJECT-TYPE
    SYNTAX      IpAddress
    MAX-ACCESS  read-only
    STATUS      current
    DESCRIPTION
        "Ingress Node IP" 
    ::=  { reservationCpDataEntry 5 }

reservationCpDataChannelUp OBJECT-TYPE
    SYNTAX      FspR7ChannelNumber
    MAX-ACCESS  read-only
    STATUS      current
    DESCRIPTION
        "Upstream Channel (RCV)" 
    ::=  { reservationCpDataEntry 6 }

reservationCpDataChannelDown OBJECT-TYPE
    SYNTAX      FspR7ChannelNumber
    MAX-ACCESS  read-only
    STATUS      current
    DESCRIPTION
        "Downstream Channel (TRMT)" 
    ::=  { reservationCpDataEntry 7 }

controlPlaneOtnConfigTable OBJECT-TYPE
    SYNTAX      SEQUENCE OF ControlPlaneOtnConfigEntry
    MAX-ACCESS  not-accessible
    STATUS      current
    DESCRIPTION   ""
    ::=  { controlPlaneConfigAndStatus 55 }

controlPlaneOtnConfigEntry OBJECT-TYPE
    SYNTAX      ControlPlaneOtnConfigEntry
    MAX-ACCESS  not-accessible
    STATUS      current
    DESCRIPTION   ""
    INDEX       {
                  controlPlaneOtnEntityIndex
                }
    ::=  { controlPlaneOtnConfigTable 1 }

ControlPlaneOtnConfigEntry ::=  SEQUENCE
  { controlPlaneOtnConfigCtmConfigFlag Unsigned32,
    controlPlaneOtnConfigCtmTraceDetail Unsigned32,
    controlPlaneOtnConfigCtmSetupTimeout Unsigned32,
    controlPlaneOtnConfigCtmShutdownTimeout Unsigned32,
    controlPlaneOtnConfigCtmRetryWait Unsigned32,
    controlPlaneOtnConfigCtmRetryWaitMultiplier Unsigned32,
    controlPlaneOtnConfigCtmMaximumRetryWait Unsigned32,
    controlPlaneOtnConfigCtmMaximumRetryNumber Unsigned32,
    controlPlaneOtnConfigRaConfigFlag Unsigned32,
    controlPlaneOtnConfigRaTraceDetail Unsigned32,
    controlPlaneOtnConfigRaAlarmActivationTime Unsigned32,
    controlPlaneOtnConfigCmConfigFlag Unsigned32,
    controlPlaneOtnConfigCmTraceDetail Unsigned32,
    controlPlaneOtnConfigCmAlarmActivationTime Unsigned32,
    controlPlaneOtnConfigCmFisFrsTimeout Unsigned32,
    controlPlaneOtnConfigCmCrankBackTimeout Unsigned32,
    controlPlaneOtnConfigCdbConfigFlag Unsigned32,
    controlPlaneOtnConfigCdbDetail Unsigned32,
    controlPlaneOtnConfigCdbMaxSize Unsigned32,
    controlPlaneOtnConfigRsvpConfigFlag Unsigned32,
    controlPlaneOtnConfigRsvpMaxExpRestartTime Counter64String,
    controlPlaneOtnConfigRsvpMaxExpRecoveryTime Unsigned32,
    controlPlaneOtnConfigTedbConfigFlag Unsigned32,
    controlPlaneOtnConfigTedbTraceDetail Unsigned32,
    controlPlaneOtnConfigTedbMaxSize Unsigned32,
    controlPlaneOtnConfigTedbRouterId IpAddress,
    controlPlaneOtnConfigTedbMinAdvertWait Unsigned32,
    controlPlaneOtnConfigNaasConfigFlag Unsigned32,
    controlPlaneOtnConfigNaasTraceDetail Unsigned32,
    controlPlaneOtnConfigNaasMaxSize Unsigned32,
    controlPlaneOtnConfigNaasAdvertWait Unsigned32,
    controlPlaneOtnConfigPcConfigFlag Unsigned32,
    controlPlaneOtnConfigPcTraceDetail Unsigned32,
    controlPlaneOtnConfigCdConfigFlag Unsigned32,
    controlPlaneOtnConfigCdTraceDetail Unsigned32,
    controlPlaneOtnConfigCdResyncTimeout Unsigned32,
    controlPlaneOtnConfigRmConfigFlag Unsigned32,
    controlPlaneOtnConfigRmTraceDetail Unsigned32,
    controlPlaneOtnConfigRmTraceTarget Unsigned32 }

controlPlaneOtnConfigCtmConfigFlag OBJECT-TYPE
    SYNTAX      Unsigned32
    MAX-ACCESS  read-write
    STATUS      current
    DESCRIPTION   "Label Switched Path Edge Component' Configuration Bitfield"
    ::=  { controlPlaneOtnConfigEntry 1 }

controlPlaneOtnConfigCtmTraceDetail OBJECT-TYPE
    SYNTAX      Unsigned32
    MAX-ACCESS  read-write
    STATUS      current
    DESCRIPTION   "Label Switched Path Edge Component' Trace Detail"
    ::=  { controlPlaneOtnConfigEntry 2 }

controlPlaneOtnConfigCtmSetupTimeout OBJECT-TYPE
    SYNTAX      Unsigned32 
    UNITS       "s"
    MAX-ACCESS  read-write
    STATUS      current
    DESCRIPTION   "Label Switched Path Edge Component' Set-Up Timeout"
    ::=  { controlPlaneOtnConfigEntry 3 }

controlPlaneOtnConfigCtmShutdownTimeout OBJECT-TYPE
    SYNTAX      Unsigned32 
    UNITS       "s"
    MAX-ACCESS  read-write
    STATUS      current
    DESCRIPTION   "Label Switched Path Edge Component' Shut-Down Timeout"
    ::=  { controlPlaneOtnConfigEntry 4 }

controlPlaneOtnConfigCtmRetryWait OBJECT-TYPE
    SYNTAX      Unsigned32 
    UNITS       "s"
    MAX-ACCESS  read-write
    STATUS      current
    DESCRIPTION   "Label Switched Path Edge Component' Initialization Retry Wait"
    ::=  { controlPlaneOtnConfigEntry 5 }

controlPlaneOtnConfigCtmRetryWaitMultiplier OBJECT-TYPE
    SYNTAX      Unsigned32
    MAX-ACCESS  read-write
    STATUS      current
    DESCRIPTION   "Label Switched Path Edge Component' Initialization Retry Wait Multiplier"
    ::=  { controlPlaneOtnConfigEntry 6 }

controlPlaneOtnConfigCtmMaximumRetryWait OBJECT-TYPE
    SYNTAX      Unsigned32 
    UNITS       "s"
    MAX-ACCESS  read-write
    STATUS      current
    DESCRIPTION   "Label Switched Path Edge Component' Initialization Maximum Retry Wait"
    ::=  { controlPlaneOtnConfigEntry 7 }

controlPlaneOtnConfigCtmMaximumRetryNumber OBJECT-TYPE
    SYNTAX      Unsigned32
    MAX-ACCESS  read-write
    STATUS      current
    DESCRIPTION   "Label Switched Path Edge Component' Initialization Maximum Retry Number"
    ::=  { controlPlaneOtnConfigEntry 8 }

controlPlaneOtnConfigRaConfigFlag OBJECT-TYPE
    SYNTAX      Unsigned32
    MAX-ACCESS  read-write
    STATUS      current
    DESCRIPTION   "Resource Allocator Configuration Bitfield"
    ::=  { controlPlaneOtnConfigEntry 9 }

controlPlaneOtnConfigRaTraceDetail OBJECT-TYPE
    SYNTAX      Unsigned32
    MAX-ACCESS  read-write
    STATUS      current
    DESCRIPTION   "Resource Allocator Trace Detail"
    ::=  { controlPlaneOtnConfigEntry 10 }

controlPlaneOtnConfigRaAlarmActivationTime OBJECT-TYPE
    SYNTAX      Unsigned32 
    UNITS       "s"
    MAX-ACCESS  read-write
    STATUS      current
    DESCRIPTION   "Resource Allocator Alarm Activation Time"
    ::=  { controlPlaneOtnConfigEntry 11 }

controlPlaneOtnConfigCmConfigFlag OBJECT-TYPE
    SYNTAX      Unsigned32
    MAX-ACCESS  read-write
    STATUS      current
    DESCRIPTION   "GMPLS Tunnel Manager Component' Configuration Bitfield"
    ::=  { controlPlaneOtnConfigEntry 12 }

controlPlaneOtnConfigCmTraceDetail OBJECT-TYPE
    SYNTAX      Unsigned32
    MAX-ACCESS  read-write
    STATUS      current
    DESCRIPTION   "GMPLS Tunnel Manager Component' Trace Detail"
    ::=  { controlPlaneOtnConfigEntry 13 }

controlPlaneOtnConfigCmAlarmActivationTime OBJECT-TYPE
    SYNTAX      Unsigned32 
    UNITS       "s"
    MAX-ACCESS  read-write
    STATUS      current
    DESCRIPTION   "GMPLS Tunnel Manager Component' Alarm Activation Time"
    ::=  { controlPlaneOtnConfigEntry 14 }

controlPlaneOtnConfigCmFisFrsTimeout OBJECT-TYPE
    SYNTAX      Unsigned32 
    UNITS       "s"
    MAX-ACCESS  read-write
    STATUS      current
    DESCRIPTION   "GMPLS Tunnel Manager Component' FIS-FRS Timeout"
    ::=  { controlPlaneOtnConfigEntry 15 }

controlPlaneOtnConfigCmCrankBackTimeout OBJECT-TYPE
    SYNTAX      Unsigned32 
    UNITS       "s"
    MAX-ACCESS  read-write
    STATUS      current
    DESCRIPTION   "GMPLS Tunnel Manager Component' Crank-Back Timeout"
    ::=  { controlPlaneOtnConfigEntry 16 }

controlPlaneOtnConfigCdbConfigFlag OBJECT-TYPE
    SYNTAX      Unsigned32
    MAX-ACCESS  read-write
    STATUS      current
    DESCRIPTION   "Label Swithed Path Database Component' Configuration Bitfield"
    ::=  { controlPlaneOtnConfigEntry 17 }

controlPlaneOtnConfigCdbDetail OBJECT-TYPE
    SYNTAX      Unsigned32
    MAX-ACCESS  read-write
    STATUS      current
    DESCRIPTION   "Label Swithed Path Database Component' Trace Detail"
    ::=  { controlPlaneOtnConfigEntry 18 }

controlPlaneOtnConfigCdbMaxSize OBJECT-TYPE
    SYNTAX      Unsigned32
    MAX-ACCESS  read-write
    STATUS      current
    DESCRIPTION   "Label Swithed Path Database Component' Maximum Size; 0 impiles no limit"
    ::=  { controlPlaneOtnConfigEntry 19 }

controlPlaneOtnConfigRsvpConfigFlag OBJECT-TYPE
    SYNTAX      Unsigned32
    MAX-ACCESS  read-write
    STATUS      current
    DESCRIPTION   "Resource Reservation Protocol Component' Configuration Bitfield"
    ::=  { controlPlaneOtnConfigEntry 20 }

controlPlaneOtnConfigRsvpMaxExpRestartTime OBJECT-TYPE
    SYNTAX      Counter64String 
    UNITS       "ms"
    MAX-ACCESS  read-write
    STATUS      current
    DESCRIPTION   "Maximum Expected Resource Reservation Protocol Component' Restart Time"
    ::=  { controlPlaneOtnConfigEntry 21 }

controlPlaneOtnConfigRsvpMaxExpRecoveryTime OBJECT-TYPE
    SYNTAX      Unsigned32 
    UNITS       "ms"
    MAX-ACCESS  read-write
    STATUS      current
    DESCRIPTION   "Maximum Expected Resource Reservation Protocol Component' Recovery Time"
    ::=  { controlPlaneOtnConfigEntry 22 }

controlPlaneOtnConfigTedbConfigFlag OBJECT-TYPE
    SYNTAX      Unsigned32
    MAX-ACCESS  read-write
    STATUS      current
    DESCRIPTION   "Traffic Engineering Component' Database Configuration Bitfield"
    ::=  { controlPlaneOtnConfigEntry 23 }

controlPlaneOtnConfigTedbTraceDetail OBJECT-TYPE
    SYNTAX      Unsigned32
    MAX-ACCESS  read-write
    STATUS      current
    DESCRIPTION   "Traffic Engineering Component' Database Trace Detail"
    ::=  { controlPlaneOtnConfigEntry 24 }

controlPlaneOtnConfigTedbMaxSize OBJECT-TYPE
    SYNTAX      Unsigned32
    MAX-ACCESS  read-write
    STATUS      current
    DESCRIPTION   "Traffic Engineering Component' Database Maximum Size"
    ::=  { controlPlaneOtnConfigEntry 25 }

controlPlaneOtnConfigTedbRouterId OBJECT-TYPE
    SYNTAX      IpAddress
    MAX-ACCESS  read-write
    STATUS      current
    DESCRIPTION   "Traffic Engineering Component' Router ID"
    ::=  { controlPlaneOtnConfigEntry 26 }

controlPlaneOtnConfigTedbMinAdvertWait OBJECT-TYPE
    SYNTAX      Unsigned32 
    UNITS       "s"
    MAX-ACCESS  read-write
    STATUS      current
    DESCRIPTION   "Traffic Engineering Component' Minimum Advertisement Wait"
    ::=  { controlPlaneOtnConfigEntry 27 }

controlPlaneOtnConfigNaasConfigFlag OBJECT-TYPE
    SYNTAX      Unsigned32
    MAX-ACCESS  read-write
    STATUS      current
    DESCRIPTION   "Node Attribute Advertising Service Database Configuration Bitfield"
    ::=  { controlPlaneOtnConfigEntry 28 }

controlPlaneOtnConfigNaasTraceDetail OBJECT-TYPE
    SYNTAX      Unsigned32
    MAX-ACCESS  read-write
    STATUS      current
    DESCRIPTION   "Node Attribute Advertising Service Database Trace Detail"
    ::=  { controlPlaneOtnConfigEntry 29 }

controlPlaneOtnConfigNaasMaxSize OBJECT-TYPE
    SYNTAX      Unsigned32
    MAX-ACCESS  read-write
    STATUS      current
    DESCRIPTION   "Node Attribute Advertising Service Database Maximum Size"
    ::=  { controlPlaneOtnConfigEntry 30 }

controlPlaneOtnConfigNaasAdvertWait OBJECT-TYPE
    SYNTAX      Unsigned32 
    UNITS       "s"
    MAX-ACCESS  read-write
    STATUS      current
    DESCRIPTION   "Node Attribute Advertising Service Database Advertisement Wait"
    ::=  { controlPlaneOtnConfigEntry 31 }

controlPlaneOtnConfigPcConfigFlag OBJECT-TYPE
    SYNTAX      Unsigned32
    MAX-ACCESS  read-write
    STATUS      current
    DESCRIPTION   "Path Computation Component' Configuration Bitfield"
    ::=  { controlPlaneOtnConfigEntry 32 }

controlPlaneOtnConfigPcTraceDetail OBJECT-TYPE
    SYNTAX      Unsigned32
    MAX-ACCESS  read-write
    STATUS      current
    DESCRIPTION   "Path Computation Component' Trace Detail."
    ::=  { controlPlaneOtnConfigEntry 33 }

controlPlaneOtnConfigCdConfigFlag OBJECT-TYPE
    SYNTAX      Unsigned32
    MAX-ACCESS  read-write
    STATUS      current
    DESCRIPTION   "Configuration Data Component' Configuration Bitfield"
    ::=  { controlPlaneOtnConfigEntry 34 }

controlPlaneOtnConfigCdTraceDetail OBJECT-TYPE
    SYNTAX      Unsigned32
    MAX-ACCESS  read-write
    STATUS      current
    DESCRIPTION   "Configuration Data Component' Trace Detail"
    ::=  { controlPlaneOtnConfigEntry 35 }

controlPlaneOtnConfigCdResyncTimeout OBJECT-TYPE
    SYNTAX      Unsigned32
    MAX-ACCESS  read-write
    STATUS      current
    DESCRIPTION   "Configuration Data Component' Resync Timeout"
    ::=  { controlPlaneOtnConfigEntry 36 }

controlPlaneOtnConfigRmConfigFlag OBJECT-TYPE
    SYNTAX      Unsigned32
    MAX-ACCESS  read-write
    STATUS      current
    DESCRIPTION   "Resource Management Component' Configuration Bitfield"
    ::=  { controlPlaneOtnConfigEntry 37 }

controlPlaneOtnConfigRmTraceDetail OBJECT-TYPE
    SYNTAX      Unsigned32
    MAX-ACCESS  read-write
    STATUS      current
    DESCRIPTION   "Resource Management Component' Trace Detail"
    ::=  { controlPlaneOtnConfigEntry 38 }

controlPlaneOtnConfigRmTraceTarget OBJECT-TYPE
    SYNTAX      Unsigned32
    MAX-ACCESS  read-write
    STATUS      current
    DESCRIPTION   "Resource Management Component' Trace Target"
    ::=  { controlPlaneOtnConfigEntry 39 }

controlPlaneOtnDataTable OBJECT-TYPE
    SYNTAX      SEQUENCE OF ControlPlaneOtnDataEntry
    MAX-ACCESS  not-accessible
    STATUS      current
    DESCRIPTION   ""
    ::=  { controlPlaneConfigAndStatus 56 }

controlPlaneOtnDataEntry OBJECT-TYPE
    SYNTAX      ControlPlaneOtnDataEntry
    MAX-ACCESS  not-accessible
    STATUS      current
    DESCRIPTION   ""
    INDEX       {
                  controlPlaneOtnEntityIndex
                }
    ::=  { controlPlaneOtnDataTable 1 }

ControlPlaneOtnDataEntry ::=  SEQUENCE
  { controlPlaneOtnDataCtmAlias SnmpAdminString,
    controlPlaneOtnDataRaAlias SnmpAdminString,
    controlPlaneOtnDataCmAlias SnmpAdminString,
    controlPlaneOtnDataCdbAlias SnmpAdminString,
    controlPlaneOtnDataTedbAlias SnmpAdminString,
    controlPlaneOtnDataNaasAlias SnmpAdminString,
    controlPlaneOtnDataPcAlias SnmpAdminString,
    controlPlaneOtnDataRsvpAlias SnmpAdminString,
    controlPlaneOtnDataCdAlias SnmpAdminString,
    controlPlaneOtnDataRmAlias SnmpAdminString,
    controlPlaneOtnDataNodeNameSyntax FspR7NodeId }

controlPlaneOtnDataCtmAlias OBJECT-TYPE
    SYNTAX      SnmpAdminString
    MAX-ACCESS  read-only
    STATUS      current
    DESCRIPTION   "Label Switched Path Edge Component Component' Base Name"
    ::=  { controlPlaneOtnDataEntry 1 }

controlPlaneOtnDataRaAlias OBJECT-TYPE
    SYNTAX      SnmpAdminString
    MAX-ACCESS  read-only
    STATUS      current
    DESCRIPTION   "Resource Allocator Component' Base Name"
    ::=  { controlPlaneOtnDataEntry 2 }

controlPlaneOtnDataCmAlias OBJECT-TYPE
    SYNTAX      SnmpAdminString
    MAX-ACCESS  read-only
    STATUS      current
    DESCRIPTION   "GMPLS Tunnel Manager Component' Base Name"
    ::=  { controlPlaneOtnDataEntry 3 }

controlPlaneOtnDataCdbAlias OBJECT-TYPE
    SYNTAX      SnmpAdminString
    MAX-ACCESS  read-only
    STATUS      current
    DESCRIPTION   "Label Swithed Path Database Component' Base Name"
    ::=  { controlPlaneOtnDataEntry 4 }

controlPlaneOtnDataTedbAlias OBJECT-TYPE
    SYNTAX      SnmpAdminString
    MAX-ACCESS  read-only
    STATUS      current
    DESCRIPTION   "Traffic Engineering Component' Database Name"
    ::=  { controlPlaneOtnDataEntry 5 }

controlPlaneOtnDataNaasAlias OBJECT-TYPE
    SYNTAX      SnmpAdminString
    MAX-ACCESS  read-only
    STATUS      current
    DESCRIPTION   "Node Attribute Advertising Service Database Component' Base Name"
    ::=  { controlPlaneOtnDataEntry 6 }

controlPlaneOtnDataPcAlias OBJECT-TYPE
    SYNTAX      SnmpAdminString
    MAX-ACCESS  read-only
    STATUS      current
    DESCRIPTION   "Path Computation Engine Component' Base Name"
    ::=  { controlPlaneOtnDataEntry 7 }

controlPlaneOtnDataRsvpAlias OBJECT-TYPE
    SYNTAX      SnmpAdminString
    MAX-ACCESS  read-only
    STATUS      current
    DESCRIPTION   "Resource Reservation Protocol Component' Base Name"
    ::=  { controlPlaneOtnDataEntry 8 }

controlPlaneOtnDataCdAlias OBJECT-TYPE
    SYNTAX      SnmpAdminString
    MAX-ACCESS  read-only
    STATUS      current
    DESCRIPTION   "Configuration Data Component' Base Name"
    ::=  { controlPlaneOtnDataEntry 9 }

controlPlaneOtnDataRmAlias OBJECT-TYPE
    SYNTAX      SnmpAdminString
    MAX-ACCESS  read-only
    STATUS      current
    DESCRIPTION   "Resource Management Component' Base Name"
    ::=  { controlPlaneOtnDataEntry 10 }

controlPlaneOtnDataNodeNameSyntax OBJECT-TYPE
    SYNTAX      FspR7NodeId
    MAX-ACCESS  read-only
    STATUS      deprecated
    DESCRIPTION   "Node Name Syntax"
    ::=  { controlPlaneOtnDataEntry 11 }

tunnelOtnConfigTable OBJECT-TYPE
    SYNTAX      SEQUENCE OF TunnelOtnConfigEntry
    MAX-ACCESS  not-accessible
    STATUS      current
    DESCRIPTION   ""
    ::=  { controlPlaneConfigAndStatus 57 }

tunnelOtnConfigEntry OBJECT-TYPE
    SYNTAX      TunnelOtnConfigEntry
    MAX-ACCESS  not-accessible
    STATUS      current
    DESCRIPTION   ""
    INDEX       {
                  controlPlaneOtnEntityIndex
                }
    ::=  { tunnelOtnConfigTable 1 }

TunnelOtnConfigEntry ::=  SEQUENCE
  { tunnelOtnConfigAlias SnmpAdminString,
    tunnelOtnConfigProvisionedPaths SnmpAdminString,
    tunnelOtnConfigPin FspR7CpPinning,
    tunnelOtnConfigAbortProcess FspR7CpAbortProcess,
    tunnelOtnConfigCommand FspR7CpCommand,
    tunnelOtnConfigProtectionType FspR7CpProtectionType,
    tunnelOtnConfigRestorationType FspR7CpRestorationType,
    tunnelOtnConfigMonitorEntities FspR7EnableDisable,
    tunnelOtnConfigAdminModifier FspR7CommandModifier,
    tunnelOtnConfigExcludedPaths SnmpAdminString,
    tunnelOtnConfigPreferPcs FspR7YesNo,
    tunnelOtnConfigEroScope SnmpAdminString,
    tunnelOtnConfigEroLifeCycle SnmpAdminString,
    tunnelOtnConfigXroScope SnmpAdminString,
    tunnelOtnConfigXroLifeCycle SnmpAdminString }

tunnelOtnConfigAlias OBJECT-TYPE
    SYNTAX      SnmpAdminString
    MAX-ACCESS  read-write
    STATUS      current
    DESCRIPTION   "Alias."
    ::=  { tunnelOtnConfigEntry 1 }

tunnelOtnConfigProvisionedPaths OBJECT-TYPE
    SYNTAX      SnmpAdminString
    MAX-ACCESS  read-write
    STATUS      current
    DESCRIPTION   ""
    ::=  { tunnelOtnConfigEntry 2 }

tunnelOtnConfigPin OBJECT-TYPE
    SYNTAX      FspR7CpPinning
    MAX-ACCESS  read-write
    STATUS      current
    DESCRIPTION   ""
    ::=  { tunnelOtnConfigEntry 3 }

tunnelOtnConfigAbortProcess OBJECT-TYPE
    SYNTAX      FspR7CpAbortProcess
    MAX-ACCESS  read-write
    STATUS      current
    DESCRIPTION   ""
    ::=  { tunnelOtnConfigEntry 4 }

tunnelOtnConfigCommand OBJECT-TYPE
    SYNTAX      FspR7CpCommand
    MAX-ACCESS  read-write
    STATUS      current
    DESCRIPTION   ""
    ::=  { tunnelOtnConfigEntry 5 }

tunnelOtnConfigProtectionType OBJECT-TYPE
    SYNTAX      FspR7CpProtectionType
    MAX-ACCESS  read-write
    STATUS      current
    DESCRIPTION   ""
    ::=  { tunnelOtnConfigEntry 6 }

tunnelOtnConfigRestorationType OBJECT-TYPE
    SYNTAX      FspR7CpRestorationType
    MAX-ACCESS  read-write
    STATUS      current
    DESCRIPTION   ""
    ::=  { tunnelOtnConfigEntry 7 }

tunnelOtnConfigMonitorEntities OBJECT-TYPE
    SYNTAX      FspR7EnableDisable
    MAX-ACCESS  read-write
    STATUS      current
    DESCRIPTION   ""
    ::=  { tunnelOtnConfigEntry 8 }

tunnelOtnConfigAdminModifier OBJECT-TYPE
    SYNTAX      FspR7CommandModifier
    MAX-ACCESS  read-write
    STATUS      current
    DESCRIPTION   ""
    ::=  { tunnelOtnConfigEntry 9 }

tunnelOtnConfigExcludedPaths OBJECT-TYPE
    SYNTAX      SnmpAdminString
    MAX-ACCESS  read-write
    STATUS      current
    DESCRIPTION
        "Lists of Path Elements to be excluded" 
    ::=  { tunnelOtnConfigEntry 10 }

tunnelOtnConfigPreferPcs OBJECT-TYPE
    SYNTAX      FspR7YesNo
    MAX-ACCESS  read-write
    STATUS      current
    DESCRIPTION
        "Preferred Path Computation Engine (Server)" 
    ::=  { tunnelOtnConfigEntry 11 }

tunnelOtnConfigEroScope OBJECT-TYPE
    SYNTAX      SnmpAdminString
    MAX-ACCESS  read-write
    STATUS      current
    DESCRIPTION
        "Inclusion Route - Scope" 
    ::=  { tunnelOtnConfigEntry 12 }

tunnelOtnConfigEroLifeCycle OBJECT-TYPE
    SYNTAX      SnmpAdminString
    MAX-ACCESS  read-write
    STATUS      current
    DESCRIPTION
        "Inclusion Route - Life Cycle" 
    ::=  { tunnelOtnConfigEntry 13 }

tunnelOtnConfigXroScope OBJECT-TYPE
    SYNTAX      SnmpAdminString
    MAX-ACCESS  read-write
    STATUS      current
    DESCRIPTION
        "Exclusion Path Elements - Scope" 
    ::=  { tunnelOtnConfigEntry 14 }

tunnelOtnConfigXroLifeCycle OBJECT-TYPE
    SYNTAX      SnmpAdminString
    MAX-ACCESS  read-write
    STATUS      current
    DESCRIPTION
        "Exclusion Path Elements - Life Cycle" 
    ::=  { tunnelOtnConfigEntry 15 }

tunnelOtnDataTable OBJECT-TYPE
    SYNTAX      SEQUENCE OF TunnelOtnDataEntry
    MAX-ACCESS  not-accessible
    STATUS      current
    DESCRIPTION   ""
    ::=  { controlPlaneConfigAndStatus 58 }

tunnelOtnDataEntry OBJECT-TYPE
    SYNTAX      TunnelOtnDataEntry
    MAX-ACCESS  not-accessible
    STATUS      current
    DESCRIPTION   ""
    INDEX       {
                  controlPlaneOtnEntityIndex
                }
    ::=  { tunnelOtnDataTable 1 }

TunnelOtnDataEntry ::=  SEQUENCE
  { tunnelOtnDataTunnelId SnmpAdminString,
    tunnelOtnDataTunnelNo Unsigned32,
    tunnelOtnDataTunnelType FspR7CpTunnelType,
    tunnelOtnDataFromTid SnmpAdminString,
    tunnelOtnDataFromNodeIP IpAddress,
    tunnelOtnDataToTid SnmpAdminString,
    tunnelOtnDataToTidMonitor SnmpAdminString,
    tunnelOtnDataToNodeIp IpAddress,
    tunnelOtnDataToNodeIpMonitor IpAddress,
    tunnelOtnDataFromAid EntityIndex,
    tunnelOtnDataToAid EntityIndex,
    tunnelOtnDataConnectionDirection FspR7Conn,
    tunnelOtnDataFacilityType FspR7InterfaceType,
    tunnelOtnDataComputedPaths SnmpAdminString,
    tunnelOtnDataComputationState FspR7CpCompState,
    tunnelOtnDataErrorMessage SnmpAdminString,
    tunnelOtnDataCirTrmt Unsigned32,
    tunnelOtnDataCbsTrmt Unsigned32,
    tunnelOtnDataErrorCodeMajor Unsigned32,
    tunnelOtnDataErrorCodeMinor Integer32,
    tunnelOtnDataErrorIp IpAddress,
    tunnelOtnDataErrorTid SnmpAdminString,
    tunnelOtnDataErrorCategory FspR7CpErrorCategory,
    tunnelOtnDataSpecificErrorMessage SnmpAdminString,
    tunnelOtnDataTunnelScope FspR7CpTunnelScope,
    tunnelOtnDataLayer FspR7PacketsLayer,
    tunnelOtnDataOifUni FspR7YesNo,
    tunnelOtnDataTunnelNumberExtension Unsigned32,
    tunnelOtnDataMonitorEntitiesDerive FspR7EnableDisable,
    tunnelOtnDataFromAidString SnmpAdminString,
    tunnelOtnDataToAidString SnmpAdminString }

tunnelOtnDataTunnelId OBJECT-TYPE
    SYNTAX      SnmpAdminString
    MAX-ACCESS  read-only
    STATUS      current
    DESCRIPTION   ""
    ::=  { tunnelOtnDataEntry 1 }

tunnelOtnDataTunnelNo OBJECT-TYPE
    SYNTAX      Unsigned32
    MAX-ACCESS  read-only
    STATUS      current
    DESCRIPTION   ""
    ::=  { tunnelOtnDataEntry 2 }

tunnelOtnDataTunnelType OBJECT-TYPE
    SYNTAX      FspR7CpTunnelType
    MAX-ACCESS  read-only
    STATUS      current
    DESCRIPTION   ""
    ::=  { tunnelOtnDataEntry 3 }

tunnelOtnDataFromTid OBJECT-TYPE
    SYNTAX      SnmpAdminString
    MAX-ACCESS  read-only
    STATUS      current
    DESCRIPTION   ""
    ::=  { tunnelOtnDataEntry 4 }

tunnelOtnDataFromNodeIP OBJECT-TYPE
    SYNTAX      IpAddress
    MAX-ACCESS  read-only
    STATUS      current
    DESCRIPTION   ""
    ::=  { tunnelOtnDataEntry 5 }

tunnelOtnDataToTid OBJECT-TYPE
    SYNTAX      SnmpAdminString
    MAX-ACCESS  read-only
    STATUS      current
    DESCRIPTION   ""
    ::=  { tunnelOtnDataEntry 6 }

tunnelOtnDataToTidMonitor OBJECT-TYPE
    SYNTAX      SnmpAdminString
    MAX-ACCESS  read-only
    STATUS      current
    DESCRIPTION   ""
    ::=  { tunnelOtnDataEntry 7 }

tunnelOtnDataToNodeIp OBJECT-TYPE
    SYNTAX      IpAddress
    MAX-ACCESS  read-only
    STATUS      current
    DESCRIPTION   ""
    ::=  { tunnelOtnDataEntry 8 }

tunnelOtnDataToNodeIpMonitor OBJECT-TYPE
    SYNTAX      IpAddress
    MAX-ACCESS  read-only
    STATUS      current
    DESCRIPTION   ""
    ::=  { tunnelOtnDataEntry 9 }

tunnelOtnDataFromAid OBJECT-TYPE
    SYNTAX      EntityIndex
    MAX-ACCESS  read-only
    STATUS      current
    DESCRIPTION   ""
    ::=  { tunnelOtnDataEntry 10 }

tunnelOtnDataToAid OBJECT-TYPE
    SYNTAX      EntityIndex
    MAX-ACCESS  read-only
    STATUS      current
    DESCRIPTION   ""
    ::=  { tunnelOtnDataEntry 11 }

tunnelOtnDataConnectionDirection OBJECT-TYPE
    SYNTAX      FspR7Conn
    MAX-ACCESS  read-only
    STATUS      current
    DESCRIPTION   ""
    ::=  { tunnelOtnDataEntry 12 }

tunnelOtnDataFacilityType OBJECT-TYPE
    SYNTAX      FspR7InterfaceType
    MAX-ACCESS  read-only
    STATUS      current
    DESCRIPTION   ""
    ::=  { tunnelOtnDataEntry 13 }

tunnelOtnDataComputedPaths OBJECT-TYPE
    SYNTAX      SnmpAdminString
    MAX-ACCESS  read-only
    STATUS      current
    DESCRIPTION   ""
    ::=  { tunnelOtnDataEntry 14 }

tunnelOtnDataComputationState OBJECT-TYPE
    SYNTAX      FspR7CpCompState
    MAX-ACCESS  read-only
    STATUS      current
    DESCRIPTION   ""
    ::=  { tunnelOtnDataEntry 15 }

tunnelOtnDataErrorMessage OBJECT-TYPE
    SYNTAX      SnmpAdminString
    MAX-ACCESS  read-only
    STATUS      current
    DESCRIPTION   ""
    ::=  { tunnelOtnDataEntry 16 }

tunnelOtnDataCirTrmt OBJECT-TYPE
    SYNTAX      Unsigned32 
    UNITS       "Mbps"
    MAX-ACCESS  read-only
    STATUS      current
    DESCRIPTION
        "CIR (Committed Information Rate ) is used on Ethernet Interfaces with a policing function" 
    ::=  { tunnelOtnDataEntry 17 }

tunnelOtnDataCbsTrmt OBJECT-TYPE
    SYNTAX      Unsigned32 (0..25600 | 4294967295) 
    UNITS       "kByte"
    MAX-ACCESS  read-only
    STATUS      current
    DESCRIPTION
        "Committed Burst Size" 
    ::=  { tunnelOtnDataEntry 18 }

tunnelOtnDataErrorCodeMajor OBJECT-TYPE
    SYNTAX      Unsigned32
    MAX-ACCESS  read-only
    STATUS      current
    DESCRIPTION
        "Errorcode Major" 
    ::=  { tunnelOtnDataEntry 19 }

tunnelOtnDataErrorCodeMinor OBJECT-TYPE
    SYNTAX      Integer32
    MAX-ACCESS  read-only
    STATUS      current
    DESCRIPTION
        "Errorcode Minor" 
    ::=  { tunnelOtnDataEntry 20 }

tunnelOtnDataErrorIp OBJECT-TYPE
    SYNTAX      IpAddress
    MAX-ACCESS  read-only
    STATUS      current
    DESCRIPTION
        "Error IP" 
    ::=  { tunnelOtnDataEntry 21 }

tunnelOtnDataErrorTid OBJECT-TYPE
    SYNTAX      SnmpAdminString
    MAX-ACCESS  read-only
    STATUS      current
    DESCRIPTION
        "Error TID" 
    ::=  { tunnelOtnDataEntry 22 }

tunnelOtnDataErrorCategory OBJECT-TYPE
    SYNTAX      FspR7CpErrorCategory
    MAX-ACCESS  read-only
    STATUS      current
    DESCRIPTION
        "CP Provisioning Failure Category" 
    ::=  { tunnelOtnDataEntry 23 }

tunnelOtnDataSpecificErrorMessage OBJECT-TYPE
    SYNTAX      SnmpAdminString
    MAX-ACCESS  read-only
    STATUS      current
    DESCRIPTION
        "Specific Error Message" 
    ::=  { tunnelOtnDataEntry 24 }

tunnelOtnDataTunnelScope OBJECT-TYPE
    SYNTAX      FspR7CpTunnelScope
    MAX-ACCESS  read-only
    STATUS      current
    DESCRIPTION
        "Service Scope extending over either Client or Network Ports of Modules or Links (UN or NR) for Connection Segements" 
    ::=  { tunnelOtnDataEntry 25 }

tunnelOtnDataLayer OBJECT-TYPE
    SYNTAX      FspR7PacketsLayer
    MAX-ACCESS  read-only
    STATUS      current
    DESCRIPTION
        "Notional Layer of Advertisement on Packets on the LIF" 
    ::=  { tunnelOtnDataEntry 26 }

tunnelOtnDataOifUni OBJECT-TYPE
    SYNTAX      FspR7YesNo
    MAX-ACCESS  read-only
    STATUS      current
    DESCRIPTION
        "OIF UNI Tunnel" 
    ::=  { tunnelOtnDataEntry 27 }

tunnelOtnDataTunnelNumberExtension OBJECT-TYPE
    SYNTAX      Unsigned32
    MAX-ACCESS  read-only
    STATUS      current
    DESCRIPTION
        "Tunnel Number Extension. (internal: serviceID.extTunnelID)" 
    ::=  { tunnelOtnDataEntry 28 }

tunnelOtnDataMonitorEntitiesDerive OBJECT-TYPE
    SYNTAX      FspR7EnableDisable
    MAX-ACCESS  read-only
    STATUS      current
    DESCRIPTION   ""
    ::=  { tunnelOtnDataEntry 29 }

tunnelOtnDataFromAidString OBJECT-TYPE
    SYNTAX      SnmpAdminString
    MAX-ACCESS  read-only
    STATUS      current
    DESCRIPTION
        "" 
    ::=  { tunnelOtnDataEntry 30 }

tunnelOtnDataToAidString OBJECT-TYPE
    SYNTAX      SnmpAdminString
    MAX-ACCESS  read-only
    STATUS      current
    DESCRIPTION
        "" 
    ::=  { tunnelOtnDataEntry 31 }

connectionOtnConfigTable OBJECT-TYPE
    SYNTAX      SEQUENCE OF ConnectionOtnConfigEntry
    MAX-ACCESS  not-accessible
    STATUS      current
    DESCRIPTION   ""
    ::=  { controlPlaneConfigAndStatus 59 }

connectionOtnConfigEntry OBJECT-TYPE
    SYNTAX      ConnectionOtnConfigEntry
    MAX-ACCESS  not-accessible
    STATUS      current
    DESCRIPTION   ""
    INDEX       {
                  controlPlaneOtnEntityIndex
                }
    ::=  { connectionOtnConfigTable 1 }

ConnectionOtnConfigEntry ::=  SEQUENCE
  { connectionOtnConfigCancelConnEntities FspR7CpCancConnection,
    connectionOtnConfigCancelModifier FspR7CommandModifier }

connectionOtnConfigCancelConnEntities OBJECT-TYPE
    SYNTAX      FspR7CpCancConnection
    MAX-ACCESS  read-write
    STATUS      current
    DESCRIPTION   ""
    ::=  { connectionOtnConfigEntry 1 }

connectionOtnConfigCancelModifier OBJECT-TYPE
    SYNTAX      FspR7CommandModifier
    MAX-ACCESS  read-write
    STATUS      current
    DESCRIPTION   ""
    ::=  { connectionOtnConfigEntry 2 }

connectionOtnDataTable OBJECT-TYPE
    SYNTAX      SEQUENCE OF ConnectionOtnDataEntry
    MAX-ACCESS  not-accessible
    STATUS      current
    DESCRIPTION   ""
    ::=  { controlPlaneConfigAndStatus 60 }

connectionOtnDataEntry OBJECT-TYPE
    SYNTAX      ConnectionOtnDataEntry
    MAX-ACCESS  not-accessible
    STATUS      current
    DESCRIPTION   ""
    INDEX       {
                  controlPlaneOtnEntityIndex
                }
    ::=  { connectionOtnDataTable 1 }

ConnectionOtnDataEntry ::=  SEQUENCE
  { connectionOtnDataTunnelId SnmpAdminString,
    connectionOtnDataTunnelNo Unsigned32,
    connectionOtnDataTunnelType FspR7CpTunnelType,
    connectionOtnDataFromTid SnmpAdminString,
    connectionOtnDataFromNodeIp IpAddress,
    connectionOtnDataToTid SnmpAdminString,
    connectionOtnDataToNodeIp IpAddress,
    connectionOtnDataFromAid EntityIndex,
    connectionOtnDataToAid EntityIndex,
    connectionOtnDataConnectionDirection FspR7Conn,
    connectionOtnDataNetworkElementPosition FspR7CpNePosition,
    connectionOtnDataFacilityType FspR7InterfaceType,
    connectionOtnDataBitrate Unsigned32,
    connectionOtnDataEncode FspR7CpEncode,
    connectionOtnDataTerminationLevel OhTerminationLevel,
    connectionOtnDataFecType FspR7FecType,
    connectionOtnDataStuff FspR7Stuff,
    connectionOtnDataSignalledPaths SnmpAdminString,
    connectionOtnDataComputedPaths SnmpAdminString,
    connectionOtnDataRole FspR7CpRole,
    connectionOtnDataErrorMessage SnmpAdminString,
    connectionOtnDataActivationState FspR7CpActivState,
    connectionOtnDataRestorable FspR7FalseTrue,
    connectionOtnDataRestorationState FspR7CpCompState,
    connectionOtnDataEqualizationState FspR7CpCompState,
    connectionOtnDataModificationState FspR7CpCompState,
    connectionOtnDataMonitorEntities FspR7EnableDisable,
    connectionOtnDataTunnelScope FspR7CpTunnelScope,
    connectionOtnDataLayer FspR7PacketsLayer,
    connectionOtnDataSourceTna IpAddress,
    connectionOtnDataDestinationTna IpAddress,
    connectionOtnDataTunnelNumberExtension Unsigned32,
    connectionOtnDataTunnelInstance Unsigned32,
    connectionOtnDataConnectionNo Unsigned32,
    connectionOtnDataFromAidString SnmpAdminString,
    connectionOtnDataToAidString SnmpAdminString,
    connectionOtnDataLayerFacType SnmpAdminString,
    connectionOtnDataLayerTermType SnmpAdminString }

connectionOtnDataTunnelId OBJECT-TYPE
    SYNTAX      SnmpAdminString
    MAX-ACCESS  read-only
    STATUS      current
    DESCRIPTION   ""
    ::=  { connectionOtnDataEntry 1 }

connectionOtnDataTunnelNo OBJECT-TYPE
    SYNTAX      Unsigned32
    MAX-ACCESS  read-only
    STATUS      current
    DESCRIPTION   ""
    ::=  { connectionOtnDataEntry 2 }

connectionOtnDataTunnelType OBJECT-TYPE
    SYNTAX      FspR7CpTunnelType
    MAX-ACCESS  read-only
    STATUS      current
    DESCRIPTION   ""
    ::=  { connectionOtnDataEntry 3 }

connectionOtnDataFromTid OBJECT-TYPE
    SYNTAX      SnmpAdminString
    MAX-ACCESS  read-only
    STATUS      current
    DESCRIPTION   ""
    ::=  { connectionOtnDataEntry 4 }

connectionOtnDataFromNodeIp OBJECT-TYPE
    SYNTAX      IpAddress
    MAX-ACCESS  read-only
    STATUS      current
    DESCRIPTION   ""
    ::=  { connectionOtnDataEntry 5 }

connectionOtnDataToTid OBJECT-TYPE
    SYNTAX      SnmpAdminString
    MAX-ACCESS  read-only
    STATUS      current
    DESCRIPTION   ""
    ::=  { connectionOtnDataEntry 6 }

connectionOtnDataToNodeIp OBJECT-TYPE
    SYNTAX      IpAddress
    MAX-ACCESS  read-only
    STATUS      current
    DESCRIPTION   ""
    ::=  { connectionOtnDataEntry 7 }

connectionOtnDataFromAid OBJECT-TYPE
    SYNTAX      EntityIndex
    MAX-ACCESS  read-only
    STATUS      current
    DESCRIPTION   ""
    ::=  { connectionOtnDataEntry 8 }

connectionOtnDataToAid OBJECT-TYPE
    SYNTAX      EntityIndex
    MAX-ACCESS  read-only
    STATUS      current
    DESCRIPTION   ""
    ::=  { connectionOtnDataEntry 9 }

connectionOtnDataConnectionDirection OBJECT-TYPE
    SYNTAX      FspR7Conn
    MAX-ACCESS  read-only
    STATUS      current
    DESCRIPTION   ""
    ::=  { connectionOtnDataEntry 10 }

connectionOtnDataNetworkElementPosition OBJECT-TYPE
    SYNTAX      FspR7CpNePosition
    MAX-ACCESS  read-only
    STATUS      current
    DESCRIPTION   ""
    ::=  { connectionOtnDataEntry 11 }

connectionOtnDataFacilityType OBJECT-TYPE
    SYNTAX      FspR7InterfaceType
    MAX-ACCESS  read-only
    STATUS      current
    DESCRIPTION   ""
    ::=  { connectionOtnDataEntry 12 }

connectionOtnDataBitrate OBJECT-TYPE
    SYNTAX      Unsigned32 
    UNITS       "Mbps"
    MAX-ACCESS  read-only
    STATUS      current
    DESCRIPTION   ""
    ::=  { connectionOtnDataEntry 13 }

connectionOtnDataEncode OBJECT-TYPE
    SYNTAX      FspR7CpEncode
    MAX-ACCESS  read-only
    STATUS      current
    DESCRIPTION   ""
    ::=  { connectionOtnDataEntry 14 }

connectionOtnDataTerminationLevel OBJECT-TYPE
    SYNTAX      OhTerminationLevel
    MAX-ACCESS  read-only
    STATUS      current
    DESCRIPTION   ""
    ::=  { connectionOtnDataEntry 15 }

connectionOtnDataFecType OBJECT-TYPE
    SYNTAX      FspR7FecType
    MAX-ACCESS  read-only
    STATUS      current
    DESCRIPTION   ""
    ::=  { connectionOtnDataEntry 16 }

connectionOtnDataStuff OBJECT-TYPE
    SYNTAX      FspR7Stuff
    MAX-ACCESS  read-only
    STATUS      current
    DESCRIPTION   ""
    ::=  { connectionOtnDataEntry 17 }

connectionOtnDataSignalledPaths OBJECT-TYPE
    SYNTAX      SnmpAdminString
    MAX-ACCESS  read-only
    STATUS      current
    DESCRIPTION   ""
    ::=  { connectionOtnDataEntry 18 }

connectionOtnDataComputedPaths OBJECT-TYPE
    SYNTAX      SnmpAdminString
    MAX-ACCESS  read-only
    STATUS      current
    DESCRIPTION   ""
    ::=  { connectionOtnDataEntry 19 }

connectionOtnDataRole OBJECT-TYPE
    SYNTAX      FspR7CpRole
    MAX-ACCESS  read-only
    STATUS      current
    DESCRIPTION   ""
    ::=  { connectionOtnDataEntry 20 }

connectionOtnDataErrorMessage OBJECT-TYPE
    SYNTAX      SnmpAdminString
    MAX-ACCESS  read-only
    STATUS      current
    DESCRIPTION   ""
    ::=  { connectionOtnDataEntry 21 }

connectionOtnDataActivationState OBJECT-TYPE
    SYNTAX      FspR7CpActivState
    MAX-ACCESS  read-only
    STATUS      current
    DESCRIPTION   ""
    ::=  { connectionOtnDataEntry 22 }

connectionOtnDataRestorable OBJECT-TYPE
    SYNTAX      FspR7FalseTrue
    MAX-ACCESS  read-only
    STATUS      current
    DESCRIPTION   ""
    ::=  { connectionOtnDataEntry 23 }

connectionOtnDataRestorationState OBJECT-TYPE
    SYNTAX      FspR7CpCompState
    MAX-ACCESS  read-only
    STATUS      deprecated
    DESCRIPTION   ""
    ::=  { connectionOtnDataEntry 24 }

connectionOtnDataEqualizationState OBJECT-TYPE
    SYNTAX      FspR7CpCompState
    MAX-ACCESS  read-only
    STATUS      current
    DESCRIPTION   ""
    ::=  { connectionOtnDataEntry 25 }

connectionOtnDataModificationState OBJECT-TYPE
    SYNTAX      FspR7CpCompState
    MAX-ACCESS  read-only
    STATUS      current
    DESCRIPTION
        "Modification Enumeration State" 
    ::=  { connectionOtnDataEntry 26 }

connectionOtnDataMonitorEntities OBJECT-TYPE
    SYNTAX      FspR7EnableDisable
    MAX-ACCESS  read-only
    STATUS      deprecated
    DESCRIPTION   ""
    ::=  { connectionOtnDataEntry 27 }

connectionOtnDataTunnelScope OBJECT-TYPE
    SYNTAX      FspR7CpTunnelScope
    MAX-ACCESS  read-only
    STATUS      current
    DESCRIPTION
        "Service Scope extending over either Client or Network Ports of Modules or Links (UN or NR) for Connection Segements" 
    ::=  { connectionOtnDataEntry 28 }

connectionOtnDataLayer OBJECT-TYPE
    SYNTAX      FspR7PacketsLayer
    MAX-ACCESS  read-only
    STATUS      current
    DESCRIPTION
        "Notional Layer of Advertisement on Packets on the LIF" 
    ::=  { connectionOtnDataEntry 29 }

connectionOtnDataSourceTna OBJECT-TYPE
    SYNTAX      IpAddress
    MAX-ACCESS  read-only
    STATUS      current
    DESCRIPTION
        "Source Transport Network Assigned Name" 
    ::=  { connectionOtnDataEntry 30 }

connectionOtnDataDestinationTna OBJECT-TYPE
    SYNTAX      IpAddress
    MAX-ACCESS  read-only
    STATUS      current
    DESCRIPTION
        "Destination Transport Network Assigned Name" 
    ::=  { connectionOtnDataEntry 31 }

connectionOtnDataTunnelNumberExtension OBJECT-TYPE
    SYNTAX      Unsigned32
    MAX-ACCESS  read-only
    STATUS      current
    DESCRIPTION
        "Tunnel Number Extension. (internal: serviceID.extTunnelID)" 
    ::=  { connectionOtnDataEntry 32 }

connectionOtnDataTunnelInstance OBJECT-TYPE
    SYNTAX      Unsigned32
    MAX-ACCESS  read-only
    STATUS      current
    DESCRIPTION
        "Tunnel Instance also called Service Instance ID. This changes every time there is Make-Before-Break operation. (internal: serviceInstID.octpID)" 
    ::=  { connectionOtnDataEntry 33 }

connectionOtnDataConnectionNo OBJECT-TYPE
    SYNTAX      Unsigned32
    MAX-ACCESS  read-only
    STATUS      current
    DESCRIPTION
        "Connection Number also called Connection ID. This changes every time there is Make-Before-Break operation. Working and protection connection numbers are different. (internal: lsptID.octpID)" 
    ::=  { connectionOtnDataEntry 34 }

connectionOtnDataFromAidString OBJECT-TYPE
    SYNTAX      SnmpAdminString
    MAX-ACCESS  read-only
    STATUS      current
    DESCRIPTION   ""
    ::=  { connectionOtnDataEntry 35 }

connectionOtnDataToAidString OBJECT-TYPE
    SYNTAX      SnmpAdminString
    MAX-ACCESS  read-only
    STATUS      current
    DESCRIPTION   ""
    ::=  { connectionOtnDataEntry 36 }

connectionOtnDataLayerFacType OBJECT-TYPE
    SYNTAX      SnmpAdminString
    MAX-ACCESS  read-only
    STATUS      current
    DESCRIPTION
        "Layer Facility Type" 
    ::=  { connectionOtnDataEntry 37 }

connectionOtnDataLayerTermType OBJECT-TYPE
    SYNTAX      SnmpAdminString
    MAX-ACCESS  read-only
    STATUS      current
    DESCRIPTION
        "Layer Termination Type" 
    ::=  { connectionOtnDataEntry 38 }

inventoryCpOtnDownDataTable OBJECT-TYPE
    SYNTAX      SEQUENCE OF InventoryCpOtnDownDataEntry
    MAX-ACCESS  not-accessible
    STATUS      current
    DESCRIPTION   ""
    ::=  { controlPlaneConfigAndStatus 61 }

inventoryCpOtnDownDataEntry OBJECT-TYPE
    SYNTAX      InventoryCpOtnDownDataEntry
    MAX-ACCESS  not-accessible
    STATUS      current
    DESCRIPTION   ""
    INDEX       {
                  controlPlaneOtnEntityIndex,
                  inventoryCpOtnDownDataNumber
                }
    ::=  { inventoryCpOtnDownDataTable 1 }

InventoryCpOtnDownDataEntry ::=  SEQUENCE
  { inventoryCpOtnDownDataNumber EntityIndex,
    inventoryCpOtnDownDataResources EntityIndex,
    inventoryCpOtnDownDataFacilities EntityIndex,
    inventoryCpOtnDownDataPhysicalTermPoints EntityIndex }

inventoryCpOtnDownDataNumber OBJECT-TYPE
    SYNTAX      EntityIndex
    MAX-ACCESS  not-accessible
    STATUS      current
    DESCRIPTION   ""
    ::=  { inventoryCpOtnDownDataEntry 1 }

inventoryCpOtnDownDataResources OBJECT-TYPE
    SYNTAX      EntityIndex
    MAX-ACCESS  read-only
    STATUS      current
    DESCRIPTION   ""
    ::=  { inventoryCpOtnDownDataEntry 2 }

inventoryCpOtnDownDataFacilities OBJECT-TYPE
    SYNTAX      EntityIndex
    MAX-ACCESS  read-only
    STATUS      current
    DESCRIPTION   ""
    ::=  { inventoryCpOtnDownDataEntry 3 }

inventoryCpOtnDownDataPhysicalTermPoints OBJECT-TYPE
    SYNTAX      EntityIndex
    MAX-ACCESS  read-only
    STATUS      current
    DESCRIPTION   ""
    ::=  { inventoryCpOtnDownDataEntry 4 }

inventoryCpOtnUpDataTable OBJECT-TYPE
    SYNTAX      SEQUENCE OF InventoryCpOtnUpDataEntry
    MAX-ACCESS  not-accessible
    STATUS      current
    DESCRIPTION   ""
    ::=  { controlPlaneConfigAndStatus 62 }

inventoryCpOtnUpDataEntry OBJECT-TYPE
    SYNTAX      InventoryCpOtnUpDataEntry
    MAX-ACCESS  not-accessible
    STATUS      current
    DESCRIPTION   ""
    INDEX       {
                  controlPlaneOtnEntityIndex,
                  inventoryCpOtnUpDataNumber
                }
    ::=  { inventoryCpOtnUpDataTable 1 }

InventoryCpOtnUpDataEntry ::=  SEQUENCE
  { inventoryCpOtnUpDataNumber EntityIndex,
    inventoryCpOtnUpDataResources EntityIndex,
    inventoryCpOtnUpDataFacilities EntityIndex,
    inventoryCpOtnUpDataPhysicalTermPoints EntityIndex }

inventoryCpOtnUpDataNumber OBJECT-TYPE
    SYNTAX      EntityIndex
    MAX-ACCESS  not-accessible
    STATUS      current
    DESCRIPTION   ""
    ::=  { inventoryCpOtnUpDataEntry 1 }

inventoryCpOtnUpDataResources OBJECT-TYPE
    SYNTAX      EntityIndex
    MAX-ACCESS  read-only
    STATUS      current
    DESCRIPTION   ""
    ::=  { inventoryCpOtnUpDataEntry 2 }

inventoryCpOtnUpDataFacilities OBJECT-TYPE
    SYNTAX      EntityIndex
    MAX-ACCESS  read-only
    STATUS      current
    DESCRIPTION   ""
    ::=  { inventoryCpOtnUpDataEntry 3 }

inventoryCpOtnUpDataPhysicalTermPoints OBJECT-TYPE
    SYNTAX      EntityIndex
    MAX-ACCESS  read-only
    STATUS      current
    DESCRIPTION   ""
    ::=  { inventoryCpOtnUpDataEntry 4 }

inventoryCpOtnCrsDownDataTable OBJECT-TYPE
    SYNTAX      SEQUENCE OF InventoryCpOtnCrsDownDataEntry
    MAX-ACCESS  not-accessible
    STATUS      current
    DESCRIPTION   ""
    ::=  { controlPlaneConfigAndStatus 63 }

inventoryCpOtnCrsDownDataEntry OBJECT-TYPE
    SYNTAX      InventoryCpOtnCrsDownDataEntry
    MAX-ACCESS  not-accessible
    STATUS      current
    DESCRIPTION   ""
    INDEX       {
                  controlPlaneOtnEntityIndex,
                  inventoryCpOtnCrsDownDataNumber,
                  entityIndex
                }
    ::=  { inventoryCpOtnCrsDownDataTable 1 }

InventoryCpOtnCrsDownDataEntry ::=  SEQUENCE
  { inventoryCpOtnCrsDownDataNumber EntityIndex,
    inventoryCpOtnCrsDownDataAids EntityIndex,
    inventoryCpOtnCrsDownDataAidsString SnmpAdminString }

inventoryCpOtnCrsDownDataNumber OBJECT-TYPE
    SYNTAX      EntityIndex
    MAX-ACCESS  not-accessible
    STATUS      current
    DESCRIPTION   ""
    ::=  { inventoryCpOtnCrsDownDataEntry 1 }

inventoryCpOtnCrsDownDataAids OBJECT-TYPE
    SYNTAX      EntityIndex
    MAX-ACCESS  read-only
    STATUS      current
    DESCRIPTION   ""
    ::=  { inventoryCpOtnCrsDownDataEntry 2 }

inventoryCpOtnCrsDownDataAidsString OBJECT-TYPE
    SYNTAX      SnmpAdminString
    MAX-ACCESS  read-only
    STATUS      current
    DESCRIPTION   ""
    ::=  { inventoryCpOtnCrsDownDataEntry 3 }

inventoryCpOtnCrsUpDataTable OBJECT-TYPE
    SYNTAX      SEQUENCE OF InventoryCpOtnCrsUpDataEntry
    MAX-ACCESS  not-accessible
    STATUS      current
    DESCRIPTION   ""
    ::=  { controlPlaneConfigAndStatus 64 }

inventoryCpOtnCrsUpDataEntry OBJECT-TYPE
    SYNTAX      InventoryCpOtnCrsUpDataEntry
    MAX-ACCESS  not-accessible
    STATUS      current
    DESCRIPTION   ""
    INDEX       {
                  controlPlaneOtnEntityIndex,
                  inventoryCpOtnCrsUpDataNumber,
                  entityIndex
                }
    ::=  { inventoryCpOtnCrsUpDataTable 1 }

InventoryCpOtnCrsUpDataEntry ::=  SEQUENCE
  { inventoryCpOtnCrsUpDataNumber EntityIndex,
    inventoryCpOtnCrsUpDataAids EntityIndex,
    inventoryCpOtnCrsUpDataAidsString SnmpAdminString }

inventoryCpOtnCrsUpDataNumber OBJECT-TYPE
    SYNTAX      EntityIndex
    MAX-ACCESS  not-accessible
    STATUS      current
    DESCRIPTION   ""
    ::=  { inventoryCpOtnCrsUpDataEntry 1 }

inventoryCpOtnCrsUpDataAids OBJECT-TYPE
    SYNTAX      EntityIndex
    MAX-ACCESS  read-only
    STATUS      current
    DESCRIPTION   ""
    ::=  { inventoryCpOtnCrsUpDataEntry 2 }

inventoryCpOtnCrsUpDataAidsString OBJECT-TYPE
    SYNTAX      SnmpAdminString
    MAX-ACCESS  read-only
    STATUS      current
    DESCRIPTION   ""
    ::=  { inventoryCpOtnCrsUpDataEntry 3 }

pathOtnDataTable OBJECT-TYPE
    SYNTAX      SEQUENCE OF PathOtnDataEntry
    MAX-ACCESS  not-accessible
    STATUS      current
    DESCRIPTION   ""
    ::=  { controlPlaneConfigAndStatus 65 }

pathOtnDataEntry OBJECT-TYPE
    SYNTAX      PathOtnDataEntry
    MAX-ACCESS  not-accessible
    STATUS      current
    DESCRIPTION   ""
    INDEX       {
                  controlPlaneOtnEntityIndex
                }
    ::=  { pathOtnDataTable 1 }

PathOtnDataEntry ::=  SEQUENCE
  { pathOtnDataPathId SnmpAdminString,
    pathOtnDataPathType FspR7CpPathType,
    pathOtnDataConnectionTunnelAid EntityIndex,
    pathOtnDataRole FspR7CpRole }

pathOtnDataPathId OBJECT-TYPE
    SYNTAX      SnmpAdminString
    MAX-ACCESS  read-only
    STATUS      current
    DESCRIPTION   ""
    ::=  { pathOtnDataEntry 1 }

pathOtnDataPathType OBJECT-TYPE
    SYNTAX      FspR7CpPathType
    MAX-ACCESS  read-only
    STATUS      current
    DESCRIPTION   ""
    ::=  { pathOtnDataEntry 2 }

pathOtnDataConnectionTunnelAid OBJECT-TYPE
    SYNTAX      EntityIndex
    MAX-ACCESS  read-only
    STATUS      current
    DESCRIPTION   ""
    ::=  { pathOtnDataEntry 3 }

pathOtnDataRole OBJECT-TYPE
    SYNTAX      FspR7CpRole
    MAX-ACCESS  read-only
    STATUS      current
    DESCRIPTION   ""
    ::=  { pathOtnDataEntry 4 }

pathElementOtnDataTable OBJECT-TYPE
    SYNTAX      SEQUENCE OF PathElementOtnDataEntry
    MAX-ACCESS  not-accessible
    STATUS      current
    DESCRIPTION   ""
    ::=  { controlPlaneConfigAndStatus 66 }

pathElementOtnDataEntry OBJECT-TYPE
    SYNTAX      PathElementOtnDataEntry
    MAX-ACCESS  not-accessible
    STATUS      current
    DESCRIPTION   ""
    INDEX       {
                  controlPlaneOtnEntityIndex
                }
    ::=  { pathElementOtnDataTable 1 }

PathElementOtnDataEntry ::=  SEQUENCE
  { pathElementOtnDataPathId SnmpAdminString,
    pathElementOtnDataSequenceNumber Unsigned32,
    pathElementOtnDataPathType FspR7CpPathType,
    pathElementOtnDataTrafficEngineeringType FspR7CpTEType,
    pathElementOtnDataLifIp IpAddress,
    pathElementOtnDataNodeIp IpAddress,
    pathElementOtnDataNodeIpMonitor IpAddress,
    pathElementOtnDataTid SnmpAdminString,
    pathElementOtnDataTidMonitor SnmpAdminString,
    pathElementOtnDataLogicalInterfaceId Unsigned32,
    pathElementOtnDataTie FspR7CpTie,
    pathElementOtnDataUpTributaryODTUType FspR7OdtuType,
    pathElementOtnDataDownTributaryODTUType FspR7OdtuType,
    pathElementOtnDataUpTributaryPort SnmpAdminString,
    pathElementOtnDataDownTributaryPort SnmpAdminString,
    pathElementOtnDataUpTributarySlot SnmpAdminString,
    pathElementOtnDataDownTributarySlot SnmpAdminString,
    pathElementOtnDataUpTributaryTSMethod FspR7ManualAuto,
    pathElementOtnDataDownTributaryTSMethod FspR7ManualAuto,
    pathElementOtnDataDownTribSlotStage2 SnmpAdminString,
    pathElementOtnDataUpTribSlotStage2 SnmpAdminString }

pathElementOtnDataPathId OBJECT-TYPE
    SYNTAX      SnmpAdminString
    MAX-ACCESS  read-only
    STATUS      current
    DESCRIPTION   ""
    ::=  { pathElementOtnDataEntry 1 }

pathElementOtnDataSequenceNumber OBJECT-TYPE
    SYNTAX      Unsigned32
    MAX-ACCESS  read-only
    STATUS      current
    DESCRIPTION   ""
    ::=  { pathElementOtnDataEntry 2 }

pathElementOtnDataPathType OBJECT-TYPE
    SYNTAX      FspR7CpPathType
    MAX-ACCESS  read-only
    STATUS      current
    DESCRIPTION   ""
    ::=  { pathElementOtnDataEntry 3 }

pathElementOtnDataTrafficEngineeringType OBJECT-TYPE
    SYNTAX      FspR7CpTEType
    MAX-ACCESS  read-only
    STATUS      current
    DESCRIPTION   ""
    ::=  { pathElementOtnDataEntry 4 }

pathElementOtnDataLifIp OBJECT-TYPE
    SYNTAX      IpAddress
    MAX-ACCESS  read-only
    STATUS      current
    DESCRIPTION   ""
    ::=  { pathElementOtnDataEntry 5 }

pathElementOtnDataNodeIp OBJECT-TYPE
    SYNTAX      IpAddress
    MAX-ACCESS  read-only
    STATUS      current
    DESCRIPTION   ""
    ::=  { pathElementOtnDataEntry 6 }

pathElementOtnDataNodeIpMonitor OBJECT-TYPE
    SYNTAX      IpAddress
    MAX-ACCESS  read-only
    STATUS      current
    DESCRIPTION   ""
    ::=  { pathElementOtnDataEntry 7 }

pathElementOtnDataTid OBJECT-TYPE
    SYNTAX      SnmpAdminString
    MAX-ACCESS  read-only
    STATUS      current
    DESCRIPTION   ""
    ::=  { pathElementOtnDataEntry 8 }

pathElementOtnDataTidMonitor OBJECT-TYPE
    SYNTAX      SnmpAdminString
    MAX-ACCESS  read-only
    STATUS      current
    DESCRIPTION   ""
    ::=  { pathElementOtnDataEntry 9 }

pathElementOtnDataLogicalInterfaceId OBJECT-TYPE
    SYNTAX      Unsigned32
    MAX-ACCESS  read-only
    STATUS      current
    DESCRIPTION   ""
    ::=  { pathElementOtnDataEntry 10 }

pathElementOtnDataTie OBJECT-TYPE
    SYNTAX      FspR7CpTie
    MAX-ACCESS  read-only
    STATUS      current
    DESCRIPTION   ""
    ::=  { pathElementOtnDataEntry 11 }

pathElementOtnDataUpTributaryODTUType OBJECT-TYPE
    SYNTAX      FspR7OdtuType
    MAX-ACCESS  read-write
    STATUS      current
    DESCRIPTION   ""
    ::=  { pathElementOtnDataEntry 12 }

pathElementOtnDataDownTributaryODTUType OBJECT-TYPE
    SYNTAX      FspR7OdtuType
    MAX-ACCESS  read-write
    STATUS      current
    DESCRIPTION   ""
    ::=  { pathElementOtnDataEntry 13 }

pathElementOtnDataUpTributaryPort OBJECT-TYPE
    SYNTAX      SnmpAdminString
    MAX-ACCESS  read-write
    STATUS      current
    DESCRIPTION   ""
    ::=  { pathElementOtnDataEntry 14 }

pathElementOtnDataDownTributaryPort OBJECT-TYPE
    SYNTAX      SnmpAdminString
    MAX-ACCESS  read-write
    STATUS      current
    DESCRIPTION   ""
    ::=  { pathElementOtnDataEntry 15 }

pathElementOtnDataUpTributarySlot OBJECT-TYPE
    SYNTAX      SnmpAdminString
    MAX-ACCESS  read-write
    STATUS      current
    DESCRIPTION   ""
    ::=  { pathElementOtnDataEntry 16 }

pathElementOtnDataDownTributarySlot OBJECT-TYPE
    SYNTAX      SnmpAdminString
    MAX-ACCESS  read-write
    STATUS      current
    DESCRIPTION   ""
    ::=  { pathElementOtnDataEntry 17 }

pathElementOtnDataUpTributaryTSMethod OBJECT-TYPE
    SYNTAX      FspR7ManualAuto
    MAX-ACCESS  read-write
    STATUS      current
    DESCRIPTION   ""
    ::=  { pathElementOtnDataEntry 18 }

pathElementOtnDataDownTributaryTSMethod OBJECT-TYPE
    SYNTAX      FspR7ManualAuto
    MAX-ACCESS  read-write
    STATUS      current
    DESCRIPTION   ""
    ::=  { pathElementOtnDataEntry 19 }

pathElementOtnDataDownTribSlotStage2 OBJECT-TYPE
    SYNTAX      SnmpAdminString
    MAX-ACCESS  read-only
    STATUS      current
    DESCRIPTION
        "Downstream Tributary Slot (TRMT) - Stage2" 
    ::=  { pathElementOtnDataEntry 20 }

pathElementOtnDataUpTribSlotStage2 OBJECT-TYPE
    SYNTAX      SnmpAdminString
    MAX-ACCESS  read-only
    STATUS      current
    DESCRIPTION
        "Upstream Tributary Slot (RCV) - Stage2" 
    ::=  { pathElementOtnDataEntry 21 }

teUnnumLinkOtnDataTable OBJECT-TYPE
    SYNTAX      SEQUENCE OF TeUnnumLinkOtnDataEntry
    MAX-ACCESS  not-accessible
    STATUS      current
    DESCRIPTION   ""
    ::=  { controlPlaneConfigAndStatus 67 }

teUnnumLinkOtnDataEntry OBJECT-TYPE
    SYNTAX      TeUnnumLinkOtnDataEntry
    MAX-ACCESS  not-accessible
    STATUS      current
    DESCRIPTION   ""
    INDEX       {
                  teRouterDataIp,
                  teUnnumLinkOtnDataNumber
                }
    ::=  { teUnnumLinkOtnDataTable 1 }

TeUnnumLinkOtnDataEntry ::=  SEQUENCE
  { teUnnumLinkOtnDataNumber Unsigned32,
    teUnnumLinkOtnDataNodeIp IpAddress,
    teUnnumLinkOtnDataNodeTid SnmpAdminString,
    teUnnumLinkOtnDataTeLinkId Unsigned32,
    teUnnumLinkOtnDataPhysicalLink Unsigned32,
    teUnnumLinkOtnDataSynchronization FspR7YesNo,
    teUnnumLinkOtnDataDiscarded FspR7YesNo,
    teUnnumLinkOtnDataFendNodeIp IpAddress,
    teUnnumLinkOtnDataFendTeLinkId Unsigned32,
    teUnnumLinkOtnDataInfo SnmpAdminString }

teUnnumLinkOtnDataNumber OBJECT-TYPE
    SYNTAX      Unsigned32
    MAX-ACCESS  not-accessible
    STATUS      current
    DESCRIPTION   ""
    ::=  { teUnnumLinkOtnDataEntry 1 }

teUnnumLinkOtnDataNodeIp OBJECT-TYPE
    SYNTAX      IpAddress
    MAX-ACCESS  read-only
    STATUS      current
    DESCRIPTION   ""
    ::=  { teUnnumLinkOtnDataEntry 2 }

teUnnumLinkOtnDataNodeTid OBJECT-TYPE
    SYNTAX      SnmpAdminString
    MAX-ACCESS  read-only
    STATUS      current
    DESCRIPTION   ""
    ::=  { teUnnumLinkOtnDataEntry 3 }

teUnnumLinkOtnDataTeLinkId OBJECT-TYPE
    SYNTAX      Unsigned32
    MAX-ACCESS  read-only
    STATUS      current
    DESCRIPTION   ""
    ::=  { teUnnumLinkOtnDataEntry 4 }

teUnnumLinkOtnDataPhysicalLink OBJECT-TYPE
    SYNTAX      Unsigned32
    MAX-ACCESS  read-only
    STATUS      current
    DESCRIPTION   ""
    ::=  { teUnnumLinkOtnDataEntry 5 }

teUnnumLinkOtnDataSynchronization OBJECT-TYPE
    SYNTAX      FspR7YesNo
    MAX-ACCESS  read-only
    STATUS      current
    DESCRIPTION   ""
    ::=  { teUnnumLinkOtnDataEntry 6 }

teUnnumLinkOtnDataDiscarded OBJECT-TYPE
    SYNTAX      FspR7YesNo
    MAX-ACCESS  read-only
    STATUS      current
    DESCRIPTION   ""
    ::=  { teUnnumLinkOtnDataEntry 7 }

teUnnumLinkOtnDataFendNodeIp OBJECT-TYPE
    SYNTAX      IpAddress
    MAX-ACCESS  read-only
    STATUS      current
    DESCRIPTION   ""
    ::=  { teUnnumLinkOtnDataEntry 8 }

teUnnumLinkOtnDataFendTeLinkId OBJECT-TYPE
    SYNTAX      Unsigned32
    MAX-ACCESS  read-only
    STATUS      current
    DESCRIPTION   ""
    ::=  { teUnnumLinkOtnDataEntry 9 }

teUnnumLinkOtnDataInfo OBJECT-TYPE
    SYNTAX      SnmpAdminString
    MAX-ACCESS  read-only
    STATUS      current
    DESCRIPTION   ""
    ::=  { teUnnumLinkOtnDataEntry 10 }

teNumLinkOtnDataTable OBJECT-TYPE
    SYNTAX      SEQUENCE OF TeNumLinkOtnDataEntry
    MAX-ACCESS  not-accessible
    STATUS      current
    DESCRIPTION   ""
    ::=  { controlPlaneConfigAndStatus 68 }

teNumLinkOtnDataEntry OBJECT-TYPE
    SYNTAX      TeNumLinkOtnDataEntry
    MAX-ACCESS  not-accessible
    STATUS      current
    DESCRIPTION   ""
    INDEX       {
                  teRouterDataIp
                }
    ::=  { teNumLinkOtnDataTable 1 }

TeNumLinkOtnDataEntry ::=  SEQUENCE
  { teNumLinkOtnDataNodeIp IpAddress,
    teNumLinkOtnDataNodeTid SnmpAdminString,
    teNumLinkOtnDataTeLinkIp IpAddress,
    teNumLinkOtnDataPhysicalLink Unsigned32,
    teNumLinkOtnDataSynchronization FspR7YesNo,
    teNumLinkOtnDataDiscarded FspR7YesNo,
    teNumLinkOtnDataFendNodeIp IpAddress,
    teNumLinkOtnDataFendTeLinkIp IpAddress,
    teNumLinkOtnDataInfo SnmpAdminString }

teNumLinkOtnDataNodeIp OBJECT-TYPE
    SYNTAX      IpAddress
    MAX-ACCESS  read-only
    STATUS      current
    DESCRIPTION   ""
    ::=  { teNumLinkOtnDataEntry 1 }

teNumLinkOtnDataNodeTid OBJECT-TYPE
    SYNTAX      SnmpAdminString
    MAX-ACCESS  read-only
    STATUS      current
    DESCRIPTION   ""
    ::=  { teNumLinkOtnDataEntry 2 }

teNumLinkOtnDataTeLinkIp OBJECT-TYPE
    SYNTAX      IpAddress
    MAX-ACCESS  read-only
    STATUS      current
    DESCRIPTION   ""
    ::=  { teNumLinkOtnDataEntry 3 }

teNumLinkOtnDataPhysicalLink OBJECT-TYPE
    SYNTAX      Unsigned32
    MAX-ACCESS  read-only
    STATUS      current
    DESCRIPTION   ""
    ::=  { teNumLinkOtnDataEntry 4 }

teNumLinkOtnDataSynchronization OBJECT-TYPE
    SYNTAX      FspR7YesNo
    MAX-ACCESS  read-only
    STATUS      current
    DESCRIPTION   ""
    ::=  { teNumLinkOtnDataEntry 5 }

teNumLinkOtnDataDiscarded OBJECT-TYPE
    SYNTAX      FspR7YesNo
    MAX-ACCESS  read-only
    STATUS      current
    DESCRIPTION   ""
    ::=  { teNumLinkOtnDataEntry 6 }

teNumLinkOtnDataFendNodeIp OBJECT-TYPE
    SYNTAX      IpAddress
    MAX-ACCESS  read-only
    STATUS      current
    DESCRIPTION   ""
    ::=  { teNumLinkOtnDataEntry 7 }

teNumLinkOtnDataFendTeLinkIp OBJECT-TYPE
    SYNTAX      IpAddress
    MAX-ACCESS  read-only
    STATUS      current
    DESCRIPTION   ""
    ::=  { teNumLinkOtnDataEntry 8 }

teNumLinkOtnDataInfo OBJECT-TYPE
    SYNTAX      SnmpAdminString
    MAX-ACCESS  read-only
    STATUS      current
    DESCRIPTION   ""
    ::=  { teNumLinkOtnDataEntry 9 }

inventoryCpWdmDownPointerTable OBJECT-TYPE
    SYNTAX      SEQUENCE OF InventoryCpWdmDownPointerEntry
    MAX-ACCESS  not-accessible
    STATUS      current
    DESCRIPTION   ""
    ::=  { controlPlaneConfigAndStatus 69 }

inventoryCpWdmDownPointerEntry OBJECT-TYPE
    SYNTAX      InventoryCpWdmDownPointerEntry
    MAX-ACCESS  not-accessible
    STATUS      current
    DESCRIPTION   ""
    INDEX       {
                  controlPlaneWdmEntityIndex,
                  inventoryCpWdmDownPointerNumber
                }
    ::=  { inventoryCpWdmDownPointerTable 1 }

InventoryCpWdmDownPointerEntry ::=  SEQUENCE
  { inventoryCpWdmDownPointerNumber EntityIndex,
    inventoryCpWdmDownPointerResources RowPointer,
    inventoryCpWdmDownPointerFacilities RowPointer,
    inventoryCpWdmDownPointerPhysTermPoints RowPointer }

inventoryCpWdmDownPointerNumber OBJECT-TYPE
    SYNTAX      EntityIndex
    MAX-ACCESS  not-accessible
    STATUS      current
    DESCRIPTION   ""
    ::=  { inventoryCpWdmDownPointerEntry 1 }

inventoryCpWdmDownPointerResources OBJECT-TYPE
    SYNTAX      RowPointer
    MAX-ACCESS  read-only
    STATUS      current
    DESCRIPTION   ""
    ::=  { inventoryCpWdmDownPointerEntry 2 }

inventoryCpWdmDownPointerFacilities OBJECT-TYPE
    SYNTAX      RowPointer
    MAX-ACCESS  read-only
    STATUS      current
    DESCRIPTION   ""
    ::=  { inventoryCpWdmDownPointerEntry 3 }

inventoryCpWdmDownPointerPhysTermPoints OBJECT-TYPE
    SYNTAX      RowPointer
    MAX-ACCESS  read-only
    STATUS      current
    DESCRIPTION   ""
    ::=  { inventoryCpWdmDownPointerEntry 4 }

inventoryCpWdmUpPointerTable OBJECT-TYPE
    SYNTAX      SEQUENCE OF InventoryCpWdmUpPointerEntry
    MAX-ACCESS  not-accessible
    STATUS      current
    DESCRIPTION   ""
    ::=  { controlPlaneConfigAndStatus 70 }

inventoryCpWdmUpPointerEntry OBJECT-TYPE
    SYNTAX      InventoryCpWdmUpPointerEntry
    MAX-ACCESS  not-accessible
    STATUS      current
    DESCRIPTION   ""
    INDEX       {
                  controlPlaneWdmEntityIndex,
                  inventoryCpWdmUpPointerNumber
                }
    ::=  { inventoryCpWdmUpPointerTable 1 }

InventoryCpWdmUpPointerEntry ::=  SEQUENCE
  { inventoryCpWdmUpPointerNumber EntityIndex,
    inventoryCpWdmUpPointerResources RowPointer,
    inventoryCpWdmUpPointerFacilities RowPointer,
    inventoryCpWdmUpPointerPhysTermPoints RowPointer }

inventoryCpWdmUpPointerNumber OBJECT-TYPE
    SYNTAX      EntityIndex
    MAX-ACCESS  not-accessible
    STATUS      current
    DESCRIPTION   ""
    ::=  { inventoryCpWdmUpPointerEntry 1 }

inventoryCpWdmUpPointerResources OBJECT-TYPE
    SYNTAX      RowPointer
    MAX-ACCESS  read-only
    STATUS      current
    DESCRIPTION   ""
    ::=  { inventoryCpWdmUpPointerEntry 2 }

inventoryCpWdmUpPointerFacilities OBJECT-TYPE
    SYNTAX      RowPointer
    MAX-ACCESS  read-only
    STATUS      current
    DESCRIPTION   ""
    ::=  { inventoryCpWdmUpPointerEntry 3 }

inventoryCpWdmUpPointerPhysTermPoints OBJECT-TYPE
    SYNTAX      RowPointer
    MAX-ACCESS  read-only
    STATUS      current
    DESCRIPTION   ""
    ::=  { inventoryCpWdmUpPointerEntry 4 }

inventoryCpEthDownPointerTable OBJECT-TYPE
    SYNTAX      SEQUENCE OF InventoryCpEthDownPointerEntry
    MAX-ACCESS  not-accessible
    STATUS      current
    DESCRIPTION   "Does not show flow entities as facilities on connection.
         inventoryCpEthDownFlowDataTable is a extension of the table. It contains only
         flow entities as a facility on connectioncon"
    ::=  { controlPlaneConfigAndStatus 71 }

inventoryCpEthDownPointerEntry OBJECT-TYPE
    SYNTAX      InventoryCpEthDownPointerEntry
    MAX-ACCESS  not-accessible
    STATUS      current
    DESCRIPTION   ""
    INDEX       {
                  controlPlaneEthEntityIndex,
                  inventoryCpEthDownPointerNumber
                }
    ::=  { inventoryCpEthDownPointerTable 1 }

InventoryCpEthDownPointerEntry ::=  SEQUENCE
  { inventoryCpEthDownPointerNumber EntityIndex,
    inventoryCpEthDownPointerResources RowPointer,
    inventoryCpEthDownPointerFacilities RowPointer }

inventoryCpEthDownPointerNumber OBJECT-TYPE
    SYNTAX      EntityIndex
    MAX-ACCESS  not-accessible
    STATUS      current
    DESCRIPTION   ""
    ::=  { inventoryCpEthDownPointerEntry 1 }

inventoryCpEthDownPointerResources OBJECT-TYPE
    SYNTAX      RowPointer
    MAX-ACCESS  read-only
    STATUS      current
    DESCRIPTION   ""
    ::=  { inventoryCpEthDownPointerEntry 2 }

inventoryCpEthDownPointerFacilities OBJECT-TYPE
    SYNTAX      RowPointer
    MAX-ACCESS  read-only
    STATUS      current
    DESCRIPTION   ""
    ::=  { inventoryCpEthDownPointerEntry 3 }

inventoryCpEthUpPointerTable OBJECT-TYPE
    SYNTAX      SEQUENCE OF InventoryCpEthUpPointerEntry
    MAX-ACCESS  not-accessible
    STATUS      current
    DESCRIPTION   "Does not show flow entities as facilities on connection.
         inventoryCpEthDownFlowUpTable is a extension of the table. It contains only
         flow entities as a facility on connectioncon"
    ::=  { controlPlaneConfigAndStatus 72 }

inventoryCpEthUpPointerEntry OBJECT-TYPE
    SYNTAX      InventoryCpEthUpPointerEntry
    MAX-ACCESS  not-accessible
    STATUS      current
    DESCRIPTION   ""
    INDEX       {
                  controlPlaneEthEntityIndex,
                  inventoryCpEthUpPointerNumber
                }
    ::=  { inventoryCpEthUpPointerTable 1 }

InventoryCpEthUpPointerEntry ::=  SEQUENCE
  { inventoryCpEthUpPointerNumber EntityIndex,
    inventoryCpEthUpPointerResources RowPointer,
    inventoryCpEthUpPointerFacilities RowPointer }

inventoryCpEthUpPointerNumber OBJECT-TYPE
    SYNTAX      EntityIndex
    MAX-ACCESS  not-accessible
    STATUS      current
    DESCRIPTION   ""
    ::=  { inventoryCpEthUpPointerEntry 1 }

inventoryCpEthUpPointerResources OBJECT-TYPE
    SYNTAX      RowPointer
    MAX-ACCESS  read-only
    STATUS      current
    DESCRIPTION   ""
    ::=  { inventoryCpEthUpPointerEntry 2 }

inventoryCpEthUpPointerFacilities OBJECT-TYPE
    SYNTAX      RowPointer
    MAX-ACCESS  read-only
    STATUS      current
    DESCRIPTION   ""
    ::=  { inventoryCpEthUpPointerEntry 3 }

inventoryCpOtnDownPointerTable OBJECT-TYPE
    SYNTAX      SEQUENCE OF InventoryCpOtnDownPointerEntry
    MAX-ACCESS  not-accessible
    STATUS      current
    DESCRIPTION   ""
    ::=  { controlPlaneConfigAndStatus 73 }

inventoryCpOtnDownPointerEntry OBJECT-TYPE
    SYNTAX      InventoryCpOtnDownPointerEntry
    MAX-ACCESS  not-accessible
    STATUS      current
    DESCRIPTION   ""
    INDEX       {
                  controlPlaneOtnEntityIndex,
                  inventoryCpOtnDownPointerNumber
                }
    ::=  { inventoryCpOtnDownPointerTable 1 }

InventoryCpOtnDownPointerEntry ::=  SEQUENCE
  { inventoryCpOtnDownPointerNumber EntityIndex,
    inventoryCpOtnDownPointerResources RowPointer,
    inventoryCpOtnDownPointerFacilities RowPointer,
    inventoryCpOtnDownPointerPhysTermPoints RowPointer }

inventoryCpOtnDownPointerNumber OBJECT-TYPE
    SYNTAX      EntityIndex
    MAX-ACCESS  not-accessible
    STATUS      current
    DESCRIPTION   ""
    ::=  { inventoryCpOtnDownPointerEntry 1 }

inventoryCpOtnDownPointerResources OBJECT-TYPE
    SYNTAX      RowPointer
    MAX-ACCESS  read-only
    STATUS      current
    DESCRIPTION   ""
    ::=  { inventoryCpOtnDownPointerEntry 2 }

inventoryCpOtnDownPointerFacilities OBJECT-TYPE
    SYNTAX      RowPointer
    MAX-ACCESS  read-only
    STATUS      current
    DESCRIPTION   ""
    ::=  { inventoryCpOtnDownPointerEntry 3 }

inventoryCpOtnDownPointerPhysTermPoints OBJECT-TYPE
    SYNTAX      RowPointer
    MAX-ACCESS  read-only
    STATUS      current
    DESCRIPTION   ""
    ::=  { inventoryCpOtnDownPointerEntry 4 }

inventoryCpOtnUpPointerTable OBJECT-TYPE
    SYNTAX      SEQUENCE OF InventoryCpOtnUpPointerEntry
    MAX-ACCESS  not-accessible
    STATUS      current
    DESCRIPTION   ""
    ::=  { controlPlaneConfigAndStatus 74 }

inventoryCpOtnUpPointerEntry OBJECT-TYPE
    SYNTAX      InventoryCpOtnUpPointerEntry
    MAX-ACCESS  not-accessible
    STATUS      current
    DESCRIPTION   ""
    INDEX       {
                  controlPlaneOtnEntityIndex,
                  inventoryCpOtnUpPointerNumber
                }
    ::=  { inventoryCpOtnUpPointerTable 1 }

InventoryCpOtnUpPointerEntry ::=  SEQUENCE
  { inventoryCpOtnUpPointerNumber EntityIndex,
    inventoryCpOtnUpPointerResources RowPointer,
    inventoryCpOtnUpPointerFacilities RowPointer,
    inventoryCpOtnUpPointerPhysicalTermPoints RowPointer }

inventoryCpOtnUpPointerNumber OBJECT-TYPE
    SYNTAX      EntityIndex
    MAX-ACCESS  not-accessible
    STATUS      current
    DESCRIPTION   ""
    ::=  { inventoryCpOtnUpPointerEntry 1 }

inventoryCpOtnUpPointerResources OBJECT-TYPE
    SYNTAX      RowPointer
    MAX-ACCESS  read-only
    STATUS      current
    DESCRIPTION   ""
    ::=  { inventoryCpOtnUpPointerEntry 2 }

inventoryCpOtnUpPointerFacilities OBJECT-TYPE
    SYNTAX      RowPointer
    MAX-ACCESS  read-only
    STATUS      current
    DESCRIPTION   ""
    ::=  { inventoryCpOtnUpPointerEntry 3 }

inventoryCpOtnUpPointerPhysicalTermPoints OBJECT-TYPE
    SYNTAX      RowPointer
    MAX-ACCESS  read-only
    STATUS      current
    DESCRIPTION   ""
    ::=  { inventoryCpOtnUpPointerEntry 4 }

diversityPathDataTable OBJECT-TYPE
    SYNTAX      SEQUENCE OF DiversityPathDataEntry
    MAX-ACCESS  not-accessible
    STATUS      current
    DESCRIPTION   ""
    ::=  { controlPlaneConfigAndStatus 75 }

diversityPathDataEntry OBJECT-TYPE
    SYNTAX      DiversityPathDataEntry
    MAX-ACCESS  not-accessible
    STATUS      current
    DESCRIPTION   ""
    INDEX       {
                  deployProvDiversityPathIndex
                }
    ::=  { diversityPathDataTable 1 }

DiversityPathDataEntry ::=  SEQUENCE
  { diversityPathDataFromTid SnmpAdminString,
    diversityPathDataToTid SnmpAdminString }

diversityPathDataFromTid OBJECT-TYPE
    SYNTAX      SnmpAdminString
    MAX-ACCESS  read-write
    STATUS      current
    DESCRIPTION
        "Source Target ID" 
    ::=  { diversityPathDataEntry 1 }

diversityPathDataToTid OBJECT-TYPE
    SYNTAX      SnmpAdminString
    MAX-ACCESS  read-write
    STATUS      current
    DESCRIPTION
        "Destination Target ID" 
    ::=  { diversityPathDataEntry 2 }

deployProvShelfTable OBJECT-TYPE
    SYNTAX      SEQUENCE OF DeployProvShelfEntry
    MAX-ACCESS  not-accessible
    STATUS      current
    DESCRIPTION   "Contains entries for provisioning of shelfs."
    ::=  { shelfDeployProv 1 }

deployProvShelfEntry OBJECT-TYPE
    SYNTAX      DeployProvShelfEntry
    MAX-ACCESS  not-accessible
    STATUS      current
    DESCRIPTION   "All shelves which are provisioned(or during deployProv)
         will have an entry in this table."
    INDEX       {
                  entityIndex
                }
    ::=  { deployProvShelfTable 1 }

DeployProvShelfEntry ::=  SEQUENCE
  { deployProvShelfRowStatus RowStatus,
    deployProvShelfForceDestroy FspR7ForcedStatus,
    deployProvShelfType FspR7EquipmentType,
    deployProvShelfAdmin FspR7AdminState,
    deployProvShelfSupply FspR7SupplyType,
    deployProvShelfBand FspR7OpticalBand,
    deployProvShelfPsuOutputPower FspR7PsuOutputPower }

deployProvShelfRowStatus OBJECT-TYPE
    SYNTAX      RowStatus
    MAX-ACCESS  read-write
    STATUS      current
    DESCRIPTION   "This object is used to create, or delete a row in this table.
         To start process of creating a new shelf, this object is initially
         set to 'createAndWait'. After this action the state of this object
         becomes 'notReady'. This object stays in this state until all required
         objects are not set. Objects which must be set are indicated by special
         objects with capabilities(provisioningShelfTypeCap -> provisioningShelfType,
         provisioningShelfAdminCap -> provisioningShelfAdmin). If specjal object
         exist, the indicated object have to be set by one of values specified in
         special object. If all required objects are set, state of this object
         becomes 'notInService'. To create a new shelf, this object have to be set
         to 'active'."
    ::=  { deployProvShelfEntry 1 }

deployProvShelfForceDestroy OBJECT-TYPE
    SYNTAX      FspR7ForcedStatus
    MAX-ACCESS  read-write
    STATUS      current
    DESCRIPTION
        "Forced Destroy" 
    ::=  { deployProvShelfEntry 2 }

deployProvShelfType OBJECT-TYPE
    SYNTAX      FspR7EquipmentType
    MAX-ACCESS  read-write
    STATUS      current
    DESCRIPTION   "The type of Shelf determines uniquely the number and allowed types of
         the provisionable dependent entities (modules)."
    ::=  { deployProvShelfEntry 3 }

deployProvShelfAdmin OBJECT-TYPE
    SYNTAX      FspR7AdminState
    MAX-ACCESS  read-write
    STATUS      current
    DESCRIPTION   "The Adminstrative State will be displayed in the GUI with full name values;
         it will be displayed differently in TL1 syntax according to TL1 display rules.
         The transaction into the UAS state requires a special destroy/delete function."
    ::=  { deployProvShelfEntry 4 }

deployProvShelfSupply OBJECT-TYPE
    SYNTAX      FspR7SupplyType
    MAX-ACCESS  read-write
    STATUS      current
    DESCRIPTION
        "The kind of power supply - provisioned value" 
    ::=  { deployProvShelfEntry 5 }

deployProvShelfBand OBJECT-TYPE
    SYNTAX      FspR7OpticalBand
    MAX-ACCESS  read-write
    STATUS      current
    DESCRIPTION   "The optical band of the passive shelf."
    ::=  { deployProvShelfEntry 6 }

deployProvShelfPsuOutputPower OBJECT-TYPE
    SYNTAX      FspR7PsuOutputPower
    MAX-ACCESS  read-write
    STATUS      current
    DESCRIPTION
        "Maximum PSU Output Power" 
    ::=  { deployProvShelfEntry 7 }

deployProvShelfCapTable OBJECT-TYPE
    SYNTAX      SEQUENCE OF DeployProvShelfCapEntry
    MAX-ACCESS  not-accessible
    STATUS      current
    DESCRIPTION   "Contains entries for provisioning of shelfs."
    ::=  { shelfDeployProv 2  }

deployProvShelfCapEntry OBJECT-TYPE
    SYNTAX      DeployProvShelfCapEntry
    MAX-ACCESS  not-accessible
    STATUS      current
    DESCRIPTION   "All shelves which are provisioned(or during deployProv)
         will have an entry in this table."
    INDEX       { entityIndex }
    ::=  { deployProvShelfCapTable 1 }

DeployProvShelfCapEntry ::=  SEQUENCE
  { deployProvShelfCapRowStatus FspR7RowStatusCaps,
    deployProvShelfCapForceDestroy FspR7ForcedStatusCaps,
    deployProvShelfCapType FspR7EquipmentTypeCaps,
    deployProvShelfCapAdmin FspR7AdminStateCaps,
    deployProvShelfCapSupply FspR7SupplyTypeCaps,
    deployProvShelfCapBand FspR7OpticalBandCaps,
    deployProvShelfCapPsuOutputPower FspR7PsuOutputPowerCaps }

deployProvShelfCapRowStatus OBJECT-TYPE
    SYNTAX      FspR7RowStatusCaps
    MAX-ACCESS  read-only
    STATUS      current
    DESCRIPTION   "This object is used to create, or delete a row in this table.
         To start process of creating a new shelf, this object is initially
         set to 'createAndWait'. After this action the state of this object
         becomes 'notReady'. This object stays in this state until all required
         objects are not set. Objects which must be set are indicated by special
         objects with capabilities(provisioningShelfTypeCap -> provisioningShelfType,
         provisioningShelfAdminCap -> provisioningShelfAdmin). If specjal object
         exist, the indicated object have to be set by one of values specified in
         special object. If all required objects are set, state of this object
         becomes 'notInService'. To create a new shelf, this object have to be set
         to 'active'."
    ::=  { deployProvShelfCapEntry 1 }

deployProvShelfCapForceDestroy OBJECT-TYPE
    SYNTAX      FspR7ForcedStatusCaps
    MAX-ACCESS  read-only
    STATUS      current
    DESCRIPTION
        "Forced Destroy" 
    ::=  { deployProvShelfCapEntry 2 }

deployProvShelfCapType OBJECT-TYPE
    SYNTAX      FspR7EquipmentTypeCaps
    MAX-ACCESS  read-only
    STATUS      current
    DESCRIPTION   "The type of Shelf determines uniquely the number and allowed types of
         the provisionable dependent entities (modules)."
    ::=  { deployProvShelfCapEntry 3 }

deployProvShelfCapAdmin OBJECT-TYPE
    SYNTAX      FspR7AdminStateCaps
    MAX-ACCESS  read-only
    STATUS      current
    DESCRIPTION   "The Adminstrative State will be displayed in the GUI with full name values;
         it will be displayed differently in TL1 syntax according to TL1 display rules.
         The transaction into the UAS state requires a special destroy/delete function."
    ::=  { deployProvShelfCapEntry 4 }

deployProvShelfCapSupply OBJECT-TYPE
    SYNTAX      FspR7SupplyTypeCaps
    MAX-ACCESS  read-only
    STATUS      current
    DESCRIPTION
        "The kind of power supply - provisioned value" 
    ::=  { deployProvShelfCapEntry 5 }

deployProvShelfCapBand OBJECT-TYPE
    SYNTAX      FspR7OpticalBandCaps
    MAX-ACCESS  read-only
    STATUS      current
    DESCRIPTION   "The optical band of the passive shelf."
    ::=  { deployProvShelfCapEntry 6 }

deployProvShelfCapPsuOutputPower OBJECT-TYPE
    SYNTAX      FspR7PsuOutputPowerCaps
    MAX-ACCESS  read-only
    STATUS      current
    DESCRIPTION
        "Maximum PSU Output Power" 
    ::=  { deployProvShelfCapEntry 7 }

deployProvShelfDefaultsTable  OBJECT-TYPE
    SYNTAX      SEQUENCE OF DeployProvShelfDefaultsEntry
    MAX-ACCESS  not-accessible
    STATUS      current
    DESCRIPTION   "Contains entries for provisioning of shelfs."
    ::=  { shelfDeployProv 3  }

deployProvShelfDefaultsEntry OBJECT-TYPE
    SYNTAX      DeployProvShelfDefaultsEntry
    MAX-ACCESS  not-accessible
    STATUS      current
    DESCRIPTION   "All shelves which are provisioned(or during deployProv)
         will have an entry in this table."
    INDEX       { entityIndex }
    ::=  { deployProvShelfDefaultsTable 1 }

DeployProvShelfDefaultsEntry ::=  SEQUENCE
  { deployProvShelfDefaultsRowStatus RowStatus,
    deployProvShelfDefaultsForceDestroy FspR7ForcedStatus,
    deployProvShelfDefaultsType FspR7EquipmentType,
    deployProvShelfDefaultsAdmin FspR7AdminState,
    deployProvShelfDefaultsSupply FspR7SupplyType,
    deployProvShelfDefaultsBand FspR7OpticalBand,
    deployProvShelfDefaultsPsuOutputPower FspR7PsuOutputPower }

deployProvShelfDefaultsRowStatus OBJECT-TYPE
    SYNTAX      RowStatus
    MAX-ACCESS  read-only
    STATUS      current
    DESCRIPTION   "This object is used to create, or delete a row in this table.
         To start process of creating a new shelf, this object is initially
         set to 'createAndWait'. After this action the state of this object
         becomes 'notReady'. This object stays in this state until all required
         objects are not set. Objects which must be set are indicated by special
         objects with capabilities(provisioningShelfTypeCap -> provisioningShelfType,
         provisioningShelfAdminCap -> provisioningShelfAdmin). If specjal object
         exist, the indicated object have to be set by one of values specified in
         special object. If all required objects are set, state of this object
         becomes 'notInService'. To create a new shelf, this object have to be set
         to 'active'."
    ::=  { deployProvShelfDefaultsEntry 1 }

deployProvShelfDefaultsForceDestroy OBJECT-TYPE
    SYNTAX      FspR7ForcedStatus
    MAX-ACCESS  read-only
    STATUS      current
    DESCRIPTION
        "Forced Destroy" 
    ::=  { deployProvShelfDefaultsEntry 2 }

deployProvShelfDefaultsType OBJECT-TYPE
    SYNTAX      FspR7EquipmentType
    MAX-ACCESS  read-only
    STATUS      current
    DESCRIPTION   "The type of Shelf determines uniquely the number and allowed types of
         the provisionable dependent entities (modules)."
    ::=  { deployProvShelfDefaultsEntry 3 }

deployProvShelfDefaultsAdmin OBJECT-TYPE
    SYNTAX      FspR7AdminState
    MAX-ACCESS  read-only
    STATUS      current
    DESCRIPTION   "The Adminstrative State will be displayed in the GUI with full name values;
         it will be displayed differently in TL1 syntax according to TL1 display rules.
         The transaction into the UAS state requires a special destroy/delete function."
    ::=  { deployProvShelfDefaultsEntry 4 }

deployProvShelfDefaultsSupply OBJECT-TYPE
    SYNTAX      FspR7SupplyType
    MAX-ACCESS  read-only
    STATUS      current
    DESCRIPTION
        "The kind of power supply - provisioned value" 
    ::=  { deployProvShelfDefaultsEntry 5 }

deployProvShelfDefaultsBand OBJECT-TYPE
    SYNTAX      FspR7OpticalBand
    MAX-ACCESS  read-only
    STATUS      current
    DESCRIPTION   "The optical band of the passive shelf."
    ::=  { deployProvShelfDefaultsEntry 6 }

deployProvShelfDefaultsPsuOutputPower OBJECT-TYPE
    SYNTAX      FspR7PsuOutputPower
    MAX-ACCESS  read-only
    STATUS      current
    DESCRIPTION
        "Maximum PSU Output Power" 
    ::=  { deployProvShelfDefaultsEntry 7 }

deployProvModuleTable OBJECT-TYPE
    SYNTAX      SEQUENCE OF DeployProvModuleEntry
    MAX-ACCESS  not-accessible
    STATUS      current
    DESCRIPTION   "Contains entries for provisioning of modules."
    ::=  { moduleDeployProv 1 }

deployProvModuleEntry OBJECT-TYPE
    SYNTAX      DeployProvModuleEntry
    MAX-ACCESS  not-accessible
    STATUS      current
    DESCRIPTION   "All modules which are provisioned(or are during deployProv) will have an entry in this table."
    INDEX       {
                  entityIndex
                }
    ::=  { deployProvModuleTable 1 }

DeployProvModuleEntry ::=  SEQUENCE
  { deployProvModuleRowStatus RowStatus,
    deployProvModuleForceDestroy FspR7ForcedStatus,
    deployProvModuleType FspR7EquipmentType,
    deployProvModuleMode FspR7TransmissionMode,
    deployProvModuleDeploy FspR7DeploymentScenario,
    deployProvModuleChannel FspR7ChannelIdentifier,
    deployProvModuleReach FspR7OpticalInterfaceReach,
    deployProvModuleBand FspR7OpticalBand,
    deployProvModuleSubBand FspR7OpticalSubBand,
    deployProvModuleGroup FspR7OpticalGroup,
    deployProvModuleFiber FspR7OpticalFiberType,
    deployProvModuleEdfaPwrOut FspR7EdfaOutputPowerRating,
    deployProvModuleAdmin FspR7AdminState,
    deployProvModuleSupply FspR7SupplyType,
    deployProvModuleDispersionCompensation FspR7DispersionCompensation,
    deployProvModuleLanAid EntityIndex,
    deployProvModuleSingleFiberLocation FspR7SingleFiberLocation,
    deployProvModulePsuOutputPower FspR7PsuOutputPower,
    deployProvModuleTilt Integer32,
    deployProvModuleGain FspR7Gain,
    deployProvModuleCapabilityLevel FspR7CapInventory,
    deployProvModuleRoadmNumber FspR7RoadmNumber,
    deployProvModuleScrambling FspR7Scrambling,
    deployProvModuleChannelSpacing FspR7ChannelSpacing,
    deployProvModuleLagSysPrio Unsigned32,
    deployProvModuleGainRange FspR7GainRange,
    deployProvModuleEqlzAdmin FspR7EqlzAdminState,
    deployProvModuleChannelsNumber FspR7NumberOfChannels,
    deployProvModuleDCFiberType FspR7DCFiberType,
    deployProvModuleMapping FspR7Mapping,
    deployProvModuleCac FspR7L2CacEnable,
    deployProvModuleChannelSpacingProvision FspR7ChannelSpacing,
    deployProvModuleChannelsProvision FspR7NumberOfChannels,
    deployProvModuleFiberDetect FspR7FiberDetect,
    deployProvModuleTrafficDirection FspR7TrafficDirection,
    deployProvModuleOscUsage FspR7OscUsage }

deployProvModuleRowStatus OBJECT-TYPE
    SYNTAX      RowStatus
    MAX-ACCESS  read-write
    STATUS      current
    DESCRIPTION   "RowStatus"
    ::=  { deployProvModuleEntry 1 }

deployProvModuleForceDestroy OBJECT-TYPE
    SYNTAX      FspR7ForcedStatus
    MAX-ACCESS  read-write
    STATUS      current
    DESCRIPTION
        "Forced Destroy" 
    ::=  { deployProvModuleEntry 2 }

deployProvModuleType OBJECT-TYPE
    SYNTAX      FspR7EquipmentType
    MAX-ACCESS  read-write
    STATUS      current
    DESCRIPTION   "The TYPE of Module."
    ::=  { deployProvModuleEntry 3 }

deployProvModuleMode OBJECT-TYPE
    SYNTAX      FspR7TransmissionMode
    MAX-ACCESS  read-write
    STATUS      current
    DESCRIPTION   "The transmission mode of the module."
    ::=  { deployProvModuleEntry 4 }

deployProvModuleDeploy OBJECT-TYPE
    SYNTAX      FspR7DeploymentScenario
    MAX-ACCESS  read-write
    STATUS      current
    DESCRIPTION   "The deployment scenario of the module."
    ::=  { deployProvModuleEntry 5 }

deployProvModuleChannel OBJECT-TYPE
    SYNTAX      FspR7ChannelIdentifier
    MAX-ACCESS  read-write
    STATUS      current
    DESCRIPTION   "The optical channel."
    ::=  { deployProvModuleEntry 6 }

deployProvModuleReach OBJECT-TYPE
    SYNTAX      FspR7OpticalInterfaceReach
    MAX-ACCESS  read-write
    STATUS      current
    DESCRIPTION   "The optical channel."
    ::=  { deployProvModuleEntry 7 }

deployProvModuleBand OBJECT-TYPE
    SYNTAX      FspR7OpticalBand
    MAX-ACCESS  read-write
    STATUS      current
    DESCRIPTION   "The The optical band of the module."
    ::=  { deployProvModuleEntry 8 }

deployProvModuleSubBand OBJECT-TYPE
    SYNTAX      FspR7OpticalSubBand
    MAX-ACCESS  read-write
    STATUS      current
    DESCRIPTION   "The subband of 16 DWDM channels."
    ::=  { deployProvModuleEntry 9 }

deployProvModuleGroup OBJECT-TYPE
    SYNTAX      FspR7OpticalGroup
    MAX-ACCESS  read-write
    STATUS      current
    DESCRIPTION   "The Group of 4 DWDM channels."
    ::=  { deployProvModuleEntry 10 }

deployProvModuleFiber OBJECT-TYPE
    SYNTAX      FspR7OpticalFiberType
    MAX-ACCESS  read-write
    STATUS      current
    DESCRIPTION   "Fiber type."
    ::=  { deployProvModuleEntry 11 }

deployProvModuleEdfaPwrOut OBJECT-TYPE
    SYNTAX      FspR7EdfaOutputPowerRating
    MAX-ACCESS  read-write
    STATUS      current
    DESCRIPTION
        "Optical Output Power Rating - Provision" 
    ::=  { deployProvModuleEntry 12 }

deployProvModuleAdmin OBJECT-TYPE
    SYNTAX      FspR7AdminState
    MAX-ACCESS  read-write
    STATUS      current
    DESCRIPTION   "The Adminstrative State."
    ::=  { deployProvModuleEntry 13 }

deployProvModuleSupply OBJECT-TYPE
    SYNTAX      FspR7SupplyType
    MAX-ACCESS  read-write
    STATUS      current
    DESCRIPTION
        "The kind of power supply - provisioned value" 
    ::=  { deployProvModuleEntry 14 }

deployProvModuleDispersionCompensation OBJECT-TYPE
    SYNTAX      FspR7DispersionCompensation
    MAX-ACCESS  read-write
    STATUS      current
    DESCRIPTION
        "Dispersion Compensation Value in km of SSMF fiber" 
    ::=  { deployProvModuleEntry 15 }

deployProvModuleLanAid OBJECT-TYPE
    SYNTAX      EntityIndex
    MAX-ACCESS  read-write
    STATUS      current
    DESCRIPTION
        "AID of LAN" 
    ::=  { deployProvModuleEntry 16 }

deployProvModuleSingleFiberLocation OBJECT-TYPE
    SYNTAX      FspR7SingleFiberLocation
    MAX-ACCESS  read-write
    STATUS      current
    DESCRIPTION
        "determines the location (A or B) for Single Fiber applications" 
    ::=  { deployProvModuleEntry 17 }

deployProvModulePsuOutputPower OBJECT-TYPE
    SYNTAX      FspR7PsuOutputPower
    MAX-ACCESS  read-write
    STATUS      current
    DESCRIPTION
        "Maximum PSU Output Power" 
    ::=  { deployProvModuleEntry 18 }

deployProvModuleTilt OBJECT-TYPE
    SYNTAX      Integer32 (-50..0 | -2147483648) 
    UNITS       "0.1 dB"
    MAX-ACCESS  read-write
    STATUS      current
    DESCRIPTION
        "Change of optical channel power in dB over the complete transmission band" 
    ::=  { deployProvModuleEntry 19 }

deployProvModuleGain OBJECT-TYPE
    SYNTAX      FspR7Gain
    MAX-ACCESS  read-write
    STATUS      current
    DESCRIPTION
        "Gain" 
    ::=  { deployProvModuleEntry 20 }

deployProvModuleCapabilityLevel OBJECT-TYPE
    SYNTAX      FspR7CapInventory
    MAX-ACCESS  read-write
    STATUS      current
    DESCRIPTION
        "Capability level provisioned" 
    ::=  { deployProvModuleEntry 21 }

deployProvModuleRoadmNumber OBJECT-TYPE
    SYNTAX      FspR7RoadmNumber
    MAX-ACCESS  read-write
    STATUS      current
    DESCRIPTION
        "Number for ROADM module typically associated with a Network Fiber or Degree" 
    ::=  { deployProvModuleEntry 22 }

deployProvModuleScrambling OBJECT-TYPE
    SYNTAX      FspR7Scrambling
    MAX-ACCESS  read-write
    STATUS      current
    DESCRIPTION   "Virtual Fac. Scrambling"
    ::=  { deployProvModuleEntry 23 }

deployProvModuleChannelSpacing OBJECT-TYPE
    SYNTAX      FspR7ChannelSpacing
    MAX-ACCESS  read-write
    STATUS      current
    DESCRIPTION
        "ITU Grid channel spacing" 
    ::=  { deployProvModuleEntry 24 }

deployProvModuleLagSysPrio OBJECT-TYPE
    SYNTAX      Unsigned32 (0..65535 | 4294967295)
    MAX-ACCESS  read-write
    STATUS      current
    DESCRIPTION
        "Link Aggregation Group Actor System Priority Part of LAG ID" 
    ::=  { deployProvModuleEntry 25 }

deployProvModuleGainRange OBJECT-TYPE
    SYNTAX      FspR7GainRange
    MAX-ACCESS  read-write
    STATUS      current
    DESCRIPTION
        "EDFA gain range to provision" 
    ::=  { deployProvModuleEntry 26 }

deployProvModuleEqlzAdmin OBJECT-TYPE
    SYNTAX      FspR7EqlzAdminState
    MAX-ACCESS  read-write
    STATUS      current
    DESCRIPTION
        "Scheduled Equalization Administration" 
    ::=  { deployProvModuleEntry 27 }

deployProvModuleChannelsNumber OBJECT-TYPE
    SYNTAX      FspR7NumberOfChannels
    MAX-ACCESS  read-write
    STATUS      current
    DESCRIPTION   "Number of channels supported by an entity"
    ::=  { deployProvModuleEntry 28 }

deployProvModuleDCFiberType OBJECT-TYPE
    SYNTAX      FspR7DCFiberType
    MAX-ACCESS  read-write
    STATUS      current
    DESCRIPTION
        "Dispersion Compensation Fibertype" 
    ::=  { deployProvModuleEntry 29 }

deployProvModuleMapping OBJECT-TYPE
    SYNTAX      FspR7Mapping
    MAX-ACCESS  read-write
    STATUS      current
    DESCRIPTION
        "Type of mapping; transparent or framing" 
    ::=  { deployProvModuleEntry 30 }

deployProvModuleCac OBJECT-TYPE
    SYNTAX      FspR7L2CacEnable
    MAX-ACCESS  read-write
    STATUS      current
    DESCRIPTION
        "Enable of CAC" 
    ::=  { deployProvModuleEntry 31 }

deployProvModuleChannelSpacingProvision OBJECT-TYPE
    SYNTAX      FspR7ChannelSpacing
    MAX-ACCESS  read-write
    STATUS      current
    DESCRIPTION
        "Channel Space Provision, reference to CHA-SPC__INVENTORY" 
    ::=  { deployProvModuleEntry 32 }

deployProvModuleChannelsProvision OBJECT-TYPE
    SYNTAX      FspR7NumberOfChannels
    MAX-ACCESS  read-write
    STATUS      current
    DESCRIPTION
        "Number of channels supported by an entity" 
    ::=  { deployProvModuleEntry 33 }

deployProvModuleFiberDetect OBJECT-TYPE
    SYNTAX      FspR7FiberDetect
    MAX-ACCESS  read-write
    STATUS      current
    DESCRIPTION
        "Fiber Detect" 
    ::=  { deployProvModuleEntry 34 }

deployProvModuleTrafficDirection OBJECT-TYPE
    SYNTAX      FspR7TrafficDirection
    MAX-ACCESS  read-write
    STATUS      current
    DESCRIPTION
        "Traffic Direction" 
    ::=  { deployProvModuleEntry 35 }

deployProvModuleOscUsage OBJECT-TYPE
    SYNTAX      FspR7OscUsage
    MAX-ACCESS  read-write
    STATUS      current
    DESCRIPTION
        "Select if and how the OSC is to be used on an amplifier" 
    ::=  { deployProvModuleEntry 36 }

deployProvModuleCapTable OBJECT-TYPE
    SYNTAX      SEQUENCE OF DeployProvModuleCapEntry
    MAX-ACCESS  not-accessible
    STATUS      current
    DESCRIPTION   "Contains entries for provisioning of modules."
    ::=  { moduleDeployProv 2  }

deployProvModuleCapEntry OBJECT-TYPE
    SYNTAX      DeployProvModuleCapEntry
    MAX-ACCESS  not-accessible
    STATUS      current
    DESCRIPTION   "All modules which are provisioned(or are during deployProv) will have an entry in this table."
    INDEX       { entityIndex }
    ::=  { deployProvModuleCapTable 1 }

DeployProvModuleCapEntry ::=  SEQUENCE
  { deployProvModuleCapRowStatus FspR7RowStatusCaps,
    deployProvModuleCapForceDestroy FspR7ForcedStatusCaps,
    deployProvModuleCapType FspR7EquipmentTypeCaps,
    deployProvModuleCapMode FspR7TransmissionModeCaps,
    deployProvModuleCapDeploy FspR7DeploymentScenarioCaps,
    deployProvModuleCapChannel FspR7ChannelIdentifierCaps,
    deployProvModuleCapReach FspR7OpticalInterfaceReachCaps,
    deployProvModuleCapBand FspR7OpticalBandCaps,
    deployProvModuleCapSubBand FspR7OpticalSubBandCaps,
    deployProvModuleCapGroup FspR7OpticalGroupCaps,
    deployProvModuleCapFiber FspR7OpticalFiberTypeCaps,
    deployProvModuleCapEdfaPwrOut FspR7EdfaOutputPowerRatingCaps,
    deployProvModuleCapAdmin FspR7AdminStateCaps,
    deployProvModuleCapSupply FspR7SupplyTypeCaps,
    deployProvModuleCapDispersionCompensation FspR7DispersionCompensationCaps,
    deployProvModuleCapLanAid Integer32,
    deployProvModuleCapSingleFiberLocation FspR7SingleFiberLocationCaps,
    deployProvModuleCapPsuOutputPower FspR7PsuOutputPowerCaps,
    deployProvModuleCapTilt FspR7Integer32Caps,
    deployProvModuleCapGain FspR7GainCaps,
    deployProvModuleCapCapabilityLevel FspR7CapInventoryCaps,
    deployProvModuleCapRoadmNumber FspR7RoadmNumberCaps,
    deployProvModuleCapScrambling FspR7ScramblingCaps,
    deployProvModuleCapChannelSpacing FspR7ChannelSpacingCaps,
    deployProvModuleCapLagSysPrio FspR7Unsigned32Caps,
    deployProvModuleCapGainRange FspR7GainRangeCaps,
    deployProvModuleCapEqlzAdmin FspR7EqlzAdminStateCaps,
    deployProvModuleCapChannelsNumber FspR7NumberOfChannelsCaps,
    deployProvModuleCapDCFiberType FspR7DCFiberTypeCaps,
    deployProvModuleCapMapping FspR7MappingCaps,
    deployProvModuleCapCac FspR7L2CacEnableCaps,
    deployProvModuleCapChannelSpacingProvision FspR7ChannelSpacingCaps,
    deployProvModuleCapChannelsProvision FspR7NumberOfChannelsCaps,
    deployProvModuleCapFiberDetect FspR7FiberDetectCaps,
    deployProvModuleCapTrafficDirection FspR7TrafficDirectionCaps,
    deployProvModuleCapOscUsage FspR7OscUsageCaps }

deployProvModuleCapRowStatus OBJECT-TYPE
    SYNTAX      FspR7RowStatusCaps
    MAX-ACCESS  read-only
    STATUS      current
    DESCRIPTION   "RowStatus"
    ::=  { deployProvModuleCapEntry 1 }

deployProvModuleCapForceDestroy OBJECT-TYPE
    SYNTAX      FspR7ForcedStatusCaps
    MAX-ACCESS  read-only
    STATUS      current
    DESCRIPTION
        "Forced Destroy" 
    ::=  { deployProvModuleCapEntry 2 }

deployProvModuleCapType OBJECT-TYPE
    SYNTAX      FspR7EquipmentTypeCaps
    MAX-ACCESS  read-only
    STATUS      current
    DESCRIPTION   "The TYPE of Module."
    ::=  { deployProvModuleCapEntry 3 }

deployProvModuleCapMode OBJECT-TYPE
    SYNTAX      FspR7TransmissionModeCaps
    MAX-ACCESS  read-only
    STATUS      current
    DESCRIPTION   "The transmission mode of the module."
    ::=  { deployProvModuleCapEntry 4 }

deployProvModuleCapDeploy OBJECT-TYPE
    SYNTAX      FspR7DeploymentScenarioCaps
    MAX-ACCESS  read-only
    STATUS      current
    DESCRIPTION   "The deployment scenario of the module."
    ::=  { deployProvModuleCapEntry 5 }

deployProvModuleCapChannel OBJECT-TYPE
    SYNTAX      FspR7ChannelIdentifierCaps
    MAX-ACCESS  read-only
    STATUS      current
    DESCRIPTION   "The optical channel."
    ::=  { deployProvModuleCapEntry 6 }

deployProvModuleCapReach OBJECT-TYPE
    SYNTAX      FspR7OpticalInterfaceReachCaps
    MAX-ACCESS  read-only
    STATUS      current
    DESCRIPTION   "The optical channel."
    ::=  { deployProvModuleCapEntry 7 }

deployProvModuleCapBand OBJECT-TYPE
    SYNTAX      FspR7OpticalBandCaps
    MAX-ACCESS  read-only
    STATUS      current
    DESCRIPTION   "The The optical band of the module."
    ::=  { deployProvModuleCapEntry 8 }

deployProvModuleCapSubBand OBJECT-TYPE
    SYNTAX      FspR7OpticalSubBandCaps
    MAX-ACCESS  read-only
    STATUS      current
    DESCRIPTION   "The subband of 16 DWDM channels."
    ::=  { deployProvModuleCapEntry 9 }

deployProvModuleCapGroup OBJECT-TYPE
    SYNTAX      FspR7OpticalGroupCaps
    MAX-ACCESS  read-only
    STATUS      current
    DESCRIPTION   "The Group of 4 DWDM channels."
    ::=  { deployProvModuleCapEntry 10 }

deployProvModuleCapFiber OBJECT-TYPE
    SYNTAX      FspR7OpticalFiberTypeCaps
    MAX-ACCESS  read-only
    STATUS      current
    DESCRIPTION   "Fiber type."
    ::=  { deployProvModuleCapEntry 11 }

deployProvModuleCapEdfaPwrOut OBJECT-TYPE
    SYNTAX      FspR7EdfaOutputPowerRatingCaps
    MAX-ACCESS  read-only
    STATUS      current
    DESCRIPTION
        "Optical Output Power Rating - Provision" 
    ::=  { deployProvModuleCapEntry 12 }

deployProvModuleCapAdmin OBJECT-TYPE
    SYNTAX      FspR7AdminStateCaps
    MAX-ACCESS  read-only
    STATUS      current
    DESCRIPTION   "The Adminstrative State."
    ::=  { deployProvModuleCapEntry 13 }

deployProvModuleCapSupply OBJECT-TYPE
    SYNTAX      FspR7SupplyTypeCaps
    MAX-ACCESS  read-only
    STATUS      current
    DESCRIPTION
        "The kind of power supply - provisioned value" 
    ::=  { deployProvModuleCapEntry 14 }

deployProvModuleCapDispersionCompensation OBJECT-TYPE
    SYNTAX      FspR7DispersionCompensationCaps
    MAX-ACCESS  read-only
    STATUS      current
    DESCRIPTION
        "Dispersion Compensation Value in km of SSMF fiber" 
    ::=  { deployProvModuleCapEntry 15 }

deployProvModuleCapLanAid OBJECT-TYPE
    SYNTAX      Integer32
    MAX-ACCESS  read-only
    STATUS      current
    DESCRIPTION
        "AID of LAN" 
    ::=  { deployProvModuleCapEntry 16 }

deployProvModuleCapSingleFiberLocation OBJECT-TYPE
    SYNTAX      FspR7SingleFiberLocationCaps
    MAX-ACCESS  read-only
    STATUS      current
    DESCRIPTION
        "determines the location (A or B) for Single Fiber applications" 
    ::=  { deployProvModuleCapEntry 17 }

deployProvModuleCapPsuOutputPower OBJECT-TYPE
    SYNTAX      FspR7PsuOutputPowerCaps
    MAX-ACCESS  read-only
    STATUS      current
    DESCRIPTION
        "Maximum PSU Output Power" 
    ::=  { deployProvModuleCapEntry 18 }

deployProvModuleCapTilt OBJECT-TYPE
    SYNTAX      FspR7Integer32Caps
    UNITS       "0.1 dB"
    MAX-ACCESS  read-only
    STATUS      current
    DESCRIPTION
        "Change of optical channel power in dB over the complete transmission band" 
    ::=  { deployProvModuleCapEntry 19 }

deployProvModuleCapGain OBJECT-TYPE
    SYNTAX      FspR7GainCaps
    MAX-ACCESS  read-only
    STATUS      current
    DESCRIPTION
        "Gain" 
    ::=  { deployProvModuleCapEntry 20 }

deployProvModuleCapCapabilityLevel OBJECT-TYPE
    SYNTAX      FspR7CapInventoryCaps
    MAX-ACCESS  read-only
    STATUS      current
    DESCRIPTION
        "Capability level provisioned" 
    ::=  { deployProvModuleCapEntry 21 }

deployProvModuleCapRoadmNumber OBJECT-TYPE
    SYNTAX      FspR7RoadmNumberCaps
    MAX-ACCESS  read-only
    STATUS      current
    DESCRIPTION
        "Number for ROADM module typically associated with a Network Fiber or Degree" 
    ::=  { deployProvModuleCapEntry 22 }

deployProvModuleCapScrambling OBJECT-TYPE
    SYNTAX      FspR7ScramblingCaps
    MAX-ACCESS  read-only
    STATUS      current
    DESCRIPTION   "Virtual Fac. Scrambling"
    ::=  { deployProvModuleCapEntry 23 }

deployProvModuleCapChannelSpacing OBJECT-TYPE
    SYNTAX      FspR7ChannelSpacingCaps
    MAX-ACCESS  read-only
    STATUS      current
    DESCRIPTION
        "ITU Grid channel spacing" 
    ::=  { deployProvModuleCapEntry 24 }

deployProvModuleCapLagSysPrio OBJECT-TYPE
    SYNTAX      FspR7Unsigned32Caps
    MAX-ACCESS  read-only
    STATUS      current
    DESCRIPTION
        "Link Aggregation Group Actor System Priority Part of LAG ID" 
    ::=  { deployProvModuleCapEntry 25 }

deployProvModuleCapGainRange OBJECT-TYPE
    SYNTAX      FspR7GainRangeCaps
    MAX-ACCESS  read-only
    STATUS      current
    DESCRIPTION
        "EDFA gain range to provision" 
    ::=  { deployProvModuleCapEntry 26 }

deployProvModuleCapEqlzAdmin OBJECT-TYPE
    SYNTAX      FspR7EqlzAdminStateCaps
    MAX-ACCESS  read-only
    STATUS      current
    DESCRIPTION
        "Scheduled Equalization Administration" 
    ::=  { deployProvModuleCapEntry 27 }

deployProvModuleCapChannelsNumber OBJECT-TYPE
    SYNTAX      FspR7NumberOfChannelsCaps
    MAX-ACCESS  read-only
    STATUS      current
    DESCRIPTION   "Number of channels supported by an entity"
    ::=  { deployProvModuleCapEntry 28 }

deployProvModuleCapDCFiberType OBJECT-TYPE
    SYNTAX      FspR7DCFiberTypeCaps
    MAX-ACCESS  read-only
    STATUS      current
    DESCRIPTION
        "Dispersion Compensation Fibertype" 
    ::=  { deployProvModuleCapEntry 29 }

deployProvModuleCapMapping OBJECT-TYPE
    SYNTAX      FspR7MappingCaps
    MAX-ACCESS  read-only
    STATUS      current
    DESCRIPTION
        "Type of mapping; transparent or framing" 
    ::=  { deployProvModuleCapEntry 30 }

deployProvModuleCapCac OBJECT-TYPE
    SYNTAX      FspR7L2CacEnableCaps
    MAX-ACCESS  read-only
    STATUS      current
    DESCRIPTION
        "Enable of CAC" 
    ::=  { deployProvModuleCapEntry 31 }

deployProvModuleCapChannelSpacingProvision OBJECT-TYPE
    SYNTAX      FspR7ChannelSpacingCaps
    MAX-ACCESS  read-only
    STATUS      current
    DESCRIPTION
        "Channel Space Provision, reference to CHA-SPC__INVENTORY" 
    ::=  { deployProvModuleCapEntry 32 }

deployProvModuleCapChannelsProvision OBJECT-TYPE
    SYNTAX      FspR7NumberOfChannelsCaps
    MAX-ACCESS  read-only
    STATUS      current
    DESCRIPTION
        "Number of channels supported by an entity" 
    ::=  { deployProvModuleCapEntry 33 }

deployProvModuleCapFiberDetect OBJECT-TYPE
    SYNTAX      FspR7FiberDetectCaps
    MAX-ACCESS  read-only
    STATUS      current
    DESCRIPTION
        "Fiber Detect" 
    ::=  { deployProvModuleCapEntry 34 }

deployProvModuleCapTrafficDirection OBJECT-TYPE
    SYNTAX      FspR7TrafficDirectionCaps
    MAX-ACCESS  read-only
    STATUS      current
    DESCRIPTION
        "Traffic Direction" 
    ::=  { deployProvModuleCapEntry 35 }

deployProvModuleCapOscUsage OBJECT-TYPE
    SYNTAX      FspR7OscUsageCaps
    MAX-ACCESS  read-only
    STATUS      current
    DESCRIPTION
        "Select if and how the OSC is to be used on an amplifier" 
    ::=  { deployProvModuleCapEntry 36 }

deployProvModuleDefaultsTable  OBJECT-TYPE
    SYNTAX      SEQUENCE OF DeployProvModuleDefaultsEntry
    MAX-ACCESS  not-accessible
    STATUS      current
    DESCRIPTION   "Contains entries for provisioning of modules."
    ::=  { moduleDeployProv 3  }

deployProvModuleDefaultsEntry OBJECT-TYPE
    SYNTAX      DeployProvModuleDefaultsEntry
    MAX-ACCESS  not-accessible
    STATUS      current
    DESCRIPTION   "All modules which are provisioned(or are during deployProv) will have an entry in this table."
    INDEX       { entityIndex }
    ::=  { deployProvModuleDefaultsTable 1 }

DeployProvModuleDefaultsEntry ::=  SEQUENCE
  { deployProvModuleDefaultsRowStatus RowStatus,
    deployProvModuleDefaultsForceDestroy FspR7ForcedStatus,
    deployProvModuleDefaultsType FspR7EquipmentType,
    deployProvModuleDefaultsMode FspR7TransmissionMode,
    deployProvModuleDefaultsDeploy FspR7DeploymentScenario,
    deployProvModuleDefaultsChannel FspR7ChannelIdentifier,
    deployProvModuleDefaultsReach FspR7OpticalInterfaceReach,
    deployProvModuleDefaultsBand FspR7OpticalBand,
    deployProvModuleDefaultsSubBand FspR7OpticalSubBand,
    deployProvModuleDefaultsGroup FspR7OpticalGroup,
    deployProvModuleDefaultsFiber FspR7OpticalFiberType,
    deployProvModuleDefaultsEdfaPwrOut FspR7EdfaOutputPowerRating,
    deployProvModuleDefaultsAdmin FspR7AdminState,
    deployProvModuleDefaultsSupply FspR7SupplyType,
    deployProvModuleDefaultsDispersionCompensation FspR7DispersionCompensation,
    deployProvModuleDefaultsLanAid EntityIndex,
    deployProvModuleDefaultsSingleFiberLocation FspR7SingleFiberLocation,
    deployProvModuleDefaultsPsuOutputPower FspR7PsuOutputPower,
    deployProvModuleDefaultsTilt Integer32,
    deployProvModuleDefaultsGain FspR7Gain,
    deployProvModuleDefaultsCapabilityLevel FspR7CapInventory,
    deployProvModuleDefaultsRoadmNumber FspR7RoadmNumber,
    deployProvModuleDefaultsScrambling FspR7Scrambling,
    deployProvModuleDefaultsChannelSpacing FspR7ChannelSpacing,
    deployProvModuleDefaultsLagSysPrio Unsigned32,
    deployProvModuleDefaultsGainRange FspR7GainRange,
    deployProvModuleDefaultsEqlzAdmin FspR7EqlzAdminState,
    deployProvModuleDefaultsChannelsNumber FspR7NumberOfChannels,
    deployProvModuleDefaultsDCFiberType FspR7DCFiberType,
    deployProvModuleDefaultsMapping FspR7Mapping,
    deployProvModuleDefaultsCac FspR7L2CacEnable,
    deployProvModuleDefaultsChannelSpacingProvision FspR7ChannelSpacing,
    deployProvModuleDefaultsChannelsProvision FspR7NumberOfChannels,
    deployProvModuleDefaultsFiberDetect FspR7FiberDetect,
    deployProvModuleDefaultsTrafficDirection FspR7TrafficDirection,
    deployProvModuleDefaultsOscUsage FspR7OscUsage }

deployProvModuleDefaultsRowStatus OBJECT-TYPE
    SYNTAX      RowStatus
    MAX-ACCESS  read-only
    STATUS      current
    DESCRIPTION   "RowStatus"
    ::=  { deployProvModuleDefaultsEntry 1 }

deployProvModuleDefaultsForceDestroy OBJECT-TYPE
    SYNTAX      FspR7ForcedStatus
    MAX-ACCESS  read-only
    STATUS      current
    DESCRIPTION
        "Forced Destroy" 
    ::=  { deployProvModuleDefaultsEntry 2 }

deployProvModuleDefaultsType OBJECT-TYPE
    SYNTAX      FspR7EquipmentType
    MAX-ACCESS  read-only
    STATUS      current
    DESCRIPTION   "The TYPE of Module."
    ::=  { deployProvModuleDefaultsEntry 3 }

deployProvModuleDefaultsMode OBJECT-TYPE
    SYNTAX      FspR7TransmissionMode
    MAX-ACCESS  read-only
    STATUS      current
    DESCRIPTION   "The transmission mode of the module."
    ::=  { deployProvModuleDefaultsEntry 4 }

deployProvModuleDefaultsDeploy OBJECT-TYPE
    SYNTAX      FspR7DeploymentScenario
    MAX-ACCESS  read-only
    STATUS      current
    DESCRIPTION   "The deployment scenario of the module."
    ::=  { deployProvModuleDefaultsEntry 5 }

deployProvModuleDefaultsChannel OBJECT-TYPE
    SYNTAX      FspR7ChannelIdentifier
    MAX-ACCESS  read-only
    STATUS      current
    DESCRIPTION   "The optical channel."
    ::=  { deployProvModuleDefaultsEntry 6 }

deployProvModuleDefaultsReach OBJECT-TYPE
    SYNTAX      FspR7OpticalInterfaceReach
    MAX-ACCESS  read-only
    STATUS      current
    DESCRIPTION   "The optical channel."
    ::=  { deployProvModuleDefaultsEntry 7 }

deployProvModuleDefaultsBand OBJECT-TYPE
    SYNTAX      FspR7OpticalBand
    MAX-ACCESS  read-only
    STATUS      current
    DESCRIPTION   "The The optical band of the module."
    ::=  { deployProvModuleDefaultsEntry 8 }

deployProvModuleDefaultsSubBand OBJECT-TYPE
    SYNTAX      FspR7OpticalSubBand
    MAX-ACCESS  read-only
    STATUS      current
    DESCRIPTION   "The subband of 16 DWDM channels."
    ::=  { deployProvModuleDefaultsEntry 9 }

deployProvModuleDefaultsGroup OBJECT-TYPE
    SYNTAX      FspR7OpticalGroup
    MAX-ACCESS  read-only
    STATUS      current
    DESCRIPTION   "The Group of 4 DWDM channels."
    ::=  { deployProvModuleDefaultsEntry 10 }

deployProvModuleDefaultsFiber OBJECT-TYPE
    SYNTAX      FspR7OpticalFiberType
    MAX-ACCESS  read-only
    STATUS      current
    DESCRIPTION   "Fiber type."
    ::=  { deployProvModuleDefaultsEntry 11 }

deployProvModuleDefaultsEdfaPwrOut OBJECT-TYPE
    SYNTAX      FspR7EdfaOutputPowerRating
    MAX-ACCESS  read-only
    STATUS      current
    DESCRIPTION
        "Optical Output Power Rating - Provision" 
    ::=  { deployProvModuleDefaultsEntry 12 }

deployProvModuleDefaultsAdmin OBJECT-TYPE
    SYNTAX      FspR7AdminState
    MAX-ACCESS  read-only
    STATUS      current
    DESCRIPTION   "The Adminstrative State."
    ::=  { deployProvModuleDefaultsEntry 13 }

deployProvModuleDefaultsSupply OBJECT-TYPE
    SYNTAX      FspR7SupplyType
    MAX-ACCESS  read-only
    STATUS      current
    DESCRIPTION
        "The kind of power supply - provisioned value" 
    ::=  { deployProvModuleDefaultsEntry 14 }

deployProvModuleDefaultsDispersionCompensation OBJECT-TYPE
    SYNTAX      FspR7DispersionCompensation
    MAX-ACCESS  read-only
    STATUS      current
    DESCRIPTION
        "Dispersion Compensation Value in km of SSMF fiber" 
    ::=  { deployProvModuleDefaultsEntry 15 }

deployProvModuleDefaultsLanAid OBJECT-TYPE
    SYNTAX      EntityIndex
    MAX-ACCESS  read-only
    STATUS      current
    DESCRIPTION
        "AID of LAN" 
    ::=  { deployProvModuleDefaultsEntry 16 }

deployProvModuleDefaultsSingleFiberLocation OBJECT-TYPE
    SYNTAX      FspR7SingleFiberLocation
    MAX-ACCESS  read-only
    STATUS      current
    DESCRIPTION
        "determines the location (A or B) for Single Fiber applications" 
    ::=  { deployProvModuleDefaultsEntry 17 }

deployProvModuleDefaultsPsuOutputPower OBJECT-TYPE
    SYNTAX      FspR7PsuOutputPower
    MAX-ACCESS  read-only
    STATUS      current
    DESCRIPTION
        "Maximum PSU Output Power" 
    ::=  { deployProvModuleDefaultsEntry 18 }

deployProvModuleDefaultsTilt OBJECT-TYPE
    SYNTAX      Integer32 (-50..0 | -2147483648) 
    UNITS       "0.1 dB"
    MAX-ACCESS  read-only
    STATUS      current
    DESCRIPTION
        "Change of optical channel power in dB over the complete transmission band" 
    ::=  { deployProvModuleDefaultsEntry 19 }

deployProvModuleDefaultsGain OBJECT-TYPE
    SYNTAX      FspR7Gain
    MAX-ACCESS  read-only
    STATUS      current
    DESCRIPTION
        "Gain" 
    ::=  { deployProvModuleDefaultsEntry 20 }

deployProvModuleDefaultsCapabilityLevel OBJECT-TYPE
    SYNTAX      FspR7CapInventory
    MAX-ACCESS  read-only
    STATUS      current
    DESCRIPTION
        "Capability level provisioned" 
    ::=  { deployProvModuleDefaultsEntry 21 }

deployProvModuleDefaultsRoadmNumber OBJECT-TYPE
    SYNTAX      FspR7RoadmNumber
    MAX-ACCESS  read-only
    STATUS      current
    DESCRIPTION
        "Number for ROADM module typically associated with a Network Fiber or Degree" 
    ::=  { deployProvModuleDefaultsEntry 22 }

deployProvModuleDefaultsScrambling OBJECT-TYPE
    SYNTAX      FspR7Scrambling
    MAX-ACCESS  read-only
    STATUS      current
    DESCRIPTION   "Virtual Fac. Scrambling"
    ::=  { deployProvModuleDefaultsEntry 23 }

deployProvModuleDefaultsChannelSpacing OBJECT-TYPE
    SYNTAX      FspR7ChannelSpacing
    MAX-ACCESS  read-only
    STATUS      current
    DESCRIPTION
        "ITU Grid channel spacing" 
    ::=  { deployProvModuleDefaultsEntry 24 }

deployProvModuleDefaultsLagSysPrio OBJECT-TYPE
    SYNTAX      Unsigned32 (0..65535 | 4294967295)
    MAX-ACCESS  read-only
    STATUS      current
    DESCRIPTION
        "Link Aggregation Group Actor System Priority Part of LAG ID" 
    ::=  { deployProvModuleDefaultsEntry 25 }

deployProvModuleDefaultsGainRange OBJECT-TYPE
    SYNTAX      FspR7GainRange
    MAX-ACCESS  read-only
    STATUS      current
    DESCRIPTION
        "EDFA gain range to provision" 
    ::=  { deployProvModuleDefaultsEntry 26 }

deployProvModuleDefaultsEqlzAdmin OBJECT-TYPE
    SYNTAX      FspR7EqlzAdminState
    MAX-ACCESS  read-only
    STATUS      current
    DESCRIPTION
        "Scheduled Equalization Administration" 
    ::=  { deployProvModuleDefaultsEntry 27 }

deployProvModuleDefaultsChannelsNumber OBJECT-TYPE
    SYNTAX      FspR7NumberOfChannels
    MAX-ACCESS  read-only
    STATUS      current
    DESCRIPTION   "Number of channels supported by an entity"
    ::=  { deployProvModuleDefaultsEntry 28 }

deployProvModuleDefaultsDCFiberType OBJECT-TYPE
    SYNTAX      FspR7DCFiberType
    MAX-ACCESS  read-only
    STATUS      current
    DESCRIPTION
        "Dispersion Compensation Fibertype" 
    ::=  { deployProvModuleDefaultsEntry 29 }

deployProvModuleDefaultsMapping OBJECT-TYPE
    SYNTAX      FspR7Mapping
    MAX-ACCESS  read-only
    STATUS      current
    DESCRIPTION
        "Type of mapping; transparent or framing" 
    ::=  { deployProvModuleDefaultsEntry 30 }

deployProvModuleDefaultsCac OBJECT-TYPE
    SYNTAX      FspR7L2CacEnable
    MAX-ACCESS  read-only
    STATUS      current
    DESCRIPTION
        "Enable of CAC" 
    ::=  { deployProvModuleDefaultsEntry 31 }

deployProvModuleDefaultsChannelSpacingProvision OBJECT-TYPE
    SYNTAX      FspR7ChannelSpacing
    MAX-ACCESS  read-only
    STATUS      current
    DESCRIPTION
        "Channel Space Provision, reference to CHA-SPC__INVENTORY" 
    ::=  { deployProvModuleDefaultsEntry 32 }

deployProvModuleDefaultsChannelsProvision OBJECT-TYPE
    SYNTAX      FspR7NumberOfChannels
    MAX-ACCESS  read-only
    STATUS      current
    DESCRIPTION
        "Number of channels supported by an entity" 
    ::=  { deployProvModuleDefaultsEntry 33 }

deployProvModuleDefaultsFiberDetect OBJECT-TYPE
    SYNTAX      FspR7FiberDetect
    MAX-ACCESS  read-only
    STATUS      current
    DESCRIPTION
        "Fiber Detect" 
    ::=  { deployProvModuleDefaultsEntry 34 }

deployProvModuleDefaultsTrafficDirection OBJECT-TYPE
    SYNTAX      FspR7TrafficDirection
    MAX-ACCESS  read-only
    STATUS      current
    DESCRIPTION
        "Traffic Direction" 
    ::=  { deployProvModuleDefaultsEntry 35 }

deployProvModuleDefaultsOscUsage OBJECT-TYPE
    SYNTAX      FspR7OscUsage
    MAX-ACCESS  read-only
    STATUS      current
    DESCRIPTION
        "Select if and how the OSC is to be used on an amplifier" 
    ::=  { deployProvModuleDefaultsEntry 36 }

deployProvPlugTable OBJECT-TYPE
    SYNTAX      SEQUENCE OF DeployProvPlugEntry
    MAX-ACCESS  not-accessible
    STATUS      current
    DESCRIPTION   "Contains entries for provisioning of plugs."
    ::=  { plugDeployProv 1 }

deployProvPlugEntry OBJECT-TYPE
    SYNTAX      DeployProvPlugEntry
    MAX-ACCESS  not-accessible
    STATUS      current
    DESCRIPTION   "All plugs which are provisioned(or during deployProv) will have an entry in this table."
    INDEX       {
                  entityIndex
                }
    ::=  { deployProvPlugTable 1 }

DeployProvPlugEntry ::=  SEQUENCE
  { deployProvPlugRowStatus RowStatus,
    deployProvPlugForceDestroy FspR7ForcedStatus,
    deployProvPlugType FspR7EquipmentType,
    deployProvPlugMaxDataRate FspR7PlugDataRate,
    deployProvPlugChannelId FspR7ChannelIdentifier,
    deployProvPlugThirdPartyUsage EnableState,
    deployProvPlugReach FspR7OpticalInterfaceReach,
    deployProvPlugAdmin FspR7AdminState,
    deployProvPlugLoopbackAttenuation Unsigned32,
    deployProvPlugLaserDelayTimer FspR7LaneGroupInventory,
    deployProvPlugConnector FspR7ConnectorType,
    deployProvPlugBidirectionalChannel FspR7BidirectionalChannel }

deployProvPlugRowStatus OBJECT-TYPE
    SYNTAX      RowStatus
    MAX-ACCESS  read-write
    STATUS      current
    DESCRIPTION   "RowStatus"
    ::=  { deployProvPlugEntry 1 }

deployProvPlugForceDestroy OBJECT-TYPE
    SYNTAX      FspR7ForcedStatus
    MAX-ACCESS  read-write
    STATUS      current
    DESCRIPTION
        "Forced Destroy" 
    ::=  { deployProvPlugEntry 2 }

deployProvPlugType OBJECT-TYPE
    SYNTAX      FspR7EquipmentType
    MAX-ACCESS  read-write
    STATUS      current
    DESCRIPTION   "Allowed Interfacetype may depend additionally on Plug TYPE"
    ::=  { deployProvPlugEntry 3 }

deployProvPlugMaxDataRate OBJECT-TYPE
    SYNTAX      FspR7PlugDataRate
    MAX-ACCESS  read-write
    STATUS      current
    DESCRIPTION   "The maximal data rate of the plug."
    ::=  { deployProvPlugEntry 4 }

deployProvPlugChannelId OBJECT-TYPE
    SYNTAX      FspR7ChannelIdentifier
    MAX-ACCESS  read-write
    STATUS      current
    DESCRIPTION   "The optical channel of the plug."
    ::=  { deployProvPlugEntry 5 }

deployProvPlugThirdPartyUsage OBJECT-TYPE
    SYNTAX      EnableState
    MAX-ACCESS  read-write
    STATUS      current
    DESCRIPTION
        "Usage of 3rd Party Plugs" 
    ::=  { deployProvPlugEntry 6 }

deployProvPlugReach OBJECT-TYPE
    SYNTAX      FspR7OpticalInterfaceReach
    MAX-ACCESS  read-write
    STATUS      current
    DESCRIPTION   "The optical reach of the plug."
    ::=  { deployProvPlugEntry 7 }

deployProvPlugAdmin OBJECT-TYPE
    SYNTAX      FspR7AdminState
    MAX-ACCESS  read-write
    STATUS      current
    DESCRIPTION   "The Adminstrative State will be displayed in the GUI with full name values;
         it will be differently displayed in TL1 syntax according to TL1 display rules. The transaction
         into the UAS state requires a special destroy/delete function."
    ::=  { deployProvPlugEntry 8 }

deployProvPlugLoopbackAttenuation OBJECT-TYPE
    SYNTAX      Unsigned32 (10..300 | 4294967295) 
    UNITS       "0.1 dB"
    MAX-ACCESS  read-write
    STATUS      current
    DESCRIPTION   "Loop back attenuation of the plug"
    ::=  { deployProvPlugEntry 9 }

deployProvPlugLaserDelayTimer OBJECT-TYPE
    SYNTAX      FspR7LaneGroupInventory
    MAX-ACCESS  read-write
    STATUS      current
    DESCRIPTION
        "Lane group to provision" 
    ::=  { deployProvPlugEntry 10 }

deployProvPlugConnector OBJECT-TYPE
    SYNTAX      FspR7ConnectorType
    MAX-ACCESS  read-write
    STATUS      current
    DESCRIPTION
        "Connector" 
    ::=  { deployProvPlugEntry 11 }

deployProvPlugBidirectionalChannel OBJECT-TYPE
    SYNTAX      FspR7BidirectionalChannel
    MAX-ACCESS  read-write
    STATUS      current
    DESCRIPTION
        "Bidirectional Channel Rates from Provisioning" 
    ::=  { deployProvPlugEntry 12 }

deployProvPlugCapTable OBJECT-TYPE
    SYNTAX      SEQUENCE OF DeployProvPlugCapEntry
    MAX-ACCESS  not-accessible
    STATUS      current
    DESCRIPTION   "Contains entries for provisioning of plugs."
    ::=  { plugDeployProv 2  }

deployProvPlugCapEntry OBJECT-TYPE
    SYNTAX      DeployProvPlugCapEntry
    MAX-ACCESS  not-accessible
    STATUS      current
    DESCRIPTION   "All plugs which are provisioned(or during deployProv) will have an entry in this table."
    INDEX       { entityIndex }
    ::=  { deployProvPlugCapTable 1 }

DeployProvPlugCapEntry ::=  SEQUENCE
  { deployProvPlugCapRowStatus FspR7RowStatusCaps,
    deployProvPlugCapForceDestroy FspR7ForcedStatusCaps,
    deployProvPlugCapType FspR7EquipmentTypeCaps,
    deployProvPlugCapMaxDataRate FspR7PlugDataRateCaps,
    deployProvPlugCapChannelId FspR7ChannelIdentifierCaps,
    deployProvPlugCapThirdPartyUsage EnableStateCaps,
    deployProvPlugCapReach FspR7OpticalInterfaceReachCaps,
    deployProvPlugCapAdmin FspR7AdminStateCaps,
    deployProvPlugCapLoopbackAttenuation FspR7Unsigned32Caps,
    deployProvPlugCapLaserDelayTimer FspR7LaneGroupInventoryCaps,
    deployProvPlugCapConnector FspR7ConnectorTypeCaps,
    deployProvPlugCapBidirectionalChannel FspR7BidirectionalChannelCaps }

deployProvPlugCapRowStatus OBJECT-TYPE
    SYNTAX      FspR7RowStatusCaps
    MAX-ACCESS  read-only
    STATUS      current
    DESCRIPTION   "RowStatus"
    ::=  { deployProvPlugCapEntry 1 }

deployProvPlugCapForceDestroy OBJECT-TYPE
    SYNTAX      FspR7ForcedStatusCaps
    MAX-ACCESS  read-only
    STATUS      current
    DESCRIPTION
        "Forced Destroy" 
    ::=  { deployProvPlugCapEntry 2 }

deployProvPlugCapType OBJECT-TYPE
    SYNTAX      FspR7EquipmentTypeCaps
    MAX-ACCESS  read-only
    STATUS      current
    DESCRIPTION   "Allowed Interfacetype may depend additionally on Plug TYPE"
    ::=  { deployProvPlugCapEntry 3 }

deployProvPlugCapMaxDataRate OBJECT-TYPE
    SYNTAX      FspR7PlugDataRateCaps
    MAX-ACCESS  read-only
    STATUS      current
    DESCRIPTION   "The maximal data rate of the plug."
    ::=  { deployProvPlugCapEntry 4 }

deployProvPlugCapChannelId OBJECT-TYPE
    SYNTAX      FspR7ChannelIdentifierCaps
    MAX-ACCESS  read-only
    STATUS      current
    DESCRIPTION   "The optical channel of the plug."
    ::=  { deployProvPlugCapEntry 5 }

deployProvPlugCapThirdPartyUsage OBJECT-TYPE
    SYNTAX      EnableStateCaps
    MAX-ACCESS  read-only
    STATUS      current
    DESCRIPTION
        "Usage of 3rd Party Plugs" 
    ::=  { deployProvPlugCapEntry 6 }

deployProvPlugCapReach OBJECT-TYPE
    SYNTAX      FspR7OpticalInterfaceReachCaps
    MAX-ACCESS  read-only
    STATUS      current
    DESCRIPTION   "The optical reach of the plug."
    ::=  { deployProvPlugCapEntry 7 }

deployProvPlugCapAdmin OBJECT-TYPE
    SYNTAX      FspR7AdminStateCaps
    MAX-ACCESS  read-only
    STATUS      current
    DESCRIPTION   "The Adminstrative State will be displayed in the GUI with full name values;
         it will be differently displayed in TL1 syntax according to TL1 display rules. The transaction
         into the UAS state requires a special destroy/delete function."
    ::=  { deployProvPlugCapEntry 8 }

deployProvPlugCapLoopbackAttenuation OBJECT-TYPE
    SYNTAX      FspR7Unsigned32Caps
    UNITS       "0.1 dB"
    MAX-ACCESS  read-only
    STATUS      current
    DESCRIPTION   "Loop back attenuation of the plug"
    ::=  { deployProvPlugCapEntry 9 }

deployProvPlugCapLaserDelayTimer OBJECT-TYPE
    SYNTAX      FspR7LaneGroupInventoryCaps
    MAX-ACCESS  read-only
    STATUS      current
    DESCRIPTION
        "Lane group to provision" 
    ::=  { deployProvPlugCapEntry 10 }

deployProvPlugCapConnector OBJECT-TYPE
    SYNTAX      FspR7ConnectorTypeCaps
    MAX-ACCESS  read-only
    STATUS      current
    DESCRIPTION
        "Connector" 
    ::=  { deployProvPlugCapEntry 11 }

deployProvPlugCapBidirectionalChannel OBJECT-TYPE
    SYNTAX      FspR7BidirectionalChannelCaps
    MAX-ACCESS  read-only
    STATUS      current
    DESCRIPTION
        "Bidirectional Channel Rates from Provisioning" 
    ::=  { deployProvPlugCapEntry 12 }

deployProvPlugDefaultsTable  OBJECT-TYPE
    SYNTAX      SEQUENCE OF DeployProvPlugDefaultsEntry
    MAX-ACCESS  not-accessible
    STATUS      current
    DESCRIPTION   "Contains entries for provisioning of plugs."
    ::=  { plugDeployProv 3  }

deployProvPlugDefaultsEntry OBJECT-TYPE
    SYNTAX      DeployProvPlugDefaultsEntry
    MAX-ACCESS  not-accessible
    STATUS      current
    DESCRIPTION   "All plugs which are provisioned(or during deployProv) will have an entry in this table."
    INDEX       { entityIndex }
    ::=  { deployProvPlugDefaultsTable 1 }

DeployProvPlugDefaultsEntry ::=  SEQUENCE
  { deployProvPlugDefaultsRowStatus RowStatus,
    deployProvPlugDefaultsForceDestroy FspR7ForcedStatus,
    deployProvPlugDefaultsType FspR7EquipmentType,
    deployProvPlugDefaultsMaxDataRate FspR7PlugDataRate,
    deployProvPlugDefaultsChannelId FspR7ChannelIdentifier,
    deployProvPlugDefaultsThirdPartyUsage EnableState,
    deployProvPlugDefaultsReach FspR7OpticalInterfaceReach,
    deployProvPlugDefaultsAdmin FspR7AdminState,
    deployProvPlugDefaultsLoopbackAttenuation Unsigned32,
    deployProvPlugDefaultsLaserDelayTimer FspR7LaneGroupInventory,
    deployProvPlugDefaultsConnector FspR7ConnectorType,
    deployProvPlugDefaultsBidirectionalChannel FspR7BidirectionalChannel }

deployProvPlugDefaultsRowStatus OBJECT-TYPE
    SYNTAX      RowStatus
    MAX-ACCESS  read-only
    STATUS      current
    DESCRIPTION   "RowStatus"
    ::=  { deployProvPlugDefaultsEntry 1 }

deployProvPlugDefaultsForceDestroy OBJECT-TYPE
    SYNTAX      FspR7ForcedStatus
    MAX-ACCESS  read-only
    STATUS      current
    DESCRIPTION
        "Forced Destroy" 
    ::=  { deployProvPlugDefaultsEntry 2 }

deployProvPlugDefaultsType OBJECT-TYPE
    SYNTAX      FspR7EquipmentType
    MAX-ACCESS  read-only
    STATUS      current
    DESCRIPTION   "Allowed Interfacetype may depend additionally on Plug TYPE"
    ::=  { deployProvPlugDefaultsEntry 3 }

deployProvPlugDefaultsMaxDataRate OBJECT-TYPE
    SYNTAX      FspR7PlugDataRate
    MAX-ACCESS  read-only
    STATUS      current
    DESCRIPTION   "The maximal data rate of the plug."
    ::=  { deployProvPlugDefaultsEntry 4 }

deployProvPlugDefaultsChannelId OBJECT-TYPE
    SYNTAX      FspR7ChannelIdentifier
    MAX-ACCESS  read-only
    STATUS      current
    DESCRIPTION   "The optical channel of the plug."
    ::=  { deployProvPlugDefaultsEntry 5 }

deployProvPlugDefaultsThirdPartyUsage OBJECT-TYPE
    SYNTAX      EnableState
    MAX-ACCESS  read-only
    STATUS      current
    DESCRIPTION
        "Usage of 3rd Party Plugs" 
    ::=  { deployProvPlugDefaultsEntry 6 }

deployProvPlugDefaultsReach OBJECT-TYPE
    SYNTAX      FspR7OpticalInterfaceReach
    MAX-ACCESS  read-only
    STATUS      current
    DESCRIPTION   "The optical reach of the plug."
    ::=  { deployProvPlugDefaultsEntry 7 }

deployProvPlugDefaultsAdmin OBJECT-TYPE
    SYNTAX      FspR7AdminState
    MAX-ACCESS  read-only
    STATUS      current
    DESCRIPTION   "The Adminstrative State will be displayed in the GUI with full name values;
         it will be differently displayed in TL1 syntax according to TL1 display rules. The transaction
         into the UAS state requires a special destroy/delete function."
    ::=  { deployProvPlugDefaultsEntry 8 }

deployProvPlugDefaultsLoopbackAttenuation OBJECT-TYPE
    SYNTAX      Unsigned32 (10..300 | 4294967295) 
    UNITS       "0.1 dB"
    MAX-ACCESS  read-only
    STATUS      current
    DESCRIPTION   "Loop back attenuation of the plug"
    ::=  { deployProvPlugDefaultsEntry 9 }

deployProvPlugDefaultsLaserDelayTimer OBJECT-TYPE
    SYNTAX      FspR7LaneGroupInventory
    MAX-ACCESS  read-only
    STATUS      current
    DESCRIPTION
        "Lane group to provision" 
    ::=  { deployProvPlugDefaultsEntry 10 }

deployProvPlugDefaultsConnector OBJECT-TYPE
    SYNTAX      FspR7ConnectorType
    MAX-ACCESS  read-only
    STATUS      current
    DESCRIPTION
        "Connector" 
    ::=  { deployProvPlugDefaultsEntry 11 }

deployProvPlugDefaultsBidirectionalChannel OBJECT-TYPE
    SYNTAX      FspR7BidirectionalChannel
    MAX-ACCESS  read-only
    STATUS      current
    DESCRIPTION
        "Bidirectional Channel Rates from Provisioning" 
    ::=  { deployProvPlugDefaultsEntry 12 }

deployProvIfTable OBJECT-TYPE
    SYNTAX      SEQUENCE OF DeployProvIfEntry
    MAX-ACCESS  not-accessible
    STATUS      current
    DESCRIPTION   "Contains entries for provisioning of interfaces."
    ::=  { facilityDeployProv 1 }

deployProvIfEntry OBJECT-TYPE
    SYNTAX      DeployProvIfEntry
    MAX-ACCESS  not-accessible
    STATUS      current
    DESCRIPTION   "All interfaces which are provisioned(or during deployProv)
         will have an entry in this table."
    INDEX       {
                  entityIndex
                }
    ::=  { deployProvIfTable 1 }

DeployProvIfEntry ::=  SEQUENCE
  { deployProvIfRowStatus RowStatus,
    deployProvIfForceDestroy FspR7ForcedStatus,
    deployProvIfType FspR7InterfaceType,
    deployProvIfPayload OtnPayloadType,
    deployProvIfBehaviour FspR7PortBehaviour,
    deployProvIfTerminationLevel OhTerminationLevel,
    deployProvIfAlsMode FspR7AlsMode,
    deployProvIfErrorForwarding FspR7ErrorFwdMode,
    deployProvIfLaserOffDelayFunction EnableState,
    deployProvIfFecType FspR7FecType,
    deployProvIfTimingSource SonetTimingSource,
    deployProvIfTcmALevel OtnTcmLevel,
    deployProvIfTcmBLevel OtnTcmLevel,
    deployProvIfSigDegThresSonetLine FspR7BERThreshold,
    deployProvIfSigDegThresSdhMs Unsigned32,
    deployProvIfSignalDegradePeriod Unsigned32,
    deployProvIfAutonegotiation EnableState,
    deployProvIfBitrate FspR7Bitrate,
    deployProvIfDuplex EthDuplexMode,
    deployProvIfFlowControl FspR7FlowControlMode,
    deployProvIfOtnStuffing FspR7Stuff,
    deployProvIfSigDegThresOtu Integer32,
    deployProvIfSigDegPeriodOtu Unsigned32,
    deployProvIfSigDegThresOdu Integer32,
    deployProvIfSigDegPeriodOdu Unsigned32,
    deployProvIfSigDegThresOduTcmA Integer32,
    deployProvIfSigDegPeriodOduTcmA Unsigned32,
    deployProvIfSigDegThresOduTcmB Integer32,
    deployProvIfSigDegPeriodOduTcmB Unsigned32,
    deployProvIfTilt Integer32,
    deployProvIfGain FspR7Gain,
    deployProvIfAdmin FspR7AdminState,
    deployProvIfAttenuationGradient Unsigned32,
    deployProvIfSigDegThresReceiver Unsigned32,
    deployProvIfTcmCLevel OtnTcmLevel,
    deployProvIfSigDegThresOduTcmC Integer32,
    deployProvIfSigDegPeriodOduTcmC Unsigned32,
    deployProvIfDisparityCorrection EnableState,
    deployProvIfIpAddr IpAddress,
    deployProvIfIpMask IpAddress,
    deployProvIfOspf FspR7OspfMode,
    deployProvIfMetric Unsigned32,
    deployProvIfAreaId IpAddress,
    deployProvIfTraceFormSonetSection SonetTraceForm,
    deployProvIfTraceExpectedSonetSection OCTET STRING,
    deployProvIfTraceTransmitSonetSection OCTET STRING,
    deployProvIfTimModeSonetSection TimMode,
    deployProvIfTraceExpectedOtu OCTET STRING,
    deployProvIfTraceTransmitSapiOtu OCTET STRING,
    deployProvIfTraceTransmitDapiOtu OCTET STRING,
    deployProvIfTraceTransmitOpspOtu OCTET STRING,
    deployProvIfTimModeOtu TimMode,
    deployProvIfTraceExpectedOdu OCTET STRING,
    deployProvIfTraceTransmitSapiOdu OCTET STRING,
    deployProvIfTraceTransmitDapiOdu OCTET STRING,
    deployProvIfTraceTransmitOpspOdu OCTET STRING,
    deployProvIfTimModeOdu TimMode,
    deployProvIfTraceExpectedOduTcmA OCTET STRING,
    deployProvIfTraceTransmitSapiOduTcmA OCTET STRING,
    deployProvIfTraceTransmitDapiOduTcmA OCTET STRING,
    deployProvIfTraceTransmitOpspOduTcmA OCTET STRING,
    deployProvIfTimModeOduTcmA TimMode,
    deployProvIfTraceExpectedOduTcmB OCTET STRING,
    deployProvIfTraceTransmitSapiOduTcmB OCTET STRING,
    deployProvIfTraceTransmitDapiOduTcmB OCTET STRING,
    deployProvIfTraceTransmitOpspOduTcmB OCTET STRING,
    deployProvIfTimModeOduTcmB TimMode,
    deployProvIfTraceExpectedOduTcmC OCTET STRING,
    deployProvIfTraceTransmitSapiOduTcmC OCTET STRING,
    deployProvIfTraceTransmitDapiOduTcmC OCTET STRING,
    deployProvIfTraceTransmitOpspOduTcmC OCTET STRING,
    deployProvIfTimModeOduTcmC TimMode,
    deployProvIfChannelProvisioning FspR7ChannelIdentifier,
    deployProvIfVariableGain Unsigned32,
    deployProvIfBand FspR7OpticalBand,
    deployProvIfSigDegThreshold Unsigned32,
    deployProvIfSigDegPeriodIntegration Unsigned32,
    deployProvIfVoaMode FspR7VoaMode,
    deployProvIfOpticalSetPoint Integer32,
    deployProvIfVoaSetpoint Unsigned32,
    deployProvIfLanAid EntityIndex,
    deployProvIfAprHighThreshold Unsigned32,
    deployProvIfPumpPower Integer32,
    deployProvIfIpType FspR7IpType,
    deployProvIfWdmRxChannel FspR7ChannelIdentifier,
    deployProvIfSigDegThresSonetSection FspR7BERThresholdSection,
    deployProvIfSigDegThresSdhSection Unsigned32,
    deployProvIfSigDegPeriodSdhSection Unsigned32,
    deployProvIfDispersionMode FspR7DispersionModes,
    deployProvIfDispersionSetting Integer32,
    deployProvIfOffset Integer32,
    deployProvIfFunction FspR7InterfaceFunction,
    deployProvIfPortMode FspR7PortMode,
    deployProvIfPortRole FspR7PortRole,
    deployProvIfUtag FspR7UntaggedFrames,
    deployProvIfPvid Unsigned32,
    deployProvIfPriority Unsigned32,
    deployProvIfStagType FspR7SnmpHexString,
    deployProvIfCac FspR7L2CacEnable,
    deployProvIfMaxFrameSize Unsigned32,
    deployProvIfVethAid EntityIndex,
    deployProvIfLagPrio Unsigned32,
    deployProvIfLagPortType FspR7LagPortType,
    deployProvIfLagActivePorts Unsigned32,
    deployProvIfLacpMode FspR7LacpMode,
    deployProvIfLagLoadBallanceSource FspR7LagLoadBallanceSource,
    deployProvIfLacpTimeout FspR7LacpTimeout,
    deployProvIfFarEndCommunication FspR7YesNo,
    deployProvIfEqlzAdmin FspR7EqlzAdminState,
    deployProvIfTxOffDelay FspR7EnableDisable,
    deployProvIfOpuPayloadType FspR7OpuPayloadType,
    deployProvIfOscOpticalSetpoint Integer32,
    deployProvIfFiberBrand FspR7FiberBrand,
    deployProvIfTiltSet FspR7TiltSet,
    deployProvIfXfpDecisionThres FspR7XfpDecisionThres,
    deployProvIfAutoPTassignment FspR7ManualAuto,
    deployProvIfTributarySlotMethod FspR7ManualAuto,
    deployProvIfOduTribPortNo SnmpAdminString,
    deployProvIfOduTribTimeSlottNo SnmpAdminString,
    deployProvIfRevertiveMode ApsRevertMode,
    deployProvIfLaserDelayTimer FspR7LaserDelayTimer,
    deployProvIfLaserOffTimer Unsigned32,
    deployProvIfLaserOnTimer Unsigned32,
    deployProvIfLaneChannelSetting FspR7ChannelIdentifier,
    deployProvIfBip FspR7Bip,
    deployProvIfCodeGain FspR7CodeGain,
    deployProvIfEdfaPwrOut FspR7EdfaOutputPowerRating,
    deployProvIfPrio Unsigned32,
    deployProvIfAuthType FspR7CpAuthType,
    deployProvIfAuthString SnmpAdminString,
    deployProvIfSigDegPcslThreshold Unsigned32 }

deployProvIfRowStatus OBJECT-TYPE
    SYNTAX      RowStatus
    MAX-ACCESS  read-write
    STATUS      current
    DESCRIPTION   "RowStatus"
    ::=  { deployProvIfEntry 1 }

deployProvIfForceDestroy OBJECT-TYPE
    SYNTAX      FspR7ForcedStatus
    MAX-ACCESS  read-write
    STATUS      current
    DESCRIPTION
        "Forced Destroy" 
    ::=  { deployProvIfEntry 2 }

deployProvIfType OBJECT-TYPE
    SYNTAX      FspR7InterfaceType
    MAX-ACCESS  read-write
    STATUS      current
    DESCRIPTION   "The TYPE defines the transport service type as wrapper with wrapper layer
         termination OR else as payload"
    ::=  { deployProvIfEntry 3 }

deployProvIfPayload OBJECT-TYPE
    SYNTAX      OtnPayloadType
    MAX-ACCESS  read-write
    STATUS      current
    DESCRIPTION   "The payload of the interface (inside a transport overhead).
         Relevant e. g. for OTN cards which wrap a payload into an OTU1/2 wrapper."
    ::=  { deployProvIfEntry 4 }

deployProvIfBehaviour OBJECT-TYPE
    SYNTAX      FspR7PortBehaviour
    MAX-ACCESS  read-write
    STATUS      current
    DESCRIPTION   "The configured behaviour of the interface. If configured as
         a network interface, the interface will use a WDM laser."
    ::=  { deployProvIfEntry 5 }

deployProvIfTerminationLevel OBJECT-TYPE
    SYNTAX      OhTerminationLevel
    MAX-ACCESS  read-write
    STATUS      current
    DESCRIPTION
        "Highest signal level hardware removes then generates for transmission." 
    ::=  { deployProvIfEntry 6 }

deployProvIfAlsMode OBJECT-TYPE
    SYNTAX      FspR7AlsMode
    MAX-ACCESS  read-write
    STATUS      current
    DESCRIPTION   "A configuration request for the Automatic Laser Shutdown (ALS)
         function. Refer to FspR7AlsMode Textual Convention for details."
    ::=  { deployProvIfEntry 7 }

deployProvIfErrorForwarding OBJECT-TYPE
    SYNTAX      FspR7ErrorFwdMode
    MAX-ACCESS  read-write
    STATUS      current
    DESCRIPTION   "A configuration request for the error forwarding
         function. Refer to FspR7ErrorFwdMode Textual Convention for details."
    ::=  { deployProvIfEntry 8 }

deployProvIfLaserOffDelayFunction OBJECT-TYPE
    SYNTAX      EnableState
    MAX-ACCESS  read-write
    STATUS      current
    DESCRIPTION   "A configuration request for the Laser Off Delay function. This function
         delays turning off the laser as a consequent action to a defect."
    ::=  { deployProvIfEntry 9 }

deployProvIfFecType OBJECT-TYPE
    SYNTAX      FspR7FecType
    MAX-ACCESS  read-write
    STATUS      current
    DESCRIPTION   "Configuration of FEC type."
    ::=  { deployProvIfEntry 10 }

deployProvIfTimingSource OBJECT-TYPE
    SYNTAX      SonetTimingSource
    MAX-ACCESS  read-write
    STATUS      current
    DESCRIPTION   "The timing source for this interface.
         - internal: used in stand-alone, point-to-point topologies stand-alone (dedicated fiber operation).
         - loopTiming: e.g. used in point-to-point via SONET network and feeder topologies. The default is
         internal(1)."
    ::=  { deployProvIfEntry 11 }

deployProvIfTcmALevel OBJECT-TYPE
    SYNTAX      OtnTcmLevel
    MAX-ACCESS  read-write
    STATUS      current
    DESCRIPTION   "Configuration of TCMA level."
    ::=  { deployProvIfEntry 12 }

deployProvIfTcmBLevel OBJECT-TYPE
    SYNTAX      OtnTcmLevel
    MAX-ACCESS  read-write
    STATUS      current
    DESCRIPTION   "Configuration of TCMB level."
    ::=  { deployProvIfEntry 13 }

deployProvIfSigDegThresSonetLine OBJECT-TYPE
    SYNTAX      FspR7BERThreshold
    MAX-ACCESS  read-write
    STATUS      current
    DESCRIPTION
        "Bit-Error-Based Degradation Definition for SONET (standard integration period)" 
    ::=  { deployProvIfEntry 14 }

deployProvIfSigDegThresSdhMs OBJECT-TYPE
    SYNTAX      Unsigned32 (1..100 | 4294967295) 
    UNITS       "%"
    MAX-ACCESS  read-write
    STATUS      current
    DESCRIPTION
        "Block-Error-Based Degradation Definition for SDH (standard integration period).
         Defined as percentage Background Block Errors (30% default) evaluated
         over a defined period (SDPER-RS)." 
    ::=  { deployProvIfEntry 15 }

deployProvIfSignalDegradePeriod OBJECT-TYPE
    SYNTAX      Unsigned32 (2..10 | 4294967295) 
    UNITS       "s"
    MAX-ACCESS  read-write
    STATUS      current
    DESCRIPTION   "The measurement period in seconds used together with
         the deployProvIfSigDegThresSdhRegSect based on the block error counting method.
         The valid range is 2..10,
         The default being 7."
    ::=  { deployProvIfEntry 16 }

deployProvIfAutonegotiation OBJECT-TYPE
    SYNTAX      EnableState
    MAX-ACCESS  read-write
    STATUS      current
    DESCRIPTION
        "Auto Negotiation for the data rate" 
    ::=  { deployProvIfEntry 17 }

deployProvIfBitrate OBJECT-TYPE
    SYNTAX      FspR7Bitrate
    MAX-ACCESS  read-write
    STATUS      current
    DESCRIPTION
        "Provisioned data rate" 
    ::=  { deployProvIfEntry 18 }

deployProvIfDuplex OBJECT-TYPE
    SYNTAX      EthDuplexMode
    MAX-ACCESS  read-write
    STATUS      current
    DESCRIPTION
        "Duplex Mode (provision), available when Auto Negoiation is Disable (AUTONEG=DISABLE)" 
    ::=  { deployProvIfEntry 19 }

deployProvIfFlowControl OBJECT-TYPE
    SYNTAX      FspR7FlowControlMode
    MAX-ACCESS  read-write
    STATUS      current
    DESCRIPTION
        "Flow Control mechanism" 
    ::=  { deployProvIfEntry 20 }

deployProvIfOtnStuffing OBJECT-TYPE
    SYNTAX      FspR7Stuff
    MAX-ACCESS  read-write
    STATUS      current
    DESCRIPTION
        "Indicates if bit/byte stuffing is used in the transport signal." 
    ::=  { deployProvIfEntry 21 }

deployProvIfSigDegThresOtu OBJECT-TYPE
    SYNTAX      Integer32 (1..100 | -2147483648) 
    UNITS       "%"
    MAX-ACCESS  read-write
    STATUS      current
    DESCRIPTION
        "Background-Block-Error-Based Signal Degradation Definition for OTU" 
    ::=  { deployProvIfEntry 22 }

deployProvIfSigDegPeriodOtu OBJECT-TYPE
    SYNTAX      Unsigned32 (2..10 | 4294967295) 
    UNITS       "s"
    MAX-ACCESS  read-write
    STATUS      current
    DESCRIPTION
        "Integration Period for Signal degrade" 
    ::=  { deployProvIfEntry 23 }

deployProvIfSigDegThresOdu OBJECT-TYPE
    SYNTAX      Integer32 (1..100 | -2147483648) 
    UNITS       "%"
    MAX-ACCESS  read-write
    STATUS      current
    DESCRIPTION
        "Background-Block-Error-Based Signal Degradation Definition for ODU" 
    ::=  { deployProvIfEntry 24 }

deployProvIfSigDegPeriodOdu OBJECT-TYPE
    SYNTAX      Unsigned32 (2..10 | 4294967295) 
    UNITS       "s"
    MAX-ACCESS  read-write
    STATUS      current
    DESCRIPTION
        "Integration Period for Signal degrade" 
    ::=  { deployProvIfEntry 25 }

deployProvIfSigDegThresOduTcmA OBJECT-TYPE
    SYNTAX      Integer32 (1..100 | -2147483648) 
    UNITS       "%"
    MAX-ACCESS  read-write
    STATUS      current
    DESCRIPTION
        "Background-Block-Error-Based Signal Degradation Definition for TCM-A" 
    ::=  { deployProvIfEntry 26 }

deployProvIfSigDegPeriodOduTcmA OBJECT-TYPE
    SYNTAX      Unsigned32 (2..10 | 4294967295) 
    UNITS       "s"
    MAX-ACCESS  read-write
    STATUS      current
    DESCRIPTION
        "Integration Period for Signal degrade" 
    ::=  { deployProvIfEntry 27 }

deployProvIfSigDegThresOduTcmB OBJECT-TYPE
    SYNTAX      Integer32 (1..100 | -2147483648) 
    UNITS       "%"
    MAX-ACCESS  read-write
    STATUS      current
    DESCRIPTION
        "Background-Block-Error-Based Signal Degradation Definition for TCM-B" 
    ::=  { deployProvIfEntry 28 }

deployProvIfSigDegPeriodOduTcmB OBJECT-TYPE
    SYNTAX      Unsigned32 (2..10 | 4294967295) 
    UNITS       "s"
    MAX-ACCESS  read-write
    STATUS      current
    DESCRIPTION
        "Integration Period of TCMB Signal Segrade" 
    ::=  { deployProvIfEntry 29 }

deployProvIfTilt OBJECT-TYPE
    SYNTAX      Integer32 (-50..0 | -2147483648) 
    UNITS       "0.1 dB"
    MAX-ACCESS  read-write
    STATUS      current
    DESCRIPTION
        "Change of optical channel power in dB over the complete transmission band" 
    ::=  { deployProvIfEntry 30 }

deployProvIfGain OBJECT-TYPE
    SYNTAX      FspR7Gain
    MAX-ACCESS  read-write
    STATUS      current
    DESCRIPTION
        "Gain" 
    ::=  { deployProvIfEntry 31 }

deployProvIfAdmin OBJECT-TYPE
    SYNTAX      FspR7AdminState
    MAX-ACCESS  read-write
    STATUS      current
    DESCRIPTION   "The Adminstrative State."
    ::=  { deployProvIfEntry 32 }

deployProvIfAttenuationGradient OBJECT-TYPE
    SYNTAX      Unsigned32 (5..990 | 4294967295) 
    UNITS       "0.1 dB/min"
    MAX-ACCESS  read-write
    STATUS      current
    DESCRIPTION   "Attenuation Gradient Threshold on Receive Fiber. Applies to both
         TRMT and RCV directions; but threshold violation is reported for
         each direction separately by the 'tapping' alarms: INTRUDE-RCV
         and INTRUDE-TRMT."
    ::=  { deployProvIfEntry 33 }

deployProvIfSigDegThresReceiver OBJECT-TYPE
    SYNTAX      Unsigned32 
    UNITS       "0.1 dB"
    MAX-ACCESS  read-write
    STATUS      current
    DESCRIPTION
        "Signal Degrade Threshold on Receiver. Reported as ATTRMT-SDHT to far end." 
    ::=  { deployProvIfEntry 34 }

deployProvIfTcmCLevel OBJECT-TYPE
    SYNTAX      OtnTcmLevel
    MAX-ACCESS  read-write
    STATUS      current
    DESCRIPTION
        "Activation of Tandem Connection Monitoring Instance C" 
    ::=  { deployProvIfEntry 35 }

deployProvIfSigDegThresOduTcmC OBJECT-TYPE
    SYNTAX      Integer32 (1..100 | -2147483648) 
    UNITS       "%"
    MAX-ACCESS  read-write
    STATUS      current
    DESCRIPTION
        "Background-Block-Error-Based Signal Degradation Definition for TCM-C" 
    ::=  { deployProvIfEntry 36 }

deployProvIfSigDegPeriodOduTcmC OBJECT-TYPE
    SYNTAX      Unsigned32 (2..10 | 4294967295) 
    UNITS       "s"
    MAX-ACCESS  read-write
    STATUS      current
    DESCRIPTION
        "Integration Period of TCMC Signal Segrade" 
    ::=  { deployProvIfEntry 37 }

deployProvIfDisparityCorrection OBJECT-TYPE
    SYNTAX      EnableState
    MAX-ACCESS  read-write
    STATUS      current
    DESCRIPTION
        "Disparity correction" 
    ::=  { deployProvIfEntry 38 }

deployProvIfIpAddr OBJECT-TYPE
    SYNTAX      IpAddress
    MAX-ACCESS  read-write
    STATUS      current
    DESCRIPTION
        "IP Address assigned to LAN IP Interface" 
    ::=  { deployProvIfEntry 39 }

deployProvIfIpMask OBJECT-TYPE
    SYNTAX      IpAddress
    MAX-ACCESS  read-write
    STATUS      current
    DESCRIPTION
        "IP MASK assigned to LAN IP Interface" 
    ::=  { deployProvIfEntry 40 }

deployProvIfOspf OBJECT-TYPE
    SYNTAX      FspR7OspfMode
    MAX-ACCESS  read-write
    STATUS      current
    DESCRIPTION
        "OSPF Routing (Dynamic)" 
    ::=  { deployProvIfEntry 41 }

deployProvIfMetric OBJECT-TYPE
    SYNTAX      Unsigned32 (0..65535 | 4294967295)
    MAX-ACCESS  read-write
    STATUS      current
    DESCRIPTION
        "Routing Metric" 
    ::=  { deployProvIfEntry 42 }

deployProvIfAreaId OBJECT-TYPE
    SYNTAX      IpAddress
    MAX-ACCESS  read-write
    STATUS      current
    DESCRIPTION
        "OSPF Area ID for IP Interface" 
    ::=  { deployProvIfEntry 43 }

deployProvIfTraceFormSonetSection OBJECT-TYPE
    SYNTAX      SonetTraceForm
    MAX-ACCESS  read-write
    STATUS      current
    DESCRIPTION
        "Byte-Length of Trace Compared to Expected" 
    ::=  { deployProvIfEntry 44 }

deployProvIfTraceExpectedSonetSection OBJECT-TYPE
    SYNTAX      OCTET STRING (SIZE(0..62))
    MAX-ACCESS  read-write
    STATUS      current
    DESCRIPTION
        "Expected Sec/RS trace. NULL TRACE implies that no trace comparison is made." 
    ::=  { deployProvIfEntry 45 }

deployProvIfTraceTransmitSonetSection OBJECT-TYPE
    SYNTAX      OCTET STRING (SIZE(0..62))
    MAX-ACCESS  read-write
    STATUS      current
    DESCRIPTION
        "Sec/RS Trace to be Transmitted" 
    ::=  { deployProvIfEntry 46 }

deployProvIfTimModeSonetSection OBJECT-TYPE
    SYNTAX      TimMode
    MAX-ACCESS  read-write
    STATUS      current
    DESCRIPTION
        "SONET Section Trace Identifier Mismatch (TIM) detection/action for TIM defect." 
    ::=  { deployProvIfEntry 47 }

deployProvIfTraceExpectedOtu OBJECT-TYPE
    SYNTAX      OCTET STRING (SIZE(0..15))
    MAX-ACCESS  read-write
    STATUS      current
    DESCRIPTION   "Expected SAPI part of the OTU trace (15 character).
         NULL TRACE implies that no trace comparison is made."
    ::=  { deployProvIfEntry 48 }

deployProvIfTraceTransmitSapiOtu OBJECT-TYPE
    SYNTAX      OCTET STRING (SIZE(0..15))
    MAX-ACCESS  read-write
    STATUS      current
    DESCRIPTION
        "The transmitted SAPI part of the OTU trace (15 character)" 
    ::=  { deployProvIfEntry 49 }

deployProvIfTraceTransmitDapiOtu OBJECT-TYPE
    SYNTAX      OCTET STRING (SIZE(0..15))
    MAX-ACCESS  read-write
    STATUS      current
    DESCRIPTION
        "The transmitted DAPI part of the OTU trace (15 character)" 
    ::=  { deployProvIfEntry 50 }

deployProvIfTraceTransmitOpspOtu OBJECT-TYPE
    SYNTAX      OCTET STRING (SIZE(0..32))
    MAX-ACCESS  read-write
    STATUS      current
    DESCRIPTION
        "The transmitted Operator Specific part of the OTU trace (32 character)" 
    ::=  { deployProvIfEntry 51 }

deployProvIfTimModeOtu OBJECT-TYPE
    SYNTAX      TimMode
    MAX-ACCESS  read-write
    STATUS      current
    DESCRIPTION
        "OTU Trace Identifier Mismatch (TIM) detection/action for TIM defect." 
    ::=  { deployProvIfEntry 52 }

deployProvIfTraceExpectedOdu OBJECT-TYPE
    SYNTAX      OCTET STRING (SIZE(0..15))
    MAX-ACCESS  read-write
    STATUS      current
    DESCRIPTION   "Expected SAPI part of the ODU trace (15 character).
         NULL TRACE implies that no trace comparison is made."
    ::=  { deployProvIfEntry 53 }

deployProvIfTraceTransmitSapiOdu OBJECT-TYPE
    SYNTAX      OCTET STRING (SIZE(0..15))
    MAX-ACCESS  read-write
    STATUS      current
    DESCRIPTION
        "The transmitted SAPI part of the ODU trace (15 character)" 
    ::=  { deployProvIfEntry 54 }

deployProvIfTraceTransmitDapiOdu OBJECT-TYPE
    SYNTAX      OCTET STRING (SIZE(0..15))
    MAX-ACCESS  read-write
    STATUS      current
    DESCRIPTION
        "The transmitted DAPI part of the ODU trace (15 character)" 
    ::=  { deployProvIfEntry 55 }

deployProvIfTraceTransmitOpspOdu OBJECT-TYPE
    SYNTAX      OCTET STRING (SIZE(0..32))
    MAX-ACCESS  read-write
    STATUS      current
    DESCRIPTION
        "The transmitted Operator Specific part of the ODU trace (32 character)" 
    ::=  { deployProvIfEntry 56 }

deployProvIfTimModeOdu OBJECT-TYPE
    SYNTAX      TimMode
    MAX-ACCESS  read-write
    STATUS      current
    DESCRIPTION
        "Detection of TIM-ODU Condition can be configured" 
    ::=  { deployProvIfEntry 57 }

deployProvIfTraceExpectedOduTcmA OBJECT-TYPE
    SYNTAX      OCTET STRING (SIZE(0..15))
    MAX-ACCESS  read-write
    STATUS      current
    DESCRIPTION   "Expected SAPI part of the TCMA trace (15 character).
         NULL TRACE-TCM implies that no trace comparison is made."
    ::=  { deployProvIfEntry 58 }

deployProvIfTraceTransmitSapiOduTcmA OBJECT-TYPE
    SYNTAX      OCTET STRING (SIZE(0..15))
    MAX-ACCESS  read-write
    STATUS      current
    DESCRIPTION
        "The transmitted SAPI part of the TCMA trace (15 character)" 
    ::=  { deployProvIfEntry 59 }

deployProvIfTraceTransmitDapiOduTcmA OBJECT-TYPE
    SYNTAX      OCTET STRING (SIZE(0..15))
    MAX-ACCESS  read-write
    STATUS      current
    DESCRIPTION
        "The transmitted DAPI part of the TCMA trace (15 character)" 
    ::=  { deployProvIfEntry 60 }

deployProvIfTraceTransmitOpspOduTcmA OBJECT-TYPE
    SYNTAX      OCTET STRING (SIZE(0..32))
    MAX-ACCESS  read-write
    STATUS      current
    DESCRIPTION
        "The transmitted Operator Specific part of the TCMA trace (32 character)" 
    ::=  { deployProvIfEntry 61 }

deployProvIfTimModeOduTcmA OBJECT-TYPE
    SYNTAX      TimMode
    MAX-ACCESS  read-write
    STATUS      current
    DESCRIPTION
        "TCM_A Trace Identifier Mismatch (TIM) detection/action for TIM defect." 
    ::=  { deployProvIfEntry 62 }

deployProvIfTraceExpectedOduTcmB OBJECT-TYPE
    SYNTAX      OCTET STRING (SIZE(0..15))
    MAX-ACCESS  read-write
    STATUS      current
    DESCRIPTION
        "Expected SAPI part of the TCMB trace (15 character). NULL TRACE-TCM implies that no trace comparison is made." 
    ::=  { deployProvIfEntry 63 }

deployProvIfTraceTransmitSapiOduTcmB OBJECT-TYPE
    SYNTAX      OCTET STRING (SIZE(0..15))
    MAX-ACCESS  read-write
    STATUS      current
    DESCRIPTION
        "The transmitted SAPI part of the TCMB trace (15 character)" 
    ::=  { deployProvIfEntry 64 }

deployProvIfTraceTransmitDapiOduTcmB OBJECT-TYPE
    SYNTAX      OCTET STRING (SIZE(0..15))
    MAX-ACCESS  read-write
    STATUS      current
    DESCRIPTION
        "The transmitted DAPI part of the TCMB trace (15 character)" 
    ::=  { deployProvIfEntry 65 }

deployProvIfTraceTransmitOpspOduTcmB OBJECT-TYPE
    SYNTAX      OCTET STRING (SIZE(0..32))
    MAX-ACCESS  read-write
    STATUS      current
    DESCRIPTION
        "The transmitted Operator Specific part of the TCMB trace (32 character)" 
    ::=  { deployProvIfEntry 66 }

deployProvIfTimModeOduTcmB OBJECT-TYPE
    SYNTAX      TimMode
    MAX-ACCESS  read-write
    STATUS      current
    DESCRIPTION
        "TCM_B Trace Identifier Mismatch (TIM) detection/action for TIM defect." 
    ::=  { deployProvIfEntry 67 }

deployProvIfTraceExpectedOduTcmC OBJECT-TYPE
    SYNTAX      OCTET STRING (SIZE(0..15))
    MAX-ACCESS  read-write
    STATUS      current
    DESCRIPTION   "Expected SAPI part of the TCMC trace (15 character).
         NULL TRACE-TCM implies that no trace comparison is made."
    ::=  { deployProvIfEntry 68 }

deployProvIfTraceTransmitSapiOduTcmC OBJECT-TYPE
    SYNTAX      OCTET STRING (SIZE(0..15))
    MAX-ACCESS  read-write
    STATUS      current
    DESCRIPTION
        "The transmitted SAPI part of the TCMC trace (15 character)" 
    ::=  { deployProvIfEntry 69 }

deployProvIfTraceTransmitDapiOduTcmC OBJECT-TYPE
    SYNTAX      OCTET STRING (SIZE(0..15))
    MAX-ACCESS  read-write
    STATUS      current
    DESCRIPTION
        "The transmitted DAPI part of the TCMC trace (15 character)" 
    ::=  { deployProvIfEntry 70 }

deployProvIfTraceTransmitOpspOduTcmC OBJECT-TYPE
    SYNTAX      OCTET STRING (SIZE(0..32))
    MAX-ACCESS  read-write
    STATUS      current
    DESCRIPTION
        "The transmitted Operator Specific part of the TCMC trace (32 character)" 
    ::=  { deployProvIfEntry 71 }

deployProvIfTimModeOduTcmC OBJECT-TYPE
    SYNTAX      TimMode
    MAX-ACCESS  read-write
    STATUS      current
    DESCRIPTION
        "TCM_C Trace Identifier Mismatch (TIM) detection/action for TIM defect." 
    ::=  { deployProvIfEntry 72 }

deployProvIfChannelProvisioning OBJECT-TYPE
    SYNTAX      FspR7ChannelIdentifier
    MAX-ACCESS  read-write
    STATUS      current
    DESCRIPTION
        "Channel" 
    ::=  { deployProvIfEntry 73 }

deployProvIfVariableGain OBJECT-TYPE
    SYNTAX      Unsigned32 (0..350 | 4294967295) 
    UNITS       "0.1 dB"
    MAX-ACCESS  read-write
    STATUS      current
    DESCRIPTION
        "Variable Gain of EDFA" 
    ::=  { deployProvIfEntry 74 }

deployProvIfBand OBJECT-TYPE
    SYNTAX      FspR7OpticalBand
    MAX-ACCESS  read-write
    STATUS      current
    DESCRIPTION   "The The optical band of the module."
    ::=  { deployProvIfEntry 75 }

deployProvIfSigDegThreshold OBJECT-TYPE
    SYNTAX      Unsigned32 (1..10000 | 4294967295)
    MAX-ACCESS  read-write
    STATUS      current
    DESCRIPTION
        "Threshold for number of errors (CV or CV+DE) in one second" 
    ::=  { deployProvIfEntry 76 }

deployProvIfSigDegPeriodIntegration OBJECT-TYPE
    SYNTAX      Unsigned32 (1..10 | 4294967295) 
    UNITS       "s"
    MAX-ACCESS  read-write
    STATUS      current
    DESCRIPTION
        "Integration Period for Signal degrade" 
    ::=  { deployProvIfEntry 77 }

deployProvIfVoaMode OBJECT-TYPE
    SYNTAX      FspR7VoaMode
    MAX-ACCESS  read-write
    STATUS      current
    DESCRIPTION
        "VOA operating mode" 
    ::=  { deployProvIfEntry 78 }

deployProvIfOpticalSetPoint OBJECT-TYPE
    SYNTAX      Integer32 (-250..100 | -2147483648) 
    UNITS       "0.1 dBm"
    MAX-ACCESS  read-write
    STATUS      current
    DESCRIPTION
        "Sets the optical power for power equalization in ROADM or for channel power control in OPCM" 
    ::=  { deployProvIfEntry 79 }

deployProvIfVoaSetpoint OBJECT-TYPE
    SYNTAX      Unsigned32 (0..300 | 4294967295) 
    UNITS       "0.1 dB"
    MAX-ACCESS  read-write
    STATUS      current
    DESCRIPTION
        "Sets the optical attenuation of VOA" 
    ::=  { deployProvIfEntry 80 }

deployProvIfLanAid OBJECT-TYPE
    SYNTAX      EntityIndex
    MAX-ACCESS  read-write
    STATUS      current
    DESCRIPTION
        "AID of LAN" 
    ::=  { deployProvIfEntry 81 }

deployProvIfAprHighThreshold OBJECT-TYPE
    SYNTAX      Unsigned32 
    UNITS       "0.1 dBm"
    MAX-ACCESS  read-write
    STATUS      current
    DESCRIPTION
        "Automatic Power Reduction High Threshold" 
    ::=  { deployProvIfEntry 82 }

deployProvIfPumpPower OBJECT-TYPE
    SYNTAX      Integer32 (115..138 | -2147483648) 
    UNITS       "0.2 dBm"
    MAX-ACCESS  read-write
    STATUS      current
    DESCRIPTION
        "Total raman pump power" 
    ::=  { deployProvIfEntry 83 }

deployProvIfIpType OBJECT-TYPE
    SYNTAX      FspR7IpType
    MAX-ACCESS  read-write
    STATUS      current
    DESCRIPTION
        "Type of IP configuration" 
    ::=  { deployProvIfEntry 84 }

deployProvIfWdmRxChannel OBJECT-TYPE
    SYNTAX      FspR7ChannelIdentifier
    MAX-ACCESS  read-write
    STATUS      current
    DESCRIPTION
        "Configuration of Rx optical channel" 
    ::=  { deployProvIfEntry 85 }

deployProvIfSigDegThresSonetSection OBJECT-TYPE
    SYNTAX      FspR7BERThresholdSection
    MAX-ACCESS  read-write
    STATUS      current
    DESCRIPTION
        "Bit-Error-Based Degradation Definition for SONET (standard integration period)" 
    ::=  { deployProvIfEntry 86 }

deployProvIfSigDegThresSdhSection OBJECT-TYPE
    SYNTAX      Unsigned32 (1..100 | 4294967295) 
    UNITS       "%"
    MAX-ACCESS  read-write
    STATUS      current
    DESCRIPTION
        "Block-Error-Based Degradation Definition for SDH (standard integration period).
         Defined as percentage Background Block Errors (30% default) evaluated
         over a defined period (SDPER-RS)." 
    ::=  { deployProvIfEntry 87 }

deployProvIfSigDegPeriodSdhSection OBJECT-TYPE
    SYNTAX      Unsigned32 (2..10 | 4294967295) 
    UNITS       "s"
    MAX-ACCESS  read-write
    STATUS      current
    DESCRIPTION
        "Provisionable Signal Degrade Integration Period for SDH" 
    ::=  { deployProvIfEntry 88 }

deployProvIfDispersionMode OBJECT-TYPE
    SYNTAX      FspR7DispersionModes
    MAX-ACCESS  read-write
    STATUS      current
    DESCRIPTION
        "Chromatic Dispersion Compensation Mode" 
    ::=  { deployProvIfEntry 89 }

deployProvIfDispersionSetting OBJECT-TYPE
    SYNTAX      Integer32 (-50000..50000 | -2147483648) 
    UNITS       "ps/nm"
    MAX-ACCESS  read-write
    STATUS      current
    DESCRIPTION
        "Chromatic Dispersion Compensation setting on module" 
    ::=  { deployProvIfEntry 90 }

deployProvIfOffset OBJECT-TYPE
    SYNTAX      Integer32 (10..30 | -2147483648) 
    UNITS       "0.1 dB"
    MAX-ACCESS  read-write
    STATUS      current
    DESCRIPTION   "Sets the offset for the mean optical power for power equalization in ROADM"
    ::=  { deployProvIfEntry 91 }

deployProvIfFunction OBJECT-TYPE
    SYNTAX      FspR7InterfaceFunction
    MAX-ACCESS  read-write
    STATUS      current
    DESCRIPTION
        "Interface Function" 
    ::=  { deployProvIfEntry 92 }

deployProvIfPortMode OBJECT-TYPE
    SYNTAX      FspR7PortMode
    MAX-ACCESS  read-write
    STATUS      current
    DESCRIPTION
        "Port Mode" 
    ::=  { deployProvIfEntry 93 }

deployProvIfPortRole OBJECT-TYPE
    SYNTAX      FspR7PortRole
    MAX-ACCESS  read-write
    STATUS      current
    DESCRIPTION
        "ADVA cloud Port Roles" 
    ::=  { deployProvIfEntry 94 }

deployProvIfUtag OBJECT-TYPE
    SYNTAX      FspR7UntaggedFrames
    MAX-ACCESS  read-write
    STATUS      current
    DESCRIPTION
        "If untagged frames shall be enabled on this port or not." 
    ::=  { deployProvIfEntry 95 }

deployProvIfPvid OBJECT-TYPE
    SYNTAX      Unsigned32 (1..4095 | 4294967295)
    MAX-ACCESS  read-write
    STATUS      current
    DESCRIPTION
        "Default VLAN ID (both STAG/CTAG mode) in case UTAG is enabled" 
    ::=  { deployProvIfEntry 96 }

deployProvIfPriority OBJECT-TYPE
    SYNTAX      Unsigned32 (0..7 | 4294967295)
    MAX-ACCESS  read-write
    STATUS      current
    DESCRIPTION
        "Default PCP in case UTAG is Enabled. The Prio may be remapped in the EVC." 
    ::=  { deployProvIfEntry 97 }

deployProvIfStagType OBJECT-TYPE
    SYNTAX      FspR7SnmpHexString
    MAX-ACCESS  read-write
    STATUS      current
    DESCRIPTION
        "TAG type field" 
    ::=  { deployProvIfEntry 98 }

deployProvIfCac OBJECT-TYPE
    SYNTAX      FspR7L2CacEnable
    MAX-ACCESS  read-write
    STATUS      current
    DESCRIPTION
        "Enable of CAC" 
    ::=  { deployProvIfEntry 99 }

deployProvIfMaxFrameSize OBJECT-TYPE
    SYNTAX      Unsigned32 (1518..9600 | 4294967295)
    MAX-ACCESS  read-write
    STATUS      current
    DESCRIPTION
        "Max Frame Size" 
    ::=  { deployProvIfEntry 100 }

deployProvIfVethAid OBJECT-TYPE
    SYNTAX      EntityIndex
    MAX-ACCESS  read-write
    STATUS      current
    DESCRIPTION
        "Shows if PORT is a member in the LAG with the VETH AID" 
    ::=  { deployProvIfEntry 101 }

deployProvIfLagPrio OBJECT-TYPE
    SYNTAX      Unsigned32 (0..65535 | 4294967295)
    MAX-ACCESS  read-write
    STATUS      current
    DESCRIPTION
        "Part of ID. Port pri that defines standby." 
    ::=  { deployProvIfEntry 102 }

deployProvIfLagPortType OBJECT-TYPE
    SYNTAX      FspR7LagPortType
    MAX-ACCESS  read-write
    STATUS      current
    DESCRIPTION
        "Type/Speed of connected ports in the Link Aggregation Group" 
    ::=  { deployProvIfEntry 103 }

deployProvIfLagActivePorts OBJECT-TYPE
    SYNTAX      Unsigned32 (1..12 | 4294967295)
    MAX-ACCESS  read-write
    STATUS      current
    DESCRIPTION
        "Number of active ports in the Link Aggregation Group" 
    ::=  { deployProvIfEntry 104 }

deployProvIfLacpMode OBJECT-TYPE
    SYNTAX      FspR7LacpMode
    MAX-ACCESS  read-write
    STATUS      current
    DESCRIPTION
        "Enable of LACP state machine" 
    ::=  { deployProvIfEntry 105 }

deployProvIfLagLoadBallanceSource OBJECT-TYPE
    SYNTAX      FspR7LagLoadBallanceSource
    MAX-ACCESS  read-write
    STATUS      current
    DESCRIPTION
        "What source is used in the load balance calculation" 
    ::=  { deployProvIfEntry 106 }

deployProvIfLacpTimeout OBJECT-TYPE
    SYNTAX      FspR7LacpTimeout
    MAX-ACCESS  read-write
    STATUS      current
    DESCRIPTION
        "Timeout of the LACP" 
    ::=  { deployProvIfEntry 107 }

deployProvIfFarEndCommunication OBJECT-TYPE
    SYNTAX      FspR7YesNo
    MAX-ACCESS  read-write
    STATUS      current
    DESCRIPTION
        "Used for Optojack plugs; Communication to Far End Plug is observed" 
    ::=  { deployProvIfEntry 108 }

deployProvIfEqlzAdmin OBJECT-TYPE
    SYNTAX      FspR7EqlzAdminState
    MAX-ACCESS  read-write
    STATUS      current
    DESCRIPTION   "Scheduled Equalization Administration"
    ::=  { deployProvIfEntry 109 }

deployProvIfTxOffDelay OBJECT-TYPE
    SYNTAX      FspR7EnableDisable
    MAX-ACCESS  read-write
    STATUS      current
    DESCRIPTION
        "Enable or disable TXOFFHOLD Period for Error Forwarding and LKDO-OFF Consequent Action." 
    ::=  { deployProvIfEntry 110 }

deployProvIfOpuPayloadType OBJECT-TYPE
    SYNTAX      FspR7OpuPayloadType
    MAX-ACCESS  read-write
    STATUS      current
    DESCRIPTION
        "OPU Payload Type Indicator" 
    ::=  { deployProvIfEntry 111 }

deployProvIfOscOpticalSetpoint OBJECT-TYPE
    SYNTAX      Integer32 (-250..50 | -2147483648) 
    UNITS       "0.1 dBm"
    MAX-ACCESS  read-write
    STATUS      current
    DESCRIPTION
        "Sets the OSC optical power" 
    ::=  { deployProvIfEntry 112 }

deployProvIfFiberBrand OBJECT-TYPE
    SYNTAX      FspR7FiberBrand
    MAX-ACCESS  read-write
    STATUS      current
    DESCRIPTION
        "Brand of fiber present in the fiber plant" 
    ::=  { deployProvIfEntry 113 }

deployProvIfTiltSet OBJECT-TYPE
    SYNTAX      FspR7TiltSet
    MAX-ACCESS  read-write
    STATUS      current
    DESCRIPTION
        "Tilt setting as discrete values versus a range" 
    ::=  { deployProvIfEntry 114 }

deployProvIfXfpDecisionThres OBJECT-TYPE
    SYNTAX      FspR7XfpDecisionThres
    MAX-ACCESS  read-write
    STATUS      current
    DESCRIPTION
        "XFP Decision threshold setting" 
    ::=  { deployProvIfEntry 115 }

deployProvIfAutoPTassignment OBJECT-TYPE
    SYNTAX      FspR7ManualAuto
    MAX-ACCESS  read-write
    STATUS      current
    DESCRIPTION
        "Auto assignment of ODU PT" 
    ::=  { deployProvIfEntry 116 }

deployProvIfTributarySlotMethod OBJECT-TYPE
    SYNTAX      FspR7ManualAuto
    MAX-ACCESS  read-write
    STATUS      current
    DESCRIPTION
        "Tributary Slot assignment method" 
    ::=  { deployProvIfEntry 117 }

deployProvIfOduTribPortNo OBJECT-TYPE
    SYNTAX      SnmpAdminString
    MAX-ACCESS  read-write
    STATUS      current
    DESCRIPTION
        "ODU Tributary Port Number" 
    ::=  { deployProvIfEntry 118 }

deployProvIfOduTribTimeSlottNo OBJECT-TYPE
    SYNTAX      SnmpAdminString
    MAX-ACCESS  read-write
    STATUS      current
    DESCRIPTION   "ODU Tributary slot number. Multiple values can be entered as a string, separated by commas or given as a range.
         For capabilities objects possible number of slots and valid range are displayed in a form:
         [1,2,3,8][count: 1-1]
         In first brackets valid slots are shown and in the second possible number of slots."
    ::=  { deployProvIfEntry 119 }

deployProvIfRevertiveMode OBJECT-TYPE
    SYNTAX      ApsRevertMode
    MAX-ACCESS  read-write
    STATUS      current
    DESCRIPTION
        "Revertive Protection Switching" 
    ::=  { deployProvIfEntry 120 }

deployProvIfLaserDelayTimer OBJECT-TYPE
    SYNTAX      FspR7LaserDelayTimer
    MAX-ACCESS  read-write
    STATUS      current
    DESCRIPTION
        "Relevant only when ERRFWD=LSROFF. Enables/disables the
         possibility to delay turning off and on the laser.
         This applies to the case when turning off the laser
         is done as an error forwarding mechanism." 
    ::=  { deployProvIfEntry 121 }

deployProvIfLaserOffTimer OBJECT-TYPE
    SYNTAX      Unsigned32 (1..1000 | 4294967295) 
    UNITS       "ms"
    MAX-ACCESS  read-write
    STATUS      current
    DESCRIPTION
        "Delay before laser is swiched off" 
    ::=  { deployProvIfEntry 122 }

deployProvIfLaserOnTimer OBJECT-TYPE
    SYNTAX      Unsigned32 (1..1000 | 4294967295) 
    UNITS       "ms"
    MAX-ACCESS  read-write
    STATUS      current
    DESCRIPTION
        "Delay before laser is switched on" 
    ::=  { deployProvIfEntry 123 }

deployProvIfLaneChannelSetting OBJECT-TYPE
    SYNTAX      FspR7ChannelIdentifier
    MAX-ACCESS  read-write
    STATUS      current
    DESCRIPTION
        "Lane Channel Setting" 
    ::=  { deployProvIfEntry 124 }

deployProvIfBip OBJECT-TYPE
    SYNTAX      FspR7Bip
    MAX-ACCESS  read-write
    STATUS      current
    DESCRIPTION
        "Bit Interleaved Parity" 
    ::=  { deployProvIfEntry 125 }

deployProvIfCodeGain OBJECT-TYPE
    SYNTAX      FspR7CodeGain
    MAX-ACCESS  read-write
    STATUS      current
    DESCRIPTION
        "Forward Error Correction Coding gain" 
    ::=  { deployProvIfEntry 126 }

deployProvIfEdfaPwrOut OBJECT-TYPE
    SYNTAX      FspR7EdfaOutputPowerRating
    MAX-ACCESS  read-write
    STATUS      current
    DESCRIPTION
        "Optical Output Power Rating - Provision" 
    ::=  { deployProvIfEntry 127 }

deployProvIfPrio OBJECT-TYPE
    SYNTAX      Unsigned32 (0..255 | 4294967295)
    MAX-ACCESS  read-write
    STATUS      current
    DESCRIPTION
        "Priority" 
    ::=  { deployProvIfEntry 128 }

deployProvIfAuthType OBJECT-TYPE
    SYNTAX      FspR7CpAuthType
    MAX-ACCESS  read-write
    STATUS      current
    DESCRIPTION
        "OSPF Authentication Type" 
    ::=  { deployProvIfEntry 129 }

deployProvIfAuthString OBJECT-TYPE
    SYNTAX      SnmpAdminString
    MAX-ACCESS  read-write
    STATUS      current
    DESCRIPTION
        "OSPF Authentication Key/String depending on Authentication Type" 
    ::=  { deployProvIfEntry 130 }

deployProvIfSigDegPcslThreshold OBJECT-TYPE
    SYNTAX      Unsigned32 (1..100 | 4294967295) 
    UNITS       "%"
    MAX-ACCESS  read-write
    STATUS      current
    DESCRIPTION
        "Block-Error-Based Degradation Definition for Physical Coding Sublayer" 
    ::=  { deployProvIfEntry 131 }

deployProvIfCapTable OBJECT-TYPE
    SYNTAX      SEQUENCE OF DeployProvIfCapEntry
    MAX-ACCESS  not-accessible
    STATUS      current
    DESCRIPTION   "Contains entries for provisioning of interfaces."
    ::=  { facilityDeployProv 2  }

deployProvIfCapEntry OBJECT-TYPE
    SYNTAX      DeployProvIfCapEntry
    MAX-ACCESS  not-accessible
    STATUS      current
    DESCRIPTION   "All interfaces which are provisioned(or during deployProv)
         will have an entry in this table."
    INDEX       { entityIndex }
    ::=  { deployProvIfCapTable 1 }

DeployProvIfCapEntry ::=  SEQUENCE
  { deployProvIfCapRowStatus FspR7RowStatusCaps,
    deployProvIfCapForceDestroy FspR7ForcedStatusCaps,
    deployProvIfCapType FspR7InterfaceTypeCaps,
    deployProvIfCapPayload OtnPayloadTypeCaps,
    deployProvIfCapBehaviour FspR7PortBehaviourCaps,
    deployProvIfCapTerminationLevel OhTerminationLevelCaps,
    deployProvIfCapAlsMode FspR7AlsModeCaps,
    deployProvIfCapErrorForwarding FspR7ErrorFwdModeCaps,
    deployProvIfCapLaserOffDelayFunction EnableStateCaps,
    deployProvIfCapFecType FspR7FecTypeCaps,
    deployProvIfCapTimingSource SonetTimingSourceCaps,
    deployProvIfCapTcmALevel OtnTcmLevelCaps,
    deployProvIfCapTcmBLevel OtnTcmLevelCaps,
    deployProvIfCapSigDegThresSonetLine FspR7BERThresholdCaps,
    deployProvIfCapSigDegThresSdhMs FspR7Unsigned32Caps,
    deployProvIfCapSignalDegradePeriod FspR7Unsigned32Caps,
    deployProvIfCapAutonegotiation EnableStateCaps,
    deployProvIfCapBitrate FspR7BitrateCaps,
    deployProvIfCapDuplex EthDuplexModeCaps,
    deployProvIfCapFlowControl FspR7FlowControlModeCaps,
    deployProvIfCapOtnStuffing FspR7StuffCaps,
    deployProvIfCapSigDegThresOtu FspR7Integer32Caps,
    deployProvIfCapSigDegPeriodOtu FspR7Unsigned32Caps,
    deployProvIfCapSigDegThresOdu FspR7Integer32Caps,
    deployProvIfCapSigDegPeriodOdu FspR7Unsigned32Caps,
    deployProvIfCapSigDegThresOduTcmA FspR7Integer32Caps,
    deployProvIfCapSigDegPeriodOduTcmA FspR7Unsigned32Caps,
    deployProvIfCapSigDegThresOduTcmB FspR7Integer32Caps,
    deployProvIfCapSigDegPeriodOduTcmB FspR7Unsigned32Caps,
    deployProvIfCapTilt FspR7Integer32Caps,
    deployProvIfCapGain FspR7GainCaps,
    deployProvIfCapAdmin FspR7AdminStateCaps,
    deployProvIfCapAttenuationGradient FspR7Unsigned32Caps,
    deployProvIfCapSigDegThresReceiver FspR7Unsigned32Caps,
    deployProvIfCapTcmCLevel OtnTcmLevelCaps,
    deployProvIfCapSigDegThresOduTcmC FspR7Integer32Caps,
    deployProvIfCapSigDegPeriodOduTcmC FspR7Unsigned32Caps,
    deployProvIfCapDisparityCorrection EnableStateCaps,
    deployProvIfCapIpAddr FspR7YesNo,
    deployProvIfCapIpMask FspR7YesNo,
    deployProvIfCapOspf FspR7OspfModeCaps,
    deployProvIfCapMetric FspR7Unsigned32Caps,
    deployProvIfCapAreaId FspR7YesNo,
    deployProvIfCapTraceFormSonetSection SonetTraceFormCaps,
    deployProvIfCapTraceExpectedSonetSection Integer32,
    deployProvIfCapTraceTransmitSonetSection Integer32,
    deployProvIfCapTimModeSonetSection TimModeCaps,
    deployProvIfCapTraceExpectedOtu Integer32,
    deployProvIfCapTraceTransmitSapiOtu Integer32,
    deployProvIfCapTraceTransmitDapiOtu Integer32,
    deployProvIfCapTraceTransmitOpspOtu Integer32,
    deployProvIfCapTimModeOtu TimModeCaps,
    deployProvIfCapTraceExpectedOdu Integer32,
    deployProvIfCapTraceTransmitSapiOdu Integer32,
    deployProvIfCapTraceTransmitDapiOdu Integer32,
    deployProvIfCapTraceTransmitOpspOdu Integer32,
    deployProvIfCapTimModeOdu TimModeCaps,
    deployProvIfCapTraceExpectedOduTcmA Integer32,
    deployProvIfCapTraceTransmitSapiOduTcmA Integer32,
    deployProvIfCapTraceTransmitDapiOduTcmA Integer32,
    deployProvIfCapTraceTransmitOpspOduTcmA Integer32,
    deployProvIfCapTimModeOduTcmA TimModeCaps,
    deployProvIfCapTraceExpectedOduTcmB Integer32,
    deployProvIfCapTraceTransmitSapiOduTcmB Integer32,
    deployProvIfCapTraceTransmitDapiOduTcmB Integer32,
    deployProvIfCapTraceTransmitOpspOduTcmB Integer32,
    deployProvIfCapTimModeOduTcmB TimModeCaps,
    deployProvIfCapTraceExpectedOduTcmC Integer32,
    deployProvIfCapTraceTransmitSapiOduTcmC Integer32,
    deployProvIfCapTraceTransmitDapiOduTcmC Integer32,
    deployProvIfCapTraceTransmitOpspOduTcmC Integer32,
    deployProvIfCapTimModeOduTcmC TimModeCaps,
    deployProvIfCapChannelProvisioning FspR7ChannelIdentifierCaps,
    deployProvIfCapVariableGain FspR7Unsigned32Caps,
    deployProvIfCapBand FspR7OpticalBandCaps,
    deployProvIfCapSigDegThreshold FspR7Unsigned32Caps,
    deployProvIfCapSigDegPeriodIntegration FspR7Unsigned32Caps,
    deployProvIfCapVoaMode FspR7VoaModeCaps,
    deployProvIfCapOpticalSetPoint FspR7Integer32Caps,
    deployProvIfCapVoaSetpoint FspR7Unsigned32Caps,
    deployProvIfCapLanAid Integer32,
    deployProvIfCapAprHighThreshold FspR7Unsigned32Caps,
    deployProvIfCapPumpPower FspR7Integer32Caps,
    deployProvIfCapIpType FspR7IpTypeCaps,
    deployProvIfCapWdmRxChannel FspR7ChannelIdentifierCaps,
    deployProvIfCapSigDegThresSonetSection FspR7BERThresholdSectionCaps,
    deployProvIfCapSigDegThresSdhSection FspR7Unsigned32Caps,
    deployProvIfCapSigDegPeriodSdhSection FspR7Unsigned32Caps,
    deployProvIfCapDispersionMode FspR7DispersionModesCaps,
    deployProvIfCapDispersionSetting FspR7Integer32Caps,
    deployProvIfCapOffset FspR7Integer32Caps,
    deployProvIfCapFunction FspR7InterfaceFunctionCaps,
    deployProvIfCapPortMode FspR7PortModeCaps,
    deployProvIfCapPortRole FspR7PortRoleCaps,
    deployProvIfCapUtag FspR7UntaggedFramesCaps,
    deployProvIfCapPvid FspR7Unsigned32Caps,
    deployProvIfCapPriority FspR7Unsigned32Caps,
    deployProvIfCapStagType Integer32,
    deployProvIfCapCac FspR7L2CacEnableCaps,
    deployProvIfCapMaxFrameSize FspR7Unsigned32Caps,
    deployProvIfCapVethAid Integer32,
    deployProvIfCapLagPrio FspR7Unsigned32Caps,
    deployProvIfCapLagPortType FspR7LagPortTypeCaps,
    deployProvIfCapLagActivePorts FspR7Unsigned32Caps,
    deployProvIfCapLacpMode FspR7LacpModeCaps,
    deployProvIfCapLagLoadBallanceSource FspR7LagLoadBallanceSourceCaps,
    deployProvIfCapLacpTimeout FspR7LacpTimeoutCaps,
    deployProvIfCapFarEndCommunication FspR7YesNoCaps,
    deployProvIfCapEqlzAdmin FspR7EqlzAdminStateCaps,
    deployProvIfCapTxOffDelay FspR7EnableDisableCaps,
    deployProvIfCapOpuPayloadType FspR7OpuPayloadTypeCaps,
    deployProvIfCapOscOpticalSetpoint FspR7Integer32Caps,
    deployProvIfCapFiberBrand FspR7FiberBrandCaps,
    deployProvIfCapTiltSet FspR7TiltSetCaps,
    deployProvIfCapXfpDecisionThres FspR7XfpDecisionThresCaps,
    deployProvIfCapAutoPTassignment FspR7ManualAutoCaps,
    deployProvIfCapTributarySlotMethod FspR7ManualAutoCaps,
    deployProvIfCapOduTribPortNo SnmpAdminString,
    deployProvIfCapOduTribTimeSlottNo SnmpAdminString,
    deployProvIfCapRevertiveMode ApsRevertModeCaps,
    deployProvIfCapLaserDelayTimer FspR7LaserDelayTimerCaps,
    deployProvIfCapLaserOffTimer FspR7Unsigned32Caps,
    deployProvIfCapLaserOnTimer FspR7Unsigned32Caps,
    deployProvIfCapLaneChannelSetting FspR7ChannelIdentifierCaps,
    deployProvIfCapBip FspR7BipCaps,
    deployProvIfCapCodeGain FspR7CodeGainCaps,
    deployProvIfCapEdfaPwrOut FspR7EdfaOutputPowerRatingCaps,
    deployProvIfCapPrio FspR7Unsigned32Caps,
    deployProvIfCapAuthType FspR7CpAuthTypeCaps,
    deployProvIfCapAuthString Integer32,
    deployProvIfCapSigDegPcslThreshold FspR7Unsigned32Caps }

deployProvIfCapRowStatus OBJECT-TYPE
    SYNTAX      FspR7RowStatusCaps
    MAX-ACCESS  read-only
    STATUS      current
    DESCRIPTION   "RowStatus"
    ::=  { deployProvIfCapEntry 1 }

deployProvIfCapForceDestroy OBJECT-TYPE
    SYNTAX      FspR7ForcedStatusCaps
    MAX-ACCESS  read-only
    STATUS      current
    DESCRIPTION
        "Forced Destroy" 
    ::=  { deployProvIfCapEntry 2 }

deployProvIfCapType OBJECT-TYPE
    SYNTAX      FspR7InterfaceTypeCaps
    MAX-ACCESS  read-only
    STATUS      current
    DESCRIPTION   "The TYPE defines the transport service type as wrapper with wrapper layer
         termination OR else as payload"
    ::=  { deployProvIfCapEntry 3 }

deployProvIfCapPayload OBJECT-TYPE
    SYNTAX      OtnPayloadTypeCaps
    MAX-ACCESS  read-only
    STATUS      current
    DESCRIPTION   "The payload of the interface (inside a transport overhead).
         Relevant e. g. for OTN cards which wrap a payload into an OTU1/2 wrapper."
    ::=  { deployProvIfCapEntry 4 }

deployProvIfCapBehaviour OBJECT-TYPE
    SYNTAX      FspR7PortBehaviourCaps
    MAX-ACCESS  read-only
    STATUS      current
    DESCRIPTION   "The configured behaviour of the interface. If configured as
         a network interface, the interface will use a WDM laser."
    ::=  { deployProvIfCapEntry 5 }

deployProvIfCapTerminationLevel OBJECT-TYPE
    SYNTAX      OhTerminationLevelCaps
    MAX-ACCESS  read-only
    STATUS      current
    DESCRIPTION
        "Highest signal level hardware removes then generates for transmission." 
    ::=  { deployProvIfCapEntry 6 }

deployProvIfCapAlsMode OBJECT-TYPE
    SYNTAX      FspR7AlsModeCaps
    MAX-ACCESS  read-only
    STATUS      current
    DESCRIPTION   "A configuration request for the Automatic Laser Shutdown (ALS)
         function. Refer to FspR7AlsMode Textual Convention for details."
    ::=  { deployProvIfCapEntry 7 }

deployProvIfCapErrorForwarding OBJECT-TYPE
    SYNTAX      FspR7ErrorFwdModeCaps
    MAX-ACCESS  read-only
    STATUS      current
    DESCRIPTION   "A configuration request for the error forwarding
         function. Refer to FspR7ErrorFwdMode Textual Convention for details."
    ::=  { deployProvIfCapEntry 8 }

deployProvIfCapLaserOffDelayFunction OBJECT-TYPE
    SYNTAX      EnableStateCaps
    MAX-ACCESS  read-only
    STATUS      current
    DESCRIPTION   "A configuration request for the Laser Off Delay function. This function
         delays turning off the laser as a consequent action to a defect."
    ::=  { deployProvIfCapEntry 9 }

deployProvIfCapFecType OBJECT-TYPE
    SYNTAX      FspR7FecTypeCaps
    MAX-ACCESS  read-only
    STATUS      current
    DESCRIPTION   "Configuration of FEC type."
    ::=  { deployProvIfCapEntry 10 }

deployProvIfCapTimingSource OBJECT-TYPE
    SYNTAX      SonetTimingSourceCaps
    MAX-ACCESS  read-only
    STATUS      current
    DESCRIPTION   "The timing source for this interface.
         - internal: used in stand-alone, point-to-point topologies stand-alone (dedicated fiber operation).
         - loopTiming: e.g. used in point-to-point via SONET network and feeder topologies. The default is
         internal(1)."
    ::=  { deployProvIfCapEntry 11 }

deployProvIfCapTcmALevel OBJECT-TYPE
    SYNTAX      OtnTcmLevelCaps
    MAX-ACCESS  read-only
    STATUS      current
    DESCRIPTION   "Configuration of TCMA level."
    ::=  { deployProvIfCapEntry 12 }

deployProvIfCapTcmBLevel OBJECT-TYPE
    SYNTAX      OtnTcmLevelCaps
    MAX-ACCESS  read-only
    STATUS      current
    DESCRIPTION   "Configuration of TCMB level."
    ::=  { deployProvIfCapEntry 13 }

deployProvIfCapSigDegThresSonetLine OBJECT-TYPE
    SYNTAX      FspR7BERThresholdCaps
    MAX-ACCESS  read-only
    STATUS      current
    DESCRIPTION
        "Bit-Error-Based Degradation Definition for SONET (standard integration period)" 
    ::=  { deployProvIfCapEntry 14 }

deployProvIfCapSigDegThresSdhMs OBJECT-TYPE
    SYNTAX      FspR7Unsigned32Caps
    UNITS       "%"
    MAX-ACCESS  read-only
    STATUS      current
    DESCRIPTION
        "Block-Error-Based Degradation Definition for SDH (standard integration period).
         Defined as percentage Background Block Errors (30% default) evaluated
         over a defined period (SDPER-RS)." 
    ::=  { deployProvIfCapEntry 15 }

deployProvIfCapSignalDegradePeriod OBJECT-TYPE
    SYNTAX      FspR7Unsigned32Caps
    UNITS       "s"
    MAX-ACCESS  read-only
    STATUS      current
    DESCRIPTION   "The measurement period in seconds used together with
         the deployProvIfSigDegThresSdhRegSect based on the block error counting method.
         The valid range is 2..10,
         The default being 7."
    ::=  { deployProvIfCapEntry 16 }

deployProvIfCapAutonegotiation OBJECT-TYPE
    SYNTAX      EnableStateCaps
    MAX-ACCESS  read-only
    STATUS      current
    DESCRIPTION
        "Auto Negotiation for the data rate" 
    ::=  { deployProvIfCapEntry 17 }

deployProvIfCapBitrate OBJECT-TYPE
    SYNTAX      FspR7BitrateCaps
    MAX-ACCESS  read-only
    STATUS      current
    DESCRIPTION
        "Provisioned data rate" 
    ::=  { deployProvIfCapEntry 18 }

deployProvIfCapDuplex OBJECT-TYPE
    SYNTAX      EthDuplexModeCaps
    MAX-ACCESS  read-only
    STATUS      current
    DESCRIPTION
        "Duplex Mode (provision), available when Auto Negoiation is Disable (AUTONEG=DISABLE)" 
    ::=  { deployProvIfCapEntry 19 }

deployProvIfCapFlowControl OBJECT-TYPE
    SYNTAX      FspR7FlowControlModeCaps
    MAX-ACCESS  read-only
    STATUS      current
    DESCRIPTION
        "Flow Control mechanism" 
    ::=  { deployProvIfCapEntry 20 }

deployProvIfCapOtnStuffing OBJECT-TYPE
    SYNTAX      FspR7StuffCaps
    MAX-ACCESS  read-only
    STATUS      current
    DESCRIPTION
        "Indicates if bit/byte stuffing is used in the transport signal." 
    ::=  { deployProvIfCapEntry 21 }

deployProvIfCapSigDegThresOtu OBJECT-TYPE
    SYNTAX      FspR7Integer32Caps
    UNITS       "%"
    MAX-ACCESS  read-only
    STATUS      current
    DESCRIPTION
        "Background-Block-Error-Based Signal Degradation Definition for OTU" 
    ::=  { deployProvIfCapEntry 22 }

deployProvIfCapSigDegPeriodOtu OBJECT-TYPE
    SYNTAX      FspR7Unsigned32Caps
    UNITS       "s"
    MAX-ACCESS  read-only
    STATUS      current
    DESCRIPTION
        "Integration Period for Signal degrade" 
    ::=  { deployProvIfCapEntry 23 }

deployProvIfCapSigDegThresOdu OBJECT-TYPE
    SYNTAX      FspR7Integer32Caps
    UNITS       "%"
    MAX-ACCESS  read-only
    STATUS      current
    DESCRIPTION
        "Background-Block-Error-Based Signal Degradation Definition for ODU" 
    ::=  { deployProvIfCapEntry 24 }

deployProvIfCapSigDegPeriodOdu OBJECT-TYPE
    SYNTAX      FspR7Unsigned32Caps
    UNITS       "s"
    MAX-ACCESS  read-only
    STATUS      current
    DESCRIPTION
        "Integration Period for Signal degrade" 
    ::=  { deployProvIfCapEntry 25 }

deployProvIfCapSigDegThresOduTcmA OBJECT-TYPE
    SYNTAX      FspR7Integer32Caps
    UNITS       "%"
    MAX-ACCESS  read-only
    STATUS      current
    DESCRIPTION
        "Background-Block-Error-Based Signal Degradation Definition for TCM-A" 
    ::=  { deployProvIfCapEntry 26 }

deployProvIfCapSigDegPeriodOduTcmA OBJECT-TYPE
    SYNTAX      FspR7Unsigned32Caps
    UNITS       "s"
    MAX-ACCESS  read-only
    STATUS      current
    DESCRIPTION
        "Integration Period for Signal degrade" 
    ::=  { deployProvIfCapEntry 27 }

deployProvIfCapSigDegThresOduTcmB OBJECT-TYPE
    SYNTAX      FspR7Integer32Caps
    UNITS       "%"
    MAX-ACCESS  read-only
    STATUS      current
    DESCRIPTION
        "Background-Block-Error-Based Signal Degradation Definition for TCM-B" 
    ::=  { deployProvIfCapEntry 28 }

deployProvIfCapSigDegPeriodOduTcmB OBJECT-TYPE
    SYNTAX      FspR7Unsigned32Caps
    UNITS       "s"
    MAX-ACCESS  read-only
    STATUS      current
    DESCRIPTION
        "Integration Period of TCMB Signal Segrade" 
    ::=  { deployProvIfCapEntry 29 }

deployProvIfCapTilt OBJECT-TYPE
    SYNTAX      FspR7Integer32Caps
    UNITS       "0.1 dB"
    MAX-ACCESS  read-only
    STATUS      current
    DESCRIPTION
        "Change of optical channel power in dB over the complete transmission band" 
    ::=  { deployProvIfCapEntry 30 }

deployProvIfCapGain OBJECT-TYPE
    SYNTAX      FspR7GainCaps
    MAX-ACCESS  read-only
    STATUS      current
    DESCRIPTION
        "Gain" 
    ::=  { deployProvIfCapEntry 31 }

deployProvIfCapAdmin OBJECT-TYPE
    SYNTAX      FspR7AdminStateCaps
    MAX-ACCESS  read-only
    STATUS      current
    DESCRIPTION   "The Adminstrative State."
    ::=  { deployProvIfCapEntry 32 }

deployProvIfCapAttenuationGradient OBJECT-TYPE
    SYNTAX      FspR7Unsigned32Caps
    UNITS       "0.1 dB/min"
    MAX-ACCESS  read-only
    STATUS      current
    DESCRIPTION   "Attenuation Gradient Threshold on Receive Fiber. Applies to both
         TRMT and RCV directions; but threshold violation is reported for
         each direction separately by the 'tapping' alarms: INTRUDE-RCV
         and INTRUDE-TRMT."
    ::=  { deployProvIfCapEntry 33 }

deployProvIfCapSigDegThresReceiver OBJECT-TYPE
    SYNTAX      FspR7Unsigned32Caps
    UNITS       "0.1 dB"
    MAX-ACCESS  read-only
    STATUS      current
    DESCRIPTION
        "Signal Degrade Threshold on Receiver. Reported as ATTRMT-SDHT to far end." 
    ::=  { deployProvIfCapEntry 34 }

deployProvIfCapTcmCLevel OBJECT-TYPE
    SYNTAX      OtnTcmLevelCaps
    MAX-ACCESS  read-only
    STATUS      current
    DESCRIPTION
        "Activation of Tandem Connection Monitoring Instance C" 
    ::=  { deployProvIfCapEntry 35 }

deployProvIfCapSigDegThresOduTcmC OBJECT-TYPE
    SYNTAX      FspR7Integer32Caps
    UNITS       "%"
    MAX-ACCESS  read-only
    STATUS      current
    DESCRIPTION
        "Background-Block-Error-Based Signal Degradation Definition for TCM-C" 
    ::=  { deployProvIfCapEntry 36 }

deployProvIfCapSigDegPeriodOduTcmC OBJECT-TYPE
    SYNTAX      FspR7Unsigned32Caps
    UNITS       "s"
    MAX-ACCESS  read-only
    STATUS      current
    DESCRIPTION
        "Integration Period of TCMC Signal Segrade" 
    ::=  { deployProvIfCapEntry 37 }

deployProvIfCapDisparityCorrection OBJECT-TYPE
    SYNTAX      EnableStateCaps
    MAX-ACCESS  read-only
    STATUS      current
    DESCRIPTION
        "Disparity correction" 
    ::=  { deployProvIfCapEntry 38 }

deployProvIfCapIpAddr OBJECT-TYPE
    SYNTAX      FspR7YesNo
    MAX-ACCESS  read-only
    STATUS      current
    DESCRIPTION
        "IP Address assigned to LAN IP Interface" 
    ::=  { deployProvIfCapEntry 39 }

deployProvIfCapIpMask OBJECT-TYPE
    SYNTAX      FspR7YesNo
    MAX-ACCESS  read-only
    STATUS      current
    DESCRIPTION
        "IP MASK assigned to LAN IP Interface" 
    ::=  { deployProvIfCapEntry 40 }

deployProvIfCapOspf OBJECT-TYPE
    SYNTAX      FspR7OspfModeCaps
    MAX-ACCESS  read-only
    STATUS      current
    DESCRIPTION
        "OSPF Routing (Dynamic)" 
    ::=  { deployProvIfCapEntry 41 }

deployProvIfCapMetric OBJECT-TYPE
    SYNTAX      FspR7Unsigned32Caps
    MAX-ACCESS  read-only
    STATUS      current
    DESCRIPTION
        "Routing Metric" 
    ::=  { deployProvIfCapEntry 42 }

deployProvIfCapAreaId OBJECT-TYPE
    SYNTAX      FspR7YesNo
    MAX-ACCESS  read-only
    STATUS      current
    DESCRIPTION
        "OSPF Area ID for IP Interface" 
    ::=  { deployProvIfCapEntry 43 }

deployProvIfCapTraceFormSonetSection OBJECT-TYPE
    SYNTAX      SonetTraceFormCaps
    MAX-ACCESS  read-only
    STATUS      current
    DESCRIPTION
        "Byte-Length of Trace Compared to Expected" 
    ::=  { deployProvIfCapEntry 44 }

deployProvIfCapTraceExpectedSonetSection OBJECT-TYPE
    SYNTAX      Integer32
    MAX-ACCESS  read-only
    STATUS      current
    DESCRIPTION
        "Expected Sec/RS trace. NULL TRACE implies that no trace comparison is made." 
    ::=  { deployProvIfCapEntry 45 }

deployProvIfCapTraceTransmitSonetSection OBJECT-TYPE
    SYNTAX      Integer32
    MAX-ACCESS  read-only
    STATUS      current
    DESCRIPTION
        "Sec/RS Trace to be Transmitted" 
    ::=  { deployProvIfCapEntry 46 }

deployProvIfCapTimModeSonetSection OBJECT-TYPE
    SYNTAX      TimModeCaps
    MAX-ACCESS  read-only
    STATUS      current
    DESCRIPTION
        "SONET Section Trace Identifier Mismatch (TIM) detection/action for TIM defect." 
    ::=  { deployProvIfCapEntry 47 }

deployProvIfCapTraceExpectedOtu OBJECT-TYPE
    SYNTAX      Integer32
    MAX-ACCESS  read-only
    STATUS      current
    DESCRIPTION   "Expected SAPI part of the OTU trace (15 character).
         NULL TRACE implies that no trace comparison is made."
    ::=  { deployProvIfCapEntry 48 }

deployProvIfCapTraceTransmitSapiOtu OBJECT-TYPE
    SYNTAX      Integer32
    MAX-ACCESS  read-only
    STATUS      current
    DESCRIPTION
        "The transmitted SAPI part of the OTU trace (15 character)" 
    ::=  { deployProvIfCapEntry 49 }

deployProvIfCapTraceTransmitDapiOtu OBJECT-TYPE
    SYNTAX      Integer32
    MAX-ACCESS  read-only
    STATUS      current
    DESCRIPTION
        "The transmitted DAPI part of the OTU trace (15 character)" 
    ::=  { deployProvIfCapEntry 50 }

deployProvIfCapTraceTransmitOpspOtu OBJECT-TYPE
    SYNTAX      Integer32
    MAX-ACCESS  read-only
    STATUS      current
    DESCRIPTION
        "The transmitted Operator Specific part of the OTU trace (32 character)" 
    ::=  { deployProvIfCapEntry 51 }

deployProvIfCapTimModeOtu OBJECT-TYPE
    SYNTAX      TimModeCaps
    MAX-ACCESS  read-only
    STATUS      current
    DESCRIPTION
        "OTU Trace Identifier Mismatch (TIM) detection/action for TIM defect." 
    ::=  { deployProvIfCapEntry 52 }

deployProvIfCapTraceExpectedOdu OBJECT-TYPE
    SYNTAX      Integer32
    MAX-ACCESS  read-only
    STATUS      current
    DESCRIPTION   "Expected SAPI part of the ODU trace (15 character).
         NULL TRACE implies that no trace comparison is made."
    ::=  { deployProvIfCapEntry 53 }

deployProvIfCapTraceTransmitSapiOdu OBJECT-TYPE
    SYNTAX      Integer32
    MAX-ACCESS  read-only
    STATUS      current
    DESCRIPTION
        "The transmitted SAPI part of the ODU trace (15 character)" 
    ::=  { deployProvIfCapEntry 54 }

deployProvIfCapTraceTransmitDapiOdu OBJECT-TYPE
    SYNTAX      Integer32
    MAX-ACCESS  read-only
    STATUS      current
    DESCRIPTION
        "The transmitted DAPI part of the ODU trace (15 character)" 
    ::=  { deployProvIfCapEntry 55 }

deployProvIfCapTraceTransmitOpspOdu OBJECT-TYPE
    SYNTAX      Integer32
    MAX-ACCESS  read-only
    STATUS      current
    DESCRIPTION
        "The transmitted Operator Specific part of the ODU trace (32 character)" 
    ::=  { deployProvIfCapEntry 56 }

deployProvIfCapTimModeOdu OBJECT-TYPE
    SYNTAX      TimModeCaps
    MAX-ACCESS  read-only
    STATUS      current
    DESCRIPTION
        "Detection of TIM-ODU Condition can be configured" 
    ::=  { deployProvIfCapEntry 57 }

deployProvIfCapTraceExpectedOduTcmA OBJECT-TYPE
    SYNTAX      Integer32
    MAX-ACCESS  read-only
    STATUS      current
    DESCRIPTION   "Expected SAPI part of the TCMA trace (15 character).
         NULL TRACE-TCM implies that no trace comparison is made."
    ::=  { deployProvIfCapEntry 58 }

deployProvIfCapTraceTransmitSapiOduTcmA OBJECT-TYPE
    SYNTAX      Integer32
    MAX-ACCESS  read-only
    STATUS      current
    DESCRIPTION
        "The transmitted SAPI part of the TCMA trace (15 character)" 
    ::=  { deployProvIfCapEntry 59 }

deployProvIfCapTraceTransmitDapiOduTcmA OBJECT-TYPE
    SYNTAX      Integer32
    MAX-ACCESS  read-only
    STATUS      current
    DESCRIPTION
        "The transmitted DAPI part of the TCMA trace (15 character)" 
    ::=  { deployProvIfCapEntry 60 }

deployProvIfCapTraceTransmitOpspOduTcmA OBJECT-TYPE
    SYNTAX      Integer32
    MAX-ACCESS  read-only
    STATUS      current
    DESCRIPTION
        "The transmitted Operator Specific part of the TCMA trace (32 character)" 
    ::=  { deployProvIfCapEntry 61 }

deployProvIfCapTimModeOduTcmA OBJECT-TYPE
    SYNTAX      TimModeCaps
    MAX-ACCESS  read-only
    STATUS      current
    DESCRIPTION
        "TCM_A Trace Identifier Mismatch (TIM) detection/action for TIM defect." 
    ::=  { deployProvIfCapEntry 62 }

deployProvIfCapTraceExpectedOduTcmB OBJECT-TYPE
    SYNTAX      Integer32
    MAX-ACCESS  read-only
    STATUS      current
    DESCRIPTION
        "Expected SAPI part of the TCMB trace (15 character). NULL TRACE-TCM implies that no trace comparison is made." 
    ::=  { deployProvIfCapEntry 63 }

deployProvIfCapTraceTransmitSapiOduTcmB OBJECT-TYPE
    SYNTAX      Integer32
    MAX-ACCESS  read-only
    STATUS      current
    DESCRIPTION
        "The transmitted SAPI part of the TCMB trace (15 character)" 
    ::=  { deployProvIfCapEntry 64 }

deployProvIfCapTraceTransmitDapiOduTcmB OBJECT-TYPE
    SYNTAX      Integer32
    MAX-ACCESS  read-only
    STATUS      current
    DESCRIPTION
        "The transmitted DAPI part of the TCMB trace (15 character)" 
    ::=  { deployProvIfCapEntry 65 }

deployProvIfCapTraceTransmitOpspOduTcmB OBJECT-TYPE
    SYNTAX      Integer32
    MAX-ACCESS  read-only
    STATUS      current
    DESCRIPTION
        "The transmitted Operator Specific part of the TCMB trace (32 character)" 
    ::=  { deployProvIfCapEntry 66 }

deployProvIfCapTimModeOduTcmB OBJECT-TYPE
    SYNTAX      TimModeCaps
    MAX-ACCESS  read-only
    STATUS      current
    DESCRIPTION
        "TCM_B Trace Identifier Mismatch (TIM) detection/action for TIM defect." 
    ::=  { deployProvIfCapEntry 67 }

deployProvIfCapTraceExpectedOduTcmC OBJECT-TYPE
    SYNTAX      Integer32
    MAX-ACCESS  read-only
    STATUS      current
    DESCRIPTION   "Expected SAPI part of the TCMC trace (15 character).
         NULL TRACE-TCM implies that no trace comparison is made."
    ::=  { deployProvIfCapEntry 68 }

deployProvIfCapTraceTransmitSapiOduTcmC OBJECT-TYPE
    SYNTAX      Integer32
    MAX-ACCESS  read-only
    STATUS      current
    DESCRIPTION
        "The transmitted SAPI part of the TCMC trace (15 character)" 
    ::=  { deployProvIfCapEntry 69 }

deployProvIfCapTraceTransmitDapiOduTcmC OBJECT-TYPE
    SYNTAX      Integer32
    MAX-ACCESS  read-only
    STATUS      current
    DESCRIPTION
        "The transmitted DAPI part of the TCMC trace (15 character)" 
    ::=  { deployProvIfCapEntry 70 }

deployProvIfCapTraceTransmitOpspOduTcmC OBJECT-TYPE
    SYNTAX      Integer32
    MAX-ACCESS  read-only
    STATUS      current
    DESCRIPTION
        "The transmitted Operator Specific part of the TCMC trace (32 character)" 
    ::=  { deployProvIfCapEntry 71 }

deployProvIfCapTimModeOduTcmC OBJECT-TYPE
    SYNTAX      TimModeCaps
    MAX-ACCESS  read-only
    STATUS      current
    DESCRIPTION
        "TCM_C Trace Identifier Mismatch (TIM) detection/action for TIM defect." 
    ::=  { deployProvIfCapEntry 72 }

deployProvIfCapChannelProvisioning OBJECT-TYPE
    SYNTAX      FspR7ChannelIdentifierCaps
    MAX-ACCESS  read-only
    STATUS      current
    DESCRIPTION
        "Channel" 
    ::=  { deployProvIfCapEntry 73 }

deployProvIfCapVariableGain OBJECT-TYPE
    SYNTAX      FspR7Unsigned32Caps
    UNITS       "0.1 dB"
    MAX-ACCESS  read-only
    STATUS      current
    DESCRIPTION
        "Variable Gain of EDFA" 
    ::=  { deployProvIfCapEntry 74 }

deployProvIfCapBand OBJECT-TYPE
    SYNTAX      FspR7OpticalBandCaps
    MAX-ACCESS  read-only
    STATUS      current
    DESCRIPTION   "The The optical band of the module."
    ::=  { deployProvIfCapEntry 75 }

deployProvIfCapSigDegThreshold OBJECT-TYPE
    SYNTAX      FspR7Unsigned32Caps
    MAX-ACCESS  read-only
    STATUS      current
    DESCRIPTION
        "Threshold for number of errors (CV or CV+DE) in one second" 
    ::=  { deployProvIfCapEntry 76 }

deployProvIfCapSigDegPeriodIntegration OBJECT-TYPE
    SYNTAX      FspR7Unsigned32Caps
    UNITS       "s"
    MAX-ACCESS  read-only
    STATUS      current
    DESCRIPTION
        "Integration Period for Signal degrade" 
    ::=  { deployProvIfCapEntry 77 }

deployProvIfCapVoaMode OBJECT-TYPE
    SYNTAX      FspR7VoaModeCaps
    MAX-ACCESS  read-only
    STATUS      current
    DESCRIPTION
        "VOA operating mode" 
    ::=  { deployProvIfCapEntry 78 }

deployProvIfCapOpticalSetPoint OBJECT-TYPE
    SYNTAX      FspR7Integer32Caps
    UNITS       "0.1 dBm"
    MAX-ACCESS  read-only
    STATUS      current
    DESCRIPTION
        "Sets the optical power for power equalization in ROADM or for channel power control in OPCM" 
    ::=  { deployProvIfCapEntry 79 }

deployProvIfCapVoaSetpoint OBJECT-TYPE
    SYNTAX      FspR7Unsigned32Caps
    UNITS       "0.1 dB"
    MAX-ACCESS  read-only
    STATUS      current
    DESCRIPTION
        "Sets the optical attenuation of VOA" 
    ::=  { deployProvIfCapEntry 80 }

deployProvIfCapLanAid OBJECT-TYPE
    SYNTAX      Integer32
    MAX-ACCESS  read-only
    STATUS      current
    DESCRIPTION
        "AID of LAN" 
    ::=  { deployProvIfCapEntry 81 }

deployProvIfCapAprHighThreshold OBJECT-TYPE
    SYNTAX      FspR7Unsigned32Caps
    UNITS       "0.1 dBm"
    MAX-ACCESS  read-only
    STATUS      current
    DESCRIPTION
        "Automatic Power Reduction High Threshold" 
    ::=  { deployProvIfCapEntry 82 }

deployProvIfCapPumpPower OBJECT-TYPE
    SYNTAX      FspR7Integer32Caps
    UNITS       "0.2 dBm"
    MAX-ACCESS  read-only
    STATUS      current
    DESCRIPTION
        "Total raman pump power" 
    ::=  { deployProvIfCapEntry 83 }

deployProvIfCapIpType OBJECT-TYPE
    SYNTAX      FspR7IpTypeCaps
    MAX-ACCESS  read-only
    STATUS      current
    DESCRIPTION
        "Type of IP configuration" 
    ::=  { deployProvIfCapEntry 84 }

deployProvIfCapWdmRxChannel OBJECT-TYPE
    SYNTAX      FspR7ChannelIdentifierCaps
    MAX-ACCESS  read-only
    STATUS      current
    DESCRIPTION
        "Configuration of Rx optical channel" 
    ::=  { deployProvIfCapEntry 85 }

deployProvIfCapSigDegThresSonetSection OBJECT-TYPE
    SYNTAX      FspR7BERThresholdSectionCaps
    MAX-ACCESS  read-only
    STATUS      current
    DESCRIPTION
        "Bit-Error-Based Degradation Definition for SONET (standard integration period)" 
    ::=  { deployProvIfCapEntry 86 }

deployProvIfCapSigDegThresSdhSection OBJECT-TYPE
    SYNTAX      FspR7Unsigned32Caps
    UNITS       "%"
    MAX-ACCESS  read-only
    STATUS      current
    DESCRIPTION
        "Block-Error-Based Degradation Definition for SDH (standard integration period).
         Defined as percentage Background Block Errors (30% default) evaluated
         over a defined period (SDPER-RS)." 
    ::=  { deployProvIfCapEntry 87 }

deployProvIfCapSigDegPeriodSdhSection OBJECT-TYPE
    SYNTAX      FspR7Unsigned32Caps
    UNITS       "s"
    MAX-ACCESS  read-only
    STATUS      current
    DESCRIPTION
        "Provisionable Signal Degrade Integration Period for SDH" 
    ::=  { deployProvIfCapEntry 88 }

deployProvIfCapDispersionMode OBJECT-TYPE
    SYNTAX      FspR7DispersionModesCaps
    MAX-ACCESS  read-only
    STATUS      current
    DESCRIPTION
        "Chromatic Dispersion Compensation Mode" 
    ::=  { deployProvIfCapEntry 89 }

deployProvIfCapDispersionSetting OBJECT-TYPE
    SYNTAX      FspR7Integer32Caps
    UNITS       "ps/nm"
    MAX-ACCESS  read-only
    STATUS      current
    DESCRIPTION
        "Chromatic Dispersion Compensation setting on module" 
    ::=  { deployProvIfCapEntry 90 }

deployProvIfCapOffset OBJECT-TYPE
    SYNTAX      FspR7Integer32Caps
    UNITS       "0.1 dB"
    MAX-ACCESS  read-only
    STATUS      current
    DESCRIPTION   "Sets the offset for the mean optical power for power equalization in ROADM"
    ::=  { deployProvIfCapEntry 91 }

deployProvIfCapFunction OBJECT-TYPE
    SYNTAX      FspR7InterfaceFunctionCaps
    MAX-ACCESS  read-only
    STATUS      current
    DESCRIPTION
        "Interface Function" 
    ::=  { deployProvIfCapEntry 92 }

deployProvIfCapPortMode OBJECT-TYPE
    SYNTAX      FspR7PortModeCaps
    MAX-ACCESS  read-only
    STATUS      current
    DESCRIPTION
        "Port Mode" 
    ::=  { deployProvIfCapEntry 93 }

deployProvIfCapPortRole OBJECT-TYPE
    SYNTAX      FspR7PortRoleCaps
    MAX-ACCESS  read-only
    STATUS      current
    DESCRIPTION
        "ADVA cloud Port Roles" 
    ::=  { deployProvIfCapEntry 94 }

deployProvIfCapUtag OBJECT-TYPE
    SYNTAX      FspR7UntaggedFramesCaps
    MAX-ACCESS  read-only
    STATUS      current
    DESCRIPTION
        "If untagged frames shall be enabled on this port or not." 
    ::=  { deployProvIfCapEntry 95 }

deployProvIfCapPvid OBJECT-TYPE
    SYNTAX      FspR7Unsigned32Caps
    MAX-ACCESS  read-only
    STATUS      current
    DESCRIPTION
        "Default VLAN ID (both STAG/CTAG mode) in case UTAG is enabled" 
    ::=  { deployProvIfCapEntry 96 }

deployProvIfCapPriority OBJECT-TYPE
    SYNTAX      FspR7Unsigned32Caps
    MAX-ACCESS  read-only
    STATUS      current
    DESCRIPTION
        "Default PCP in case UTAG is Enabled. The Prio may be remapped in the EVC." 
    ::=  { deployProvIfCapEntry 97 }

deployProvIfCapStagType OBJECT-TYPE
    SYNTAX      Integer32
    MAX-ACCESS  read-only
    STATUS      current
    DESCRIPTION
        "TAG type field" 
    ::=  { deployProvIfCapEntry 98 }

deployProvIfCapCac OBJECT-TYPE
    SYNTAX      FspR7L2CacEnableCaps
    MAX-ACCESS  read-only
    STATUS      current
    DESCRIPTION
        "Enable of CAC" 
    ::=  { deployProvIfCapEntry 99 }

deployProvIfCapMaxFrameSize OBJECT-TYPE
    SYNTAX      FspR7Unsigned32Caps
    MAX-ACCESS  read-only
    STATUS      current
    DESCRIPTION
        "Max Frame Size" 
    ::=  { deployProvIfCapEntry 100 }

deployProvIfCapVethAid OBJECT-TYPE
    SYNTAX      Integer32
    MAX-ACCESS  read-only
    STATUS      current
    DESCRIPTION
        "Shows if PORT is a member in the LAG with the VETH AID" 
    ::=  { deployProvIfCapEntry 101 }

deployProvIfCapLagPrio OBJECT-TYPE
    SYNTAX      FspR7Unsigned32Caps
    MAX-ACCESS  read-only
    STATUS      current
    DESCRIPTION
        "Part of ID. Port pri that defines standby." 
    ::=  { deployProvIfCapEntry 102 }

deployProvIfCapLagPortType OBJECT-TYPE
    SYNTAX      FspR7LagPortTypeCaps
    MAX-ACCESS  read-only
    STATUS      current
    DESCRIPTION
        "Type/Speed of connected ports in the Link Aggregation Group" 
    ::=  { deployProvIfCapEntry 103 }

deployProvIfCapLagActivePorts OBJECT-TYPE
    SYNTAX      FspR7Unsigned32Caps
    MAX-ACCESS  read-only
    STATUS      current
    DESCRIPTION
        "Number of active ports in the Link Aggregation Group" 
    ::=  { deployProvIfCapEntry 104 }

deployProvIfCapLacpMode OBJECT-TYPE
    SYNTAX      FspR7LacpModeCaps
    MAX-ACCESS  read-only
    STATUS      current
    DESCRIPTION
        "Enable of LACP state machine" 
    ::=  { deployProvIfCapEntry 105 }

deployProvIfCapLagLoadBallanceSource OBJECT-TYPE
    SYNTAX      FspR7LagLoadBallanceSourceCaps
    MAX-ACCESS  read-only
    STATUS      current
    DESCRIPTION
        "What source is used in the load balance calculation" 
    ::=  { deployProvIfCapEntry 106 }

deployProvIfCapLacpTimeout OBJECT-TYPE
    SYNTAX      FspR7LacpTimeoutCaps
    MAX-ACCESS  read-only
    STATUS      current
    DESCRIPTION
        "Timeout of the LACP" 
    ::=  { deployProvIfCapEntry 107 }

deployProvIfCapFarEndCommunication OBJECT-TYPE
    SYNTAX      FspR7YesNoCaps
    MAX-ACCESS  read-only
    STATUS      current
    DESCRIPTION
        "Used for Optojack plugs; Communication to Far End Plug is observed" 
    ::=  { deployProvIfCapEntry 108 }

deployProvIfCapEqlzAdmin OBJECT-TYPE
    SYNTAX      FspR7EqlzAdminStateCaps
    MAX-ACCESS  read-only
    STATUS      current
    DESCRIPTION   "Scheduled Equalization Administration"
    ::=  { deployProvIfCapEntry 109 }

deployProvIfCapTxOffDelay OBJECT-TYPE
    SYNTAX      FspR7EnableDisableCaps
    MAX-ACCESS  read-only
    STATUS      current
    DESCRIPTION
        "Enable or disable TXOFFHOLD Period for Error Forwarding and LKDO-OFF Consequent Action." 
    ::=  { deployProvIfCapEntry 110 }

deployProvIfCapOpuPayloadType OBJECT-TYPE
    SYNTAX      FspR7OpuPayloadTypeCaps
    MAX-ACCESS  read-only
    STATUS      current
    DESCRIPTION
        "OPU Payload Type Indicator" 
    ::=  { deployProvIfCapEntry 111 }

deployProvIfCapOscOpticalSetpoint OBJECT-TYPE
    SYNTAX      FspR7Integer32Caps
    UNITS       "0.1 dBm"
    MAX-ACCESS  read-only
    STATUS      current
    DESCRIPTION
        "Sets the OSC optical power" 
    ::=  { deployProvIfCapEntry 112 }

deployProvIfCapFiberBrand OBJECT-TYPE
    SYNTAX      FspR7FiberBrandCaps
    MAX-ACCESS  read-only
    STATUS      current
    DESCRIPTION
        "Brand of fiber present in the fiber plant" 
    ::=  { deployProvIfCapEntry 113 }

deployProvIfCapTiltSet OBJECT-TYPE
    SYNTAX      FspR7TiltSetCaps
    MAX-ACCESS  read-only
    STATUS      current
    DESCRIPTION
        "Tilt setting as discrete values versus a range" 
    ::=  { deployProvIfCapEntry 114 }

deployProvIfCapXfpDecisionThres OBJECT-TYPE
    SYNTAX      FspR7XfpDecisionThresCaps
    MAX-ACCESS  read-only
    STATUS      current
    DESCRIPTION
        "XFP Decision threshold setting" 
    ::=  { deployProvIfCapEntry 115 }

deployProvIfCapAutoPTassignment OBJECT-TYPE
    SYNTAX      FspR7ManualAutoCaps
    MAX-ACCESS  read-only
    STATUS      current
    DESCRIPTION
        "Auto assignment of ODU PT" 
    ::=  { deployProvIfCapEntry 116 }

deployProvIfCapTributarySlotMethod OBJECT-TYPE
    SYNTAX      FspR7ManualAutoCaps
    MAX-ACCESS  read-only
    STATUS      current
    DESCRIPTION
        "Tributary Slot assignment method" 
    ::=  { deployProvIfCapEntry 117 }

deployProvIfCapOduTribPortNo OBJECT-TYPE
    SYNTAX      SnmpAdminString
    MAX-ACCESS  read-only
    STATUS      current
    DESCRIPTION
        "ODU Tributary Port Number" 
    ::=  { deployProvIfCapEntry 118 }

deployProvIfCapOduTribTimeSlottNo OBJECT-TYPE
    SYNTAX      SnmpAdminString
    MAX-ACCESS  read-only
    STATUS      current
    DESCRIPTION   "ODU Tributary slot number. Multiple values can be entered as a string, separated by commas or given as a range.
         For capabilities objects possible number of slots and valid range are displayed in a form:
         [1,2,3,8][count: 1-1]
         In first brackets valid slots are shown and in the second possible number of slots."
    ::=  { deployProvIfCapEntry 119 }

deployProvIfCapRevertiveMode OBJECT-TYPE
    SYNTAX      ApsRevertModeCaps
    MAX-ACCESS  read-only
    STATUS      current
    DESCRIPTION
        "Revertive Protection Switching" 
    ::=  { deployProvIfCapEntry 120 }

deployProvIfCapLaserDelayTimer OBJECT-TYPE
    SYNTAX      FspR7LaserDelayTimerCaps
    MAX-ACCESS  read-only
    STATUS      current
    DESCRIPTION
        "Relevant only when ERRFWD=LSROFF. Enables/disables the
         possibility to delay turning off and on the laser.
         This applies to the case when turning off the laser
         is done as an error forwarding mechanism." 
    ::=  { deployProvIfCapEntry 121 }

deployProvIfCapLaserOffTimer OBJECT-TYPE
    SYNTAX      FspR7Unsigned32Caps
    UNITS       "ms"
    MAX-ACCESS  read-only
    STATUS      current
    DESCRIPTION
        "Delay before laser is swiched off" 
    ::=  { deployProvIfCapEntry 122 }

deployProvIfCapLaserOnTimer OBJECT-TYPE
    SYNTAX      FspR7Unsigned32Caps
    UNITS       "ms"
    MAX-ACCESS  read-only
    STATUS      current
    DESCRIPTION
        "Delay before laser is switched on" 
    ::=  { deployProvIfCapEntry 123 }

deployProvIfCapLaneChannelSetting OBJECT-TYPE
    SYNTAX      FspR7ChannelIdentifierCaps
    MAX-ACCESS  read-only
    STATUS      current
    DESCRIPTION
        "Lane Channel Setting" 
    ::=  { deployProvIfCapEntry 124 }

deployProvIfCapBip OBJECT-TYPE
    SYNTAX      FspR7BipCaps
    MAX-ACCESS  read-only
    STATUS      current
    DESCRIPTION
        "Bit Interleaved Parity" 
    ::=  { deployProvIfCapEntry 125 }

deployProvIfCapCodeGain OBJECT-TYPE
    SYNTAX      FspR7CodeGainCaps
    MAX-ACCESS  read-only
    STATUS      current
    DESCRIPTION
        "Forward Error Correction Coding gain" 
    ::=  { deployProvIfCapEntry 126 }

deployProvIfCapEdfaPwrOut OBJECT-TYPE
    SYNTAX      FspR7EdfaOutputPowerRatingCaps
    MAX-ACCESS  read-only
    STATUS      current
    DESCRIPTION
        "Optical Output Power Rating - Provision" 
    ::=  { deployProvIfCapEntry 127 }

deployProvIfCapPrio OBJECT-TYPE
    SYNTAX      FspR7Unsigned32Caps
    MAX-ACCESS  read-only
    STATUS      current
    DESCRIPTION
        "Priority" 
    ::=  { deployProvIfCapEntry 128 }

deployProvIfCapAuthType OBJECT-TYPE
    SYNTAX      FspR7CpAuthTypeCaps
    MAX-ACCESS  read-only
    STATUS      current
    DESCRIPTION
        "OSPF Authentication Type" 
    ::=  { deployProvIfCapEntry 129 }

deployProvIfCapAuthString OBJECT-TYPE
    SYNTAX      Integer32
    MAX-ACCESS  read-only
    STATUS      current
    DESCRIPTION
        "OSPF Authentication Key/String depending on Authentication Type" 
    ::=  { deployProvIfCapEntry 130 }

deployProvIfCapSigDegPcslThreshold OBJECT-TYPE
    SYNTAX      FspR7Unsigned32Caps
    UNITS       "%"
    MAX-ACCESS  read-only
    STATUS      current
    DESCRIPTION
        "Block-Error-Based Degradation Definition for Physical Coding Sublayer" 
    ::=  { deployProvIfCapEntry 131 }

deployProvIfDefaultsTable  OBJECT-TYPE
    SYNTAX      SEQUENCE OF DeployProvIfDefaultsEntry
    MAX-ACCESS  not-accessible
    STATUS      current
    DESCRIPTION   "Contains entries for provisioning of interfaces."
    ::=  { facilityDeployProv 3  }

deployProvIfDefaultsEntry OBJECT-TYPE
    SYNTAX      DeployProvIfDefaultsEntry
    MAX-ACCESS  not-accessible
    STATUS      current
    DESCRIPTION   "All interfaces which are provisioned(or during deployProv)
         will have an entry in this table."
    INDEX       { entityIndex }
    ::=  { deployProvIfDefaultsTable 1 }

DeployProvIfDefaultsEntry ::=  SEQUENCE
  { deployProvIfDefaultsRowStatus RowStatus,
    deployProvIfDefaultsForceDestroy FspR7ForcedStatus,
    deployProvIfDefaultsType FspR7InterfaceType,
    deployProvIfDefaultsPayload OtnPayloadType,
    deployProvIfDefaultsBehaviour FspR7PortBehaviour,
    deployProvIfDefaultsTerminationLevel OhTerminationLevel,
    deployProvIfDefaultsAlsMode FspR7AlsMode,
    deployProvIfDefaultsErrorForwarding FspR7ErrorFwdMode,
    deployProvIfDefaultsLaserOffDelayFunction EnableState,
    deployProvIfDefaultsFecType FspR7FecType,
    deployProvIfDefaultsTimingSource SonetTimingSource,
    deployProvIfDefaultsTcmALevel OtnTcmLevel,
    deployProvIfDefaultsTcmBLevel OtnTcmLevel,
    deployProvIfDefaultsSigDegThresSonetLine FspR7BERThreshold,
    deployProvIfDefaultsSigDegThresSdhMs Unsigned32,
    deployProvIfDefaultsSignalDegradePeriod Unsigned32,
    deployProvIfDefaultsAutonegotiation EnableState,
    deployProvIfDefaultsBitrate FspR7Bitrate,
    deployProvIfDefaultsDuplex EthDuplexMode,
    deployProvIfDefaultsFlowControl FspR7FlowControlMode,
    deployProvIfDefaultsOtnStuffing FspR7Stuff,
    deployProvIfDefaultsSigDegThresOtu Integer32,
    deployProvIfDefaultsSigDegPeriodOtu Unsigned32,
    deployProvIfDefaultsSigDegThresOdu Integer32,
    deployProvIfDefaultsSigDegPeriodOdu Unsigned32,
    deployProvIfDefaultsSigDegThresOduTcmA Integer32,
    deployProvIfDefaultsSigDegPeriodOduTcmA Unsigned32,
    deployProvIfDefaultsSigDegThresOduTcmB Integer32,
    deployProvIfDefaultsSigDegPeriodOduTcmB Unsigned32,
    deployProvIfDefaultsTilt Integer32,
    deployProvIfDefaultsGain FspR7Gain,
    deployProvIfDefaultsAdmin FspR7AdminState,
    deployProvIfDefaultsAttenuationGradient Unsigned32,
    deployProvIfDefaultsSigDegThresReceiver Unsigned32,
    deployProvIfDefaultsTcmCLevel OtnTcmLevel,
    deployProvIfDefaultsSigDegThresOduTcmC Integer32,
    deployProvIfDefaultsSigDegPeriodOduTcmC Unsigned32,
    deployProvIfDefaultsDisparityCorrection EnableState,
    deployProvIfDefaultsIpAddr IpAddress,
    deployProvIfDefaultsIpMask IpAddress,
    deployProvIfDefaultsOspf FspR7OspfMode,
    deployProvIfDefaultsMetric Unsigned32,
    deployProvIfDefaultsAreaId IpAddress,
    deployProvIfDefaultsTraceFormSonetSection SonetTraceForm,
    deployProvIfDefaultsTraceExpectedSonetSection OCTET STRING,
    deployProvIfDefaultsTraceTransmitSonetSection OCTET STRING,
    deployProvIfDefaultsTimModeSonetSection TimMode,
    deployProvIfDefaultsTraceExpectedOtu OCTET STRING,
    deployProvIfDefaultsTraceTransmitSapiOtu OCTET STRING,
    deployProvIfDefaultsTraceTransmitDapiOtu OCTET STRING,
    deployProvIfDefaultsTraceTransmitOpspOtu OCTET STRING,
    deployProvIfDefaultsTimModeOtu TimMode,
    deployProvIfDefaultsTraceExpectedOdu OCTET STRING,
    deployProvIfDefaultsTraceTransmitSapiOdu OCTET STRING,
    deployProvIfDefaultsTraceTransmitDapiOdu OCTET STRING,
    deployProvIfDefaultsTraceTransmitOpspOdu OCTET STRING,
    deployProvIfDefaultsTimModeOdu TimMode,
    deployProvIfDefaultsTraceExpectedOduTcmA OCTET STRING,
    deployProvIfDefaultsTraceTransmitSapiOduTcmA OCTET STRING,
    deployProvIfDefaultsTraceTransmitDapiOduTcmA OCTET STRING,
    deployProvIfDefaultsTraceTransmitOpspOduTcmA OCTET STRING,
    deployProvIfDefaultsTimModeOduTcmA TimMode,
    deployProvIfDefaultsTraceExpectedOduTcmB OCTET STRING,
    deployProvIfDefaultsTraceTransmitSapiOduTcmB OCTET STRING,
    deployProvIfDefaultsTraceTransmitDapiOduTcmB OCTET STRING,
    deployProvIfDefaultsTraceTransmitOpspOduTcmB OCTET STRING,
    deployProvIfDefaultsTimModeOduTcmB TimMode,
    deployProvIfDefaultsTraceExpectedOduTcmC OCTET STRING,
    deployProvIfDefaultsTraceTransmitSapiOduTcmC OCTET STRING,
    deployProvIfDefaultsTraceTransmitDapiOduTcmC OCTET STRING,
    deployProvIfDefaultsTraceTransmitOpspOduTcmC OCTET STRING,
    deployProvIfDefaultsTimModeOduTcmC TimMode,
    deployProvIfDefaultsChannelProvisioning FspR7ChannelIdentifier,
    deployProvIfDefaultsVariableGain Unsigned32,
    deployProvIfDefaultsBand FspR7OpticalBand,
    deployProvIfDefaultsSigDegThreshold Unsigned32,
    deployProvIfDefaultsSigDegPeriodIntegration Unsigned32,
    deployProvIfDefaultsVoaMode FspR7VoaMode,
    deployProvIfDefaultsOpticalSetPoint Integer32,
    deployProvIfDefaultsVoaSetpoint Unsigned32,
    deployProvIfDefaultsLanAid EntityIndex,
    deployProvIfDefaultsAprHighThreshold Unsigned32,
    deployProvIfDefaultsPumpPower Integer32,
    deployProvIfDefaultsIpType FspR7IpType,
    deployProvIfDefaultsWdmRxChannel FspR7ChannelIdentifier,
    deployProvIfDefaultsSigDegThresSonetSection FspR7BERThresholdSection,
    deployProvIfDefaultsSigDegThresSdhSection Unsigned32,
    deployProvIfDefaultsSigDegPeriodSdhSection Unsigned32,
    deployProvIfDefaultsDispersionMode FspR7DispersionModes,
    deployProvIfDefaultsDispersionSetting Integer32,
    deployProvIfDefaultsOffset Integer32,
    deployProvIfDefaultsFunction FspR7InterfaceFunction,
    deployProvIfDefaultsPortMode FspR7PortMode,
    deployProvIfDefaultsPortRole FspR7PortRole,
    deployProvIfDefaultsUtag FspR7UntaggedFrames,
    deployProvIfDefaultsPvid Unsigned32,
    deployProvIfDefaultsPriority Unsigned32,
    deployProvIfDefaultsStagType FspR7SnmpHexString,
    deployProvIfDefaultsCac FspR7L2CacEnable,
    deployProvIfDefaultsMaxFrameSize Unsigned32,
    deployProvIfDefaultsVethAid EntityIndex,
    deployProvIfDefaultsLagPrio Unsigned32,
    deployProvIfDefaultsLagPortType FspR7LagPortType,
    deployProvIfDefaultsLagActivePorts Unsigned32,
    deployProvIfDefaultsLacpMode FspR7LacpMode,
    deployProvIfDefaultsLagLoadBallanceSource FspR7LagLoadBallanceSource,
    deployProvIfDefaultsLacpTimeout FspR7LacpTimeout,
    deployProvIfDefaultsFarEndCommunication FspR7YesNo,
    deployProvIfDefaultsEqlzAdmin FspR7EqlzAdminState,
    deployProvIfDefaultsTxOffDelay FspR7EnableDisable,
    deployProvIfDefaultsOpuPayloadType FspR7OpuPayloadType,
    deployProvIfDefaultsOscOpticalSetpoint Integer32,
    deployProvIfDefaultsFiberBrand FspR7FiberBrand,
    deployProvIfDefaultsTiltSet FspR7TiltSet,
    deployProvIfDefaultsXfpDecisionThres FspR7XfpDecisionThres,
    deployProvIfDefaultsAutoPTassignment FspR7ManualAuto,
    deployProvIfDefaultsTributarySlotMethod FspR7ManualAuto,
    deployProvIfDefaultsOduTribPortNo SnmpAdminString,
    deployProvIfDefaultsOduTribTimeSlottNo SnmpAdminString,
    deployProvIfDefaultsRevertiveMode ApsRevertMode,
    deployProvIfDefaultsLaserDelayTimer FspR7LaserDelayTimer,
    deployProvIfDefaultsLaserOffTimer Unsigned32,
    deployProvIfDefaultsLaserOnTimer Unsigned32,
    deployProvIfDefaultsLaneChannelSetting FspR7ChannelIdentifier,
    deployProvIfDefaultsBip FspR7Bip,
    deployProvIfDefaultsCodeGain FspR7CodeGain,
    deployProvIfDefaultsEdfaPwrOut FspR7EdfaOutputPowerRating,
    deployProvIfDefaultsPrio Unsigned32,
    deployProvIfDefaultsAuthType FspR7CpAuthType,
    deployProvIfDefaultsAuthString SnmpAdminString,
    deployProvIfDefaultsSigDegPcslThreshold Unsigned32 }

deployProvIfDefaultsRowStatus OBJECT-TYPE
    SYNTAX      RowStatus
    MAX-ACCESS  read-only
    STATUS      current
    DESCRIPTION   "RowStatus"
    ::=  { deployProvIfDefaultsEntry 1 }

deployProvIfDefaultsForceDestroy OBJECT-TYPE
    SYNTAX      FspR7ForcedStatus
    MAX-ACCESS  read-only
    STATUS      current
    DESCRIPTION
        "Forced Destroy" 
    ::=  { deployProvIfDefaultsEntry 2 }

deployProvIfDefaultsType OBJECT-TYPE
    SYNTAX      FspR7InterfaceType
    MAX-ACCESS  read-only
    STATUS      current
    DESCRIPTION   "The TYPE defines the transport service type as wrapper with wrapper layer
         termination OR else as payload"
    ::=  { deployProvIfDefaultsEntry 3 }

deployProvIfDefaultsPayload OBJECT-TYPE
    SYNTAX      OtnPayloadType
    MAX-ACCESS  read-only
    STATUS      current
    DESCRIPTION   "The payload of the interface (inside a transport overhead).
         Relevant e. g. for OTN cards which wrap a payload into an OTU1/2 wrapper."
    ::=  { deployProvIfDefaultsEntry 4 }

deployProvIfDefaultsBehaviour OBJECT-TYPE
    SYNTAX      FspR7PortBehaviour
    MAX-ACCESS  read-only
    STATUS      current
    DESCRIPTION   "The configured behaviour of the interface. If configured as
         a network interface, the interface will use a WDM laser."
    ::=  { deployProvIfDefaultsEntry 5 }

deployProvIfDefaultsTerminationLevel OBJECT-TYPE
    SYNTAX      OhTerminationLevel
    MAX-ACCESS  read-only
    STATUS      current
    DESCRIPTION
        "Highest signal level hardware removes then generates for transmission." 
    ::=  { deployProvIfDefaultsEntry 6 }

deployProvIfDefaultsAlsMode OBJECT-TYPE
    SYNTAX      FspR7AlsMode
    MAX-ACCESS  read-only
    STATUS      current
    DESCRIPTION   "A configuration request for the Automatic Laser Shutdown (ALS)
         function. Refer to FspR7AlsMode Textual Convention for details."
    ::=  { deployProvIfDefaultsEntry 7 }

deployProvIfDefaultsErrorForwarding OBJECT-TYPE
    SYNTAX      FspR7ErrorFwdMode
    MAX-ACCESS  read-only
    STATUS      current
    DESCRIPTION   "A configuration request for the error forwarding
         function. Refer to FspR7ErrorFwdMode Textual Convention for details."
    ::=  { deployProvIfDefaultsEntry 8 }

deployProvIfDefaultsLaserOffDelayFunction OBJECT-TYPE
    SYNTAX      EnableState
    MAX-ACCESS  read-only
    STATUS      current
    DESCRIPTION   "A configuration request for the Laser Off Delay function. This function
         delays turning off the laser as a consequent action to a defect."
    ::=  { deployProvIfDefaultsEntry 9 }

deployProvIfDefaultsFecType OBJECT-TYPE
    SYNTAX      FspR7FecType
    MAX-ACCESS  read-only
    STATUS      current
    DESCRIPTION   "Configuration of FEC type."
    ::=  { deployProvIfDefaultsEntry 10 }

deployProvIfDefaultsTimingSource OBJECT-TYPE
    SYNTAX      SonetTimingSource
    MAX-ACCESS  read-only
    STATUS      current
    DESCRIPTION   "The timing source for this interface.
         - internal: used in stand-alone, point-to-point topologies stand-alone (dedicated fiber operation).
         - loopTiming: e.g. used in point-to-point via SONET network and feeder topologies. The default is
         internal(1)."
    ::=  { deployProvIfDefaultsEntry 11 }

deployProvIfDefaultsTcmALevel OBJECT-TYPE
    SYNTAX      OtnTcmLevel
    MAX-ACCESS  read-only
    STATUS      current
    DESCRIPTION   "Configuration of TCMA level."
    ::=  { deployProvIfDefaultsEntry 12 }

deployProvIfDefaultsTcmBLevel OBJECT-TYPE
    SYNTAX      OtnTcmLevel
    MAX-ACCESS  read-only
    STATUS      current
    DESCRIPTION   "Configuration of TCMB level."
    ::=  { deployProvIfDefaultsEntry 13 }

deployProvIfDefaultsSigDegThresSonetLine OBJECT-TYPE
    SYNTAX      FspR7BERThreshold
    MAX-ACCESS  read-only
    STATUS      current
    DESCRIPTION
        "Bit-Error-Based Degradation Definition for SONET (standard integration period)" 
    ::=  { deployProvIfDefaultsEntry 14 }

deployProvIfDefaultsSigDegThresSdhMs OBJECT-TYPE
    SYNTAX      Unsigned32 (1..100 | 4294967295) 
    UNITS       "%"
    MAX-ACCESS  read-only
    STATUS      current
    DESCRIPTION
        "Block-Error-Based Degradation Definition for SDH (standard integration period).
         Defined as percentage Background Block Errors (30% default) evaluated
         over a defined period (SDPER-RS)." 
    ::=  { deployProvIfDefaultsEntry 15 }

deployProvIfDefaultsSignalDegradePeriod OBJECT-TYPE
    SYNTAX      Unsigned32 (2..10 | 4294967295) 
    UNITS       "s"
    MAX-ACCESS  read-only
    STATUS      current
    DESCRIPTION   "The measurement period in seconds used together with
         the deployProvIfSigDegThresSdhRegSect based on the block error counting method.
         The valid range is 2..10,
         The default being 7."
    ::=  { deployProvIfDefaultsEntry 16 }

deployProvIfDefaultsAutonegotiation OBJECT-TYPE
    SYNTAX      EnableState
    MAX-ACCESS  read-only
    STATUS      current
    DESCRIPTION
        "Auto Negotiation for the data rate" 
    ::=  { deployProvIfDefaultsEntry 17 }

deployProvIfDefaultsBitrate OBJECT-TYPE
    SYNTAX      FspR7Bitrate
    MAX-ACCESS  read-only
    STATUS      current
    DESCRIPTION
        "Provisioned data rate" 
    ::=  { deployProvIfDefaultsEntry 18 }

deployProvIfDefaultsDuplex OBJECT-TYPE
    SYNTAX      EthDuplexMode
    MAX-ACCESS  read-only
    STATUS      current
    DESCRIPTION
        "Duplex Mode (provision), available when Auto Negoiation is Disable (AUTONEG=DISABLE)" 
    ::=  { deployProvIfDefaultsEntry 19 }

deployProvIfDefaultsFlowControl OBJECT-TYPE
    SYNTAX      FspR7FlowControlMode
    MAX-ACCESS  read-only
    STATUS      current
    DESCRIPTION
        "Flow Control mechanism" 
    ::=  { deployProvIfDefaultsEntry 20 }

deployProvIfDefaultsOtnStuffing OBJECT-TYPE
    SYNTAX      FspR7Stuff
    MAX-ACCESS  read-only
    STATUS      current
    DESCRIPTION
        "Indicates if bit/byte stuffing is used in the transport signal." 
    ::=  { deployProvIfDefaultsEntry 21 }

deployProvIfDefaultsSigDegThresOtu OBJECT-TYPE
    SYNTAX      Integer32 (1..100 | -2147483648) 
    UNITS       "%"
    MAX-ACCESS  read-only
    STATUS      current
    DESCRIPTION
        "Background-Block-Error-Based Signal Degradation Definition for OTU" 
    ::=  { deployProvIfDefaultsEntry 22 }

deployProvIfDefaultsSigDegPeriodOtu OBJECT-TYPE
    SYNTAX      Unsigned32 (2..10 | 4294967295) 
    UNITS       "s"
    MAX-ACCESS  read-only
    STATUS      current
    DESCRIPTION
        "Integration Period for Signal degrade" 
    ::=  { deployProvIfDefaultsEntry 23 }

deployProvIfDefaultsSigDegThresOdu OBJECT-TYPE
    SYNTAX      Integer32 (1..100 | -2147483648) 
    UNITS       "%"
    MAX-ACCESS  read-only
    STATUS      current
    DESCRIPTION
        "Background-Block-Error-Based Signal Degradation Definition for ODU" 
    ::=  { deployProvIfDefaultsEntry 24 }

deployProvIfDefaultsSigDegPeriodOdu OBJECT-TYPE
    SYNTAX      Unsigned32 (2..10 | 4294967295) 
    UNITS       "s"
    MAX-ACCESS  read-only
    STATUS      current
    DESCRIPTION
        "Integration Period for Signal degrade" 
    ::=  { deployProvIfDefaultsEntry 25 }

deployProvIfDefaultsSigDegThresOduTcmA OBJECT-TYPE
    SYNTAX      Integer32 (1..100 | -2147483648) 
    UNITS       "%"
    MAX-ACCESS  read-only
    STATUS      current
    DESCRIPTION
        "Background-Block-Error-Based Signal Degradation Definition for TCM-A" 
    ::=  { deployProvIfDefaultsEntry 26 }

deployProvIfDefaultsSigDegPeriodOduTcmA OBJECT-TYPE
    SYNTAX      Unsigned32 (2..10 | 4294967295) 
    UNITS       "s"
    MAX-ACCESS  read-only
    STATUS      current
    DESCRIPTION
        "Integration Period for Signal degrade" 
    ::=  { deployProvIfDefaultsEntry 27 }

deployProvIfDefaultsSigDegThresOduTcmB OBJECT-TYPE
    SYNTAX      Integer32 (1..100 | -2147483648) 
    UNITS       "%"
    MAX-ACCESS  read-only
    STATUS      current
    DESCRIPTION
        "Background-Block-Error-Based Signal Degradation Definition for TCM-B" 
    ::=  { deployProvIfDefaultsEntry 28 }

deployProvIfDefaultsSigDegPeriodOduTcmB OBJECT-TYPE
    SYNTAX      Unsigned32 (2..10 | 4294967295) 
    UNITS       "s"
    MAX-ACCESS  read-only
    STATUS      current
    DESCRIPTION
        "Integration Period of TCMB Signal Segrade" 
    ::=  { deployProvIfDefaultsEntry 29 }

deployProvIfDefaultsTilt OBJECT-TYPE
    SYNTAX      Integer32 (-50..0 | -2147483648) 
    UNITS       "0.1 dB"
    MAX-ACCESS  read-only
    STATUS      current
    DESCRIPTION
        "Change of optical channel power in dB over the complete transmission band" 
    ::=  { deployProvIfDefaultsEntry 30 }

deployProvIfDefaultsGain OBJECT-TYPE
    SYNTAX      FspR7Gain
    MAX-ACCESS  read-only
    STATUS      current
    DESCRIPTION
        "Gain" 
    ::=  { deployProvIfDefaultsEntry 31 }

deployProvIfDefaultsAdmin OBJECT-TYPE
    SYNTAX      FspR7AdminState
    MAX-ACCESS  read-only
    STATUS      current
    DESCRIPTION   "The Adminstrative State."
    ::=  { deployProvIfDefaultsEntry 32 }

deployProvIfDefaultsAttenuationGradient OBJECT-TYPE
    SYNTAX      Unsigned32 (5..990 | 4294967295) 
    UNITS       "0.1 dB/min"
    MAX-ACCESS  read-only
    STATUS      current
    DESCRIPTION   "Attenuation Gradient Threshold on Receive Fiber. Applies to both
         TRMT and RCV directions; but threshold violation is reported for
         each direction separately by the 'tapping' alarms: INTRUDE-RCV
         and INTRUDE-TRMT."
    ::=  { deployProvIfDefaultsEntry 33 }

deployProvIfDefaultsSigDegThresReceiver OBJECT-TYPE
    SYNTAX      Unsigned32 
    UNITS       "0.1 dB"
    MAX-ACCESS  read-only
    STATUS      current
    DESCRIPTION
        "Signal Degrade Threshold on Receiver. Reported as ATTRMT-SDHT to far end." 
    ::=  { deployProvIfDefaultsEntry 34 }

deployProvIfDefaultsTcmCLevel OBJECT-TYPE
    SYNTAX      OtnTcmLevel
    MAX-ACCESS  read-only
    STATUS      current
    DESCRIPTION
        "Activation of Tandem Connection Monitoring Instance C" 
    ::=  { deployProvIfDefaultsEntry 35 }

deployProvIfDefaultsSigDegThresOduTcmC OBJECT-TYPE
    SYNTAX      Integer32 (1..100 | -2147483648) 
    UNITS       "%"
    MAX-ACCESS  read-only
    STATUS      current
    DESCRIPTION
        "Background-Block-Error-Based Signal Degradation Definition for TCM-C" 
    ::=  { deployProvIfDefaultsEntry 36 }

deployProvIfDefaultsSigDegPeriodOduTcmC OBJECT-TYPE
    SYNTAX      Unsigned32 (2..10 | 4294967295) 
    UNITS       "s"
    MAX-ACCESS  read-only
    STATUS      current
    DESCRIPTION
        "Integration Period of TCMC Signal Segrade" 
    ::=  { deployProvIfDefaultsEntry 37 }

deployProvIfDefaultsDisparityCorrection OBJECT-TYPE
    SYNTAX      EnableState
    MAX-ACCESS  read-only
    STATUS      current
    DESCRIPTION
        "Disparity correction" 
    ::=  { deployProvIfDefaultsEntry 38 }

deployProvIfDefaultsIpAddr OBJECT-TYPE
    SYNTAX      IpAddress
    MAX-ACCESS  read-only
    STATUS      current
    DESCRIPTION
        "IP Address assigned to LAN IP Interface" 
    ::=  { deployProvIfDefaultsEntry 39 }

deployProvIfDefaultsIpMask OBJECT-TYPE
    SYNTAX      IpAddress
    MAX-ACCESS  read-only
    STATUS      current
    DESCRIPTION
        "IP MASK assigned to LAN IP Interface" 
    ::=  { deployProvIfDefaultsEntry 40 }

deployProvIfDefaultsOspf OBJECT-TYPE
    SYNTAX      FspR7OspfMode
    MAX-ACCESS  read-only
    STATUS      current
    DESCRIPTION
        "OSPF Routing (Dynamic)" 
    ::=  { deployProvIfDefaultsEntry 41 }

deployProvIfDefaultsMetric OBJECT-TYPE
    SYNTAX      Unsigned32 (0..65535 | 4294967295)
    MAX-ACCESS  read-only
    STATUS      current
    DESCRIPTION
        "Routing Metric" 
    ::=  { deployProvIfDefaultsEntry 42 }

deployProvIfDefaultsAreaId OBJECT-TYPE
    SYNTAX      IpAddress
    MAX-ACCESS  read-only
    STATUS      current
    DESCRIPTION
        "OSPF Area ID for IP Interface" 
    ::=  { deployProvIfDefaultsEntry 43 }

deployProvIfDefaultsTraceFormSonetSection OBJECT-TYPE
    SYNTAX      SonetTraceForm
    MAX-ACCESS  read-only
    STATUS      current
    DESCRIPTION
        "Byte-Length of Trace Compared to Expected" 
    ::=  { deployProvIfDefaultsEntry 44 }

deployProvIfDefaultsTraceExpectedSonetSection OBJECT-TYPE
    SYNTAX      OCTET STRING (SIZE(0..62))
    MAX-ACCESS  read-only
    STATUS      current
    DESCRIPTION
        "Expected Sec/RS trace. NULL TRACE implies that no trace comparison is made." 
    ::=  { deployProvIfDefaultsEntry 45 }

deployProvIfDefaultsTraceTransmitSonetSection OBJECT-TYPE
    SYNTAX      OCTET STRING (SIZE(0..62))
    MAX-ACCESS  read-only
    STATUS      current
    DESCRIPTION
        "Sec/RS Trace to be Transmitted" 
    ::=  { deployProvIfDefaultsEntry 46 }

deployProvIfDefaultsTimModeSonetSection OBJECT-TYPE
    SYNTAX      TimMode
    MAX-ACCESS  read-only
    STATUS      current
    DESCRIPTION
        "SONET Section Trace Identifier Mismatch (TIM) detection/action for TIM defect." 
    ::=  { deployProvIfDefaultsEntry 47 }

deployProvIfDefaultsTraceExpectedOtu OBJECT-TYPE
    SYNTAX      OCTET STRING (SIZE(0..15))
    MAX-ACCESS  read-only
    STATUS      current
    DESCRIPTION   "Expected SAPI part of the OTU trace (15 character).
         NULL TRACE implies that no trace comparison is made."
    ::=  { deployProvIfDefaultsEntry 48 }

deployProvIfDefaultsTraceTransmitSapiOtu OBJECT-TYPE
    SYNTAX      OCTET STRING (SIZE(0..15))
    MAX-ACCESS  read-only
    STATUS      current
    DESCRIPTION
        "The transmitted SAPI part of the OTU trace (15 character)" 
    ::=  { deployProvIfDefaultsEntry 49 }

deployProvIfDefaultsTraceTransmitDapiOtu OBJECT-TYPE
    SYNTAX      OCTET STRING (SIZE(0..15))
    MAX-ACCESS  read-only
    STATUS      current
    DESCRIPTION
        "The transmitted DAPI part of the OTU trace (15 character)" 
    ::=  { deployProvIfDefaultsEntry 50 }

deployProvIfDefaultsTraceTransmitOpspOtu OBJECT-TYPE
    SYNTAX      OCTET STRING (SIZE(0..32))
    MAX-ACCESS  read-only
    STATUS      current
    DESCRIPTION
        "The transmitted Operator Specific part of the OTU trace (32 character)" 
    ::=  { deployProvIfDefaultsEntry 51 }

deployProvIfDefaultsTimModeOtu OBJECT-TYPE
    SYNTAX      TimMode
    MAX-ACCESS  read-only
    STATUS      current
    DESCRIPTION
        "OTU Trace Identifier Mismatch (TIM) detection/action for TIM defect." 
    ::=  { deployProvIfDefaultsEntry 52 }

deployProvIfDefaultsTraceExpectedOdu OBJECT-TYPE
    SYNTAX      OCTET STRING (SIZE(0..15))
    MAX-ACCESS  read-only
    STATUS      current
    DESCRIPTION   "Expected SAPI part of the ODU trace (15 character).
         NULL TRACE implies that no trace comparison is made."
    ::=  { deployProvIfDefaultsEntry 53 }

deployProvIfDefaultsTraceTransmitSapiOdu OBJECT-TYPE
    SYNTAX      OCTET STRING (SIZE(0..15))
    MAX-ACCESS  read-only
    STATUS      current
    DESCRIPTION
        "The transmitted SAPI part of the ODU trace (15 character)" 
    ::=  { deployProvIfDefaultsEntry 54 }

deployProvIfDefaultsTraceTransmitDapiOdu OBJECT-TYPE
    SYNTAX      OCTET STRING (SIZE(0..15))
    MAX-ACCESS  read-only
    STATUS      current
    DESCRIPTION
        "The transmitted DAPI part of the ODU trace (15 character)" 
    ::=  { deployProvIfDefaultsEntry 55 }

deployProvIfDefaultsTraceTransmitOpspOdu OBJECT-TYPE
    SYNTAX      OCTET STRING (SIZE(0..32))
    MAX-ACCESS  read-only
    STATUS      current
    DESCRIPTION
        "The transmitted Operator Specific part of the ODU trace (32 character)" 
    ::=  { deployProvIfDefaultsEntry 56 }

deployProvIfDefaultsTimModeOdu OBJECT-TYPE
    SYNTAX      TimMode
    MAX-ACCESS  read-only
    STATUS      current
    DESCRIPTION
        "Detection of TIM-ODU Condition can be configured" 
    ::=  { deployProvIfDefaultsEntry 57 }

deployProvIfDefaultsTraceExpectedOduTcmA OBJECT-TYPE
    SYNTAX      OCTET STRING (SIZE(0..15))
    MAX-ACCESS  read-only
    STATUS      current
    DESCRIPTION   "Expected SAPI part of the TCMA trace (15 character).
         NULL TRACE-TCM implies that no trace comparison is made."
    ::=  { deployProvIfDefaultsEntry 58 }

deployProvIfDefaultsTraceTransmitSapiOduTcmA OBJECT-TYPE
    SYNTAX      OCTET STRING (SIZE(0..15))
    MAX-ACCESS  read-only
    STATUS      current
    DESCRIPTION
        "The transmitted SAPI part of the TCMA trace (15 character)" 
    ::=  { deployProvIfDefaultsEntry 59 }

deployProvIfDefaultsTraceTransmitDapiOduTcmA OBJECT-TYPE
    SYNTAX      OCTET STRING (SIZE(0..15))
    MAX-ACCESS  read-only
    STATUS      current
    DESCRIPTION
        "The transmitted DAPI part of the TCMA trace (15 character)" 
    ::=  { deployProvIfDefaultsEntry 60 }

deployProvIfDefaultsTraceTransmitOpspOduTcmA OBJECT-TYPE
    SYNTAX      OCTET STRING (SIZE(0..32))
    MAX-ACCESS  read-only
    STATUS      current
    DESCRIPTION
        "The transmitted Operator Specific part of the TCMA trace (32 character)" 
    ::=  { deployProvIfDefaultsEntry 61 }

deployProvIfDefaultsTimModeOduTcmA OBJECT-TYPE
    SYNTAX      TimMode
    MAX-ACCESS  read-only
    STATUS      current
    DESCRIPTION
        "TCM_A Trace Identifier Mismatch (TIM) detection/action for TIM defect." 
    ::=  { deployProvIfDefaultsEntry 62 }

deployProvIfDefaultsTraceExpectedOduTcmB OBJECT-TYPE
    SYNTAX      OCTET STRING (SIZE(0..15))
    MAX-ACCESS  read-only
    STATUS      current
    DESCRIPTION
        "Expected SAPI part of the TCMB trace (15 character). NULL TRACE-TCM implies that no trace comparison is made." 
    ::=  { deployProvIfDefaultsEntry 63 }

deployProvIfDefaultsTraceTransmitSapiOduTcmB OBJECT-TYPE
    SYNTAX      OCTET STRING (SIZE(0..15))
    MAX-ACCESS  read-only
    STATUS      current
    DESCRIPTION
        "The transmitted SAPI part of the TCMB trace (15 character)" 
    ::=  { deployProvIfDefaultsEntry 64 }

deployProvIfDefaultsTraceTransmitDapiOduTcmB OBJECT-TYPE
    SYNTAX      OCTET STRING (SIZE(0..15))
    MAX-ACCESS  read-only
    STATUS      current
    DESCRIPTION
        "The transmitted DAPI part of the TCMB trace (15 character)" 
    ::=  { deployProvIfDefaultsEntry 65 }

deployProvIfDefaultsTraceTransmitOpspOduTcmB OBJECT-TYPE
    SYNTAX      OCTET STRING (SIZE(0..32))
    MAX-ACCESS  read-only
    STATUS      current
    DESCRIPTION
        "The transmitted Operator Specific part of the TCMB trace (32 character)" 
    ::=  { deployProvIfDefaultsEntry 66 }

deployProvIfDefaultsTimModeOduTcmB OBJECT-TYPE
    SYNTAX      TimMode
    MAX-ACCESS  read-only
    STATUS      current
    DESCRIPTION
        "TCM_B Trace Identifier Mismatch (TIM) detection/action for TIM defect." 
    ::=  { deployProvIfDefaultsEntry 67 }

deployProvIfDefaultsTraceExpectedOduTcmC OBJECT-TYPE
    SYNTAX      OCTET STRING (SIZE(0..15))
    MAX-ACCESS  read-only
    STATUS      current
    DESCRIPTION   "Expected SAPI part of the TCMC trace (15 character).
         NULL TRACE-TCM implies that no trace comparison is made."
    ::=  { deployProvIfDefaultsEntry 68 }

deployProvIfDefaultsTraceTransmitSapiOduTcmC OBJECT-TYPE
    SYNTAX      OCTET STRING (SIZE(0..15))
    MAX-ACCESS  read-only
    STATUS      current
    DESCRIPTION
        "The transmitted SAPI part of the TCMC trace (15 character)" 
    ::=  { deployProvIfDefaultsEntry 69 }

deployProvIfDefaultsTraceTransmitDapiOduTcmC OBJECT-TYPE
    SYNTAX      OCTET STRING (SIZE(0..15))
    MAX-ACCESS  read-only
    STATUS      current
    DESCRIPTION
        "The transmitted DAPI part of the TCMC trace (15 character)" 
    ::=  { deployProvIfDefaultsEntry 70 }

deployProvIfDefaultsTraceTransmitOpspOduTcmC OBJECT-TYPE
    SYNTAX      OCTET STRING (SIZE(0..32))
    MAX-ACCESS  read-only
    STATUS      current
    DESCRIPTION
        "The transmitted Operator Specific part of the TCMC trace (32 character)" 
    ::=  { deployProvIfDefaultsEntry 71 }

deployProvIfDefaultsTimModeOduTcmC OBJECT-TYPE
    SYNTAX      TimMode
    MAX-ACCESS  read-only
    STATUS      current
    DESCRIPTION
        "TCM_C Trace Identifier Mismatch (TIM) detection/action for TIM defect." 
    ::=  { deployProvIfDefaultsEntry 72 }

deployProvIfDefaultsChannelProvisioning OBJECT-TYPE
    SYNTAX      FspR7ChannelIdentifier
    MAX-ACCESS  read-only
    STATUS      current
    DESCRIPTION
        "Channel" 
    ::=  { deployProvIfDefaultsEntry 73 }

deployProvIfDefaultsVariableGain OBJECT-TYPE
    SYNTAX      Unsigned32 (0..350 | 4294967295) 
    UNITS       "0.1 dB"
    MAX-ACCESS  read-only
    STATUS      current
    DESCRIPTION
        "Variable Gain of EDFA" 
    ::=  { deployProvIfDefaultsEntry 74 }

deployProvIfDefaultsBand OBJECT-TYPE
    SYNTAX      FspR7OpticalBand
    MAX-ACCESS  read-only
    STATUS      current
    DESCRIPTION   "The The optical band of the module."
    ::=  { deployProvIfDefaultsEntry 75 }

deployProvIfDefaultsSigDegThreshold OBJECT-TYPE
    SYNTAX      Unsigned32 (1..10000 | 4294967295)
    MAX-ACCESS  read-only
    STATUS      current
    DESCRIPTION
        "Threshold for number of errors (CV or CV+DE) in one second" 
    ::=  { deployProvIfDefaultsEntry 76 }

deployProvIfDefaultsSigDegPeriodIntegration OBJECT-TYPE
    SYNTAX      Unsigned32 (1..10 | 4294967295) 
    UNITS       "s"
    MAX-ACCESS  read-only
    STATUS      current
    DESCRIPTION
        "Integration Period for Signal degrade" 
    ::=  { deployProvIfDefaultsEntry 77 }

deployProvIfDefaultsVoaMode OBJECT-TYPE
    SYNTAX      FspR7VoaMode
    MAX-ACCESS  read-only
    STATUS      current
    DESCRIPTION
        "VOA operating mode" 
    ::=  { deployProvIfDefaultsEntry 78 }

deployProvIfDefaultsOpticalSetPoint OBJECT-TYPE
    SYNTAX      Integer32 (-250..100 | -2147483648) 
    UNITS       "0.1 dBm"
    MAX-ACCESS  read-only
    STATUS      current
    DESCRIPTION
        "Sets the optical power for power equalization in ROADM or for channel power control in OPCM" 
    ::=  { deployProvIfDefaultsEntry 79 }

deployProvIfDefaultsVoaSetpoint OBJECT-TYPE
    SYNTAX      Unsigned32 (0..300 | 4294967295) 
    UNITS       "0.1 dB"
    MAX-ACCESS  read-only
    STATUS      current
    DESCRIPTION
        "Sets the optical attenuation of VOA" 
    ::=  { deployProvIfDefaultsEntry 80 }

deployProvIfDefaultsLanAid OBJECT-TYPE
    SYNTAX      EntityIndex
    MAX-ACCESS  read-only
    STATUS      current
    DESCRIPTION
        "AID of LAN" 
    ::=  { deployProvIfDefaultsEntry 81 }

deployProvIfDefaultsAprHighThreshold OBJECT-TYPE
    SYNTAX      Unsigned32 
    UNITS       "0.1 dBm"
    MAX-ACCESS  read-only
    STATUS      current
    DESCRIPTION
        "Automatic Power Reduction High Threshold" 
    ::=  { deployProvIfDefaultsEntry 82 }

deployProvIfDefaultsPumpPower OBJECT-TYPE
    SYNTAX      Integer32 (115..138 | -2147483648) 
    UNITS       "0.2 dBm"
    MAX-ACCESS  read-only
    STATUS      current
    DESCRIPTION
        "Total raman pump power" 
    ::=  { deployProvIfDefaultsEntry 83 }

deployProvIfDefaultsIpType OBJECT-TYPE
    SYNTAX      FspR7IpType
    MAX-ACCESS  read-only
    STATUS      current
    DESCRIPTION
        "Type of IP configuration" 
    ::=  { deployProvIfDefaultsEntry 84 }

deployProvIfDefaultsWdmRxChannel OBJECT-TYPE
    SYNTAX      FspR7ChannelIdentifier
    MAX-ACCESS  read-only
    STATUS      current
    DESCRIPTION
        "Configuration of Rx optical channel" 
    ::=  { deployProvIfDefaultsEntry 85 }

deployProvIfDefaultsSigDegThresSonetSection OBJECT-TYPE
    SYNTAX      FspR7BERThresholdSection
    MAX-ACCESS  read-only
    STATUS      current
    DESCRIPTION
        "Bit-Error-Based Degradation Definition for SONET (standard integration period)" 
    ::=  { deployProvIfDefaultsEntry 86 }

deployProvIfDefaultsSigDegThresSdhSection OBJECT-TYPE
    SYNTAX      Unsigned32 (1..100 | 4294967295) 
    UNITS       "%"
    MAX-ACCESS  read-only
    STATUS      current
    DESCRIPTION
        "Block-Error-Based Degradation Definition for SDH (standard integration period).
         Defined as percentage Background Block Errors (30% default) evaluated
         over a defined period (SDPER-RS)." 
    ::=  { deployProvIfDefaultsEntry 87 }

deployProvIfDefaultsSigDegPeriodSdhSection OBJECT-TYPE
    SYNTAX      Unsigned32 (2..10 | 4294967295) 
    UNITS       "s"
    MAX-ACCESS  read-only
    STATUS      current
    DESCRIPTION
        "Provisionable Signal Degrade Integration Period for SDH" 
    ::=  { deployProvIfDefaultsEntry 88 }

deployProvIfDefaultsDispersionMode OBJECT-TYPE
    SYNTAX      FspR7DispersionModes
    MAX-ACCESS  read-only
    STATUS      current
    DESCRIPTION
        "Chromatic Dispersion Compensation Mode" 
    ::=  { deployProvIfDefaultsEntry 89 }

deployProvIfDefaultsDispersionSetting OBJECT-TYPE
    SYNTAX      Integer32 (-50000..50000 | -2147483648) 
    UNITS       "ps/nm"
    MAX-ACCESS  read-only
    STATUS      current
    DESCRIPTION
        "Chromatic Dispersion Compensation setting on module" 
    ::=  { deployProvIfDefaultsEntry 90 }

deployProvIfDefaultsOffset OBJECT-TYPE
    SYNTAX      Integer32 (10..30 | -2147483648) 
    UNITS       "0.1 dB"
    MAX-ACCESS  read-only
    STATUS      current
    DESCRIPTION   "Sets the offset for the mean optical power for power equalization in ROADM"
    ::=  { deployProvIfDefaultsEntry 91 }

deployProvIfDefaultsFunction OBJECT-TYPE
    SYNTAX      FspR7InterfaceFunction
    MAX-ACCESS  read-only
    STATUS      current
    DESCRIPTION
        "Interface Function" 
    ::=  { deployProvIfDefaultsEntry 92 }

deployProvIfDefaultsPortMode OBJECT-TYPE
    SYNTAX      FspR7PortMode
    MAX-ACCESS  read-only
    STATUS      current
    DESCRIPTION
        "Port Mode" 
    ::=  { deployProvIfDefaultsEntry 93 }

deployProvIfDefaultsPortRole OBJECT-TYPE
    SYNTAX      FspR7PortRole
    MAX-ACCESS  read-only
    STATUS      current
    DESCRIPTION
        "ADVA cloud Port Roles" 
    ::=  { deployProvIfDefaultsEntry 94 }

deployProvIfDefaultsUtag OBJECT-TYPE
    SYNTAX      FspR7UntaggedFrames
    MAX-ACCESS  read-only
    STATUS      current
    DESCRIPTION
        "If untagged frames shall be enabled on this port or not." 
    ::=  { deployProvIfDefaultsEntry 95 }

deployProvIfDefaultsPvid OBJECT-TYPE
    SYNTAX      Unsigned32 (1..4095 | 4294967295)
    MAX-ACCESS  read-only
    STATUS      current
    DESCRIPTION
        "Default VLAN ID (both STAG/CTAG mode) in case UTAG is enabled" 
    ::=  { deployProvIfDefaultsEntry 96 }

deployProvIfDefaultsPriority OBJECT-TYPE
    SYNTAX      Unsigned32 (0..7 | 4294967295)
    MAX-ACCESS  read-only
    STATUS      current
    DESCRIPTION
        "Default PCP in case UTAG is Enabled. The Prio may be remapped in the EVC." 
    ::=  { deployProvIfDefaultsEntry 97 }

deployProvIfDefaultsStagType OBJECT-TYPE
    SYNTAX      FspR7SnmpHexString
    MAX-ACCESS  read-only
    STATUS      current
    DESCRIPTION
        "TAG type field" 
    ::=  { deployProvIfDefaultsEntry 98 }

deployProvIfDefaultsCac OBJECT-TYPE
    SYNTAX      FspR7L2CacEnable
    MAX-ACCESS  read-only
    STATUS      current
    DESCRIPTION
        "Enable of CAC" 
    ::=  { deployProvIfDefaultsEntry 99 }

deployProvIfDefaultsMaxFrameSize OBJECT-TYPE
    SYNTAX      Unsigned32 (1518..9600 | 4294967295)
    MAX-ACCESS  read-only
    STATUS      current
    DESCRIPTION
        "Max Frame Size" 
    ::=  { deployProvIfDefaultsEntry 100 }

deployProvIfDefaultsVethAid OBJECT-TYPE
    SYNTAX      EntityIndex
    MAX-ACCESS  read-only
    STATUS      current
    DESCRIPTION
        "Shows if PORT is a member in the LAG with the VETH AID" 
    ::=  { deployProvIfDefaultsEntry 101 }

deployProvIfDefaultsLagPrio OBJECT-TYPE
    SYNTAX      Unsigned32 (0..65535 | 4294967295)
    MAX-ACCESS  read-only
    STATUS      current
    DESCRIPTION
        "Part of ID. Port pri that defines standby." 
    ::=  { deployProvIfDefaultsEntry 102 }

deployProvIfDefaultsLagPortType OBJECT-TYPE
    SYNTAX      FspR7LagPortType
    MAX-ACCESS  read-only
    STATUS      current
    DESCRIPTION
        "Type/Speed of connected ports in the Link Aggregation Group" 
    ::=  { deployProvIfDefaultsEntry 103 }

deployProvIfDefaultsLagActivePorts OBJECT-TYPE
    SYNTAX      Unsigned32 (1..12 | 4294967295)
    MAX-ACCESS  read-only
    STATUS      current
    DESCRIPTION
        "Number of active ports in the Link Aggregation Group" 
    ::=  { deployProvIfDefaultsEntry 104 }

deployProvIfDefaultsLacpMode OBJECT-TYPE
    SYNTAX      FspR7LacpMode
    MAX-ACCESS  read-only
    STATUS      current
    DESCRIPTION
        "Enable of LACP state machine" 
    ::=  { deployProvIfDefaultsEntry 105 }

deployProvIfDefaultsLagLoadBallanceSource OBJECT-TYPE
    SYNTAX      FspR7LagLoadBallanceSource
    MAX-ACCESS  read-only
    STATUS      current
    DESCRIPTION
        "What source is used in the load balance calculation" 
    ::=  { deployProvIfDefaultsEntry 106 }

deployProvIfDefaultsLacpTimeout OBJECT-TYPE
    SYNTAX      FspR7LacpTimeout
    MAX-ACCESS  read-only
    STATUS      current
    DESCRIPTION
        "Timeout of the LACP" 
    ::=  { deployProvIfDefaultsEntry 107 }

deployProvIfDefaultsFarEndCommunication OBJECT-TYPE
    SYNTAX      FspR7YesNo
    MAX-ACCESS  read-only
    STATUS      current
    DESCRIPTION
        "Used for Optojack plugs; Communication to Far End Plug is observed" 
    ::=  { deployProvIfDefaultsEntry 108 }

deployProvIfDefaultsEqlzAdmin OBJECT-TYPE
    SYNTAX      FspR7EqlzAdminState
    MAX-ACCESS  read-only
    STATUS      current
    DESCRIPTION   "Scheduled Equalization Administration"
    ::=  { deployProvIfDefaultsEntry 109 }

deployProvIfDefaultsTxOffDelay OBJECT-TYPE
    SYNTAX      FspR7EnableDisable
    MAX-ACCESS  read-only
    STATUS      current
    DESCRIPTION
        "Enable or disable TXOFFHOLD Period for Error Forwarding and LKDO-OFF Consequent Action." 
    ::=  { deployProvIfDefaultsEntry 110 }

deployProvIfDefaultsOpuPayloadType OBJECT-TYPE
    SYNTAX      FspR7OpuPayloadType
    MAX-ACCESS  read-only
    STATUS      current
    DESCRIPTION
        "OPU Payload Type Indicator" 
    ::=  { deployProvIfDefaultsEntry 111 }

deployProvIfDefaultsOscOpticalSetpoint OBJECT-TYPE
    SYNTAX      Integer32 (-250..50 | -2147483648) 
    UNITS       "0.1 dBm"
    MAX-ACCESS  read-only
    STATUS      current
    DESCRIPTION
        "Sets the OSC optical power" 
    ::=  { deployProvIfDefaultsEntry 112 }

deployProvIfDefaultsFiberBrand OBJECT-TYPE
    SYNTAX      FspR7FiberBrand
    MAX-ACCESS  read-only
    STATUS      current
    DESCRIPTION
        "Brand of fiber present in the fiber plant" 
    ::=  { deployProvIfDefaultsEntry 113 }

deployProvIfDefaultsTiltSet OBJECT-TYPE
    SYNTAX      FspR7TiltSet
    MAX-ACCESS  read-only
    STATUS      current
    DESCRIPTION
        "Tilt setting as discrete values versus a range" 
    ::=  { deployProvIfDefaultsEntry 114 }

deployProvIfDefaultsXfpDecisionThres OBJECT-TYPE
    SYNTAX      FspR7XfpDecisionThres
    MAX-ACCESS  read-only
    STATUS      current
    DESCRIPTION
        "XFP Decision threshold setting" 
    ::=  { deployProvIfDefaultsEntry 115 }

deployProvIfDefaultsAutoPTassignment OBJECT-TYPE
    SYNTAX      FspR7ManualAuto
    MAX-ACCESS  read-only
    STATUS      current
    DESCRIPTION
        "Auto assignment of ODU PT" 
    ::=  { deployProvIfDefaultsEntry 116 }

deployProvIfDefaultsTributarySlotMethod OBJECT-TYPE
    SYNTAX      FspR7ManualAuto
    MAX-ACCESS  read-only
    STATUS      current
    DESCRIPTION
        "Tributary Slot assignment method" 
    ::=  { deployProvIfDefaultsEntry 117 }

deployProvIfDefaultsOduTribPortNo OBJECT-TYPE
    SYNTAX      SnmpAdminString
    MAX-ACCESS  read-only
    STATUS      current
    DESCRIPTION
        "ODU Tributary Port Number" 
    ::=  { deployProvIfDefaultsEntry 118 }

deployProvIfDefaultsOduTribTimeSlottNo OBJECT-TYPE
    SYNTAX      SnmpAdminString
    MAX-ACCESS  read-only
    STATUS      current
    DESCRIPTION   "ODU Tributary slot number. Multiple values can be entered as a string, separated by commas or given as a range.
         For capabilities objects possible number of slots and valid range are displayed in a form:
         [1,2,3,8][count: 1-1]
         In first brackets valid slots are shown and in the second possible number of slots."
    ::=  { deployProvIfDefaultsEntry 119 }

deployProvIfDefaultsRevertiveMode OBJECT-TYPE
    SYNTAX      ApsRevertMode
    MAX-ACCESS  read-only
    STATUS      current
    DESCRIPTION
        "Revertive Protection Switching" 
    ::=  { deployProvIfDefaultsEntry 120 }

deployProvIfDefaultsLaserDelayTimer OBJECT-TYPE
    SYNTAX      FspR7LaserDelayTimer
    MAX-ACCESS  read-only
    STATUS      current
    DESCRIPTION
        "Relevant only when ERRFWD=LSROFF. Enables/disables the
         possibility to delay turning off and on the laser.
         This applies to the case when turning off the laser
         is done as an error forwarding mechanism." 
    ::=  { deployProvIfDefaultsEntry 121 }

deployProvIfDefaultsLaserOffTimer OBJECT-TYPE
    SYNTAX      Unsigned32 (1..1000 | 4294967295) 
    UNITS       "ms"
    MAX-ACCESS  read-only
    STATUS      current
    DESCRIPTION
        "Delay before laser is swiched off" 
    ::=  { deployProvIfDefaultsEntry 122 }

deployProvIfDefaultsLaserOnTimer OBJECT-TYPE
    SYNTAX      Unsigned32 (1..1000 | 4294967295) 
    UNITS       "ms"
    MAX-ACCESS  read-only
    STATUS      current
    DESCRIPTION
        "Delay before laser is switched on" 
    ::=  { deployProvIfDefaultsEntry 123 }

deployProvIfDefaultsLaneChannelSetting OBJECT-TYPE
    SYNTAX      FspR7ChannelIdentifier
    MAX-ACCESS  read-only
    STATUS      current
    DESCRIPTION
        "Lane Channel Setting" 
    ::=  { deployProvIfDefaultsEntry 124 }

deployProvIfDefaultsBip OBJECT-TYPE
    SYNTAX      FspR7Bip
    MAX-ACCESS  read-only
    STATUS      current
    DESCRIPTION
        "Bit Interleaved Parity" 
    ::=  { deployProvIfDefaultsEntry 125 }

deployProvIfDefaultsCodeGain OBJECT-TYPE
    SYNTAX      FspR7CodeGain
    MAX-ACCESS  read-only
    STATUS      current
    DESCRIPTION
        "Forward Error Correction Coding gain" 
    ::=  { deployProvIfDefaultsEntry 126 }

deployProvIfDefaultsEdfaPwrOut OBJECT-TYPE
    SYNTAX      FspR7EdfaOutputPowerRating
    MAX-ACCESS  read-only
    STATUS      current
    DESCRIPTION
        "Optical Output Power Rating - Provision" 
    ::=  { deployProvIfDefaultsEntry 127 }

deployProvIfDefaultsPrio OBJECT-TYPE
    SYNTAX      Unsigned32 (0..255 | 4294967295)
    MAX-ACCESS  read-only
    STATUS      current
    DESCRIPTION
        "Priority" 
    ::=  { deployProvIfDefaultsEntry 128 }

deployProvIfDefaultsAuthType OBJECT-TYPE
    SYNTAX      FspR7CpAuthType
    MAX-ACCESS  read-only
    STATUS      current
    DESCRIPTION
        "OSPF Authentication Type" 
    ::=  { deployProvIfDefaultsEntry 129 }

deployProvIfDefaultsAuthString OBJECT-TYPE
    SYNTAX      SnmpAdminString
    MAX-ACCESS  read-only
    STATUS      current
    DESCRIPTION
        "OSPF Authentication Key/String depending on Authentication Type" 
    ::=  { deployProvIfDefaultsEntry 130 }

deployProvIfDefaultsSigDegPcslThreshold OBJECT-TYPE
    SYNTAX      Unsigned32 (1..100 | 4294967295) 
    UNITS       "%"
    MAX-ACCESS  read-only
    STATUS      current
    DESCRIPTION
        "Block-Error-Based Degradation Definition for Physical Coding Sublayer" 
    ::=  { deployProvIfDefaultsEntry 131 }

deployProvVchChannelTable OBJECT-TYPE
    SYNTAX      SEQUENCE OF DeployProvVchChannelEntry
    MAX-ACCESS  not-accessible
    STATUS      current
    DESCRIPTION   "Contains entries for provisioning of interfaces."
    ::=  { facilityDeployProv 4 }

deployProvVchChannelEntry OBJECT-TYPE
    SYNTAX      DeployProvVchChannelEntry
    MAX-ACCESS  not-accessible
    STATUS      current
    DESCRIPTION   "All interfaces which are provisioned(or are during
         provisioning) will have an entry in this table."
    INDEX       {
                  entityIndex
                }
    ::=  { deployProvVchChannelTable 1 }

DeployProvVchChannelEntry ::=  SEQUENCE
  { deployProvVchChannelRowStatus RowStatus,
    deployProvVchChannelForceDestroy FspR7ForcedStatus,
    deployProvVchChannelType FspR7InterfaceType,
    deployProvVchChannelVcgType VirtualContainerType,
    deployProvVchChannelBundle SonetVcBundleAllocation,
    deployProvVchChannelCir Unsigned32,
    deployProvVchChannelAdmin FspR7AdminState,
    deployProvVchChannelSigDegThresOdu Integer32,
    deployProvVchChannelSigDegPeriodOdu Unsigned32,
    deployProvVchChannelTraceExpectedOdu OCTET STRING,
    deployProvVchChannelTraceTransmitSapiOdu OCTET STRING,
    deployProvVchChannelTraceTransmitDapiOdu OCTET STRING,
    deployProvVchChannelTraceTransmitOpspOdu OCTET STRING,
    deployProvVchChannelTimModeOdu TimMode,
    deployProvVchChannelEqlzAdmin FspR7EqlzAdminState }

deployProvVchChannelRowStatus OBJECT-TYPE
    SYNTAX      RowStatus
    MAX-ACCESS  read-write
    STATUS      current
    DESCRIPTION   "RowStatus"
    ::=  { deployProvVchChannelEntry 1 }

deployProvVchChannelForceDestroy OBJECT-TYPE
    SYNTAX      FspR7ForcedStatus
    MAX-ACCESS  read-write
    STATUS      current
    DESCRIPTION
        "Forced Destroy" 
    ::=  { deployProvVchChannelEntry 2 }

deployProvVchChannelType OBJECT-TYPE
    SYNTAX      FspR7InterfaceType
    MAX-ACCESS  read-write
    STATUS      current
    DESCRIPTION   "The TYPE defines the transport service type as wrapper
         with wrapper layer termination OR else as payload"
    ::=  { deployProvVchChannelEntry 3 }

deployProvVchChannelVcgType OBJECT-TYPE
    SYNTAX      VirtualContainerType
    MAX-ACCESS  read-write
    STATUS      current
    DESCRIPTION
        "Virtual Container Group Type" 
    ::=  { deployProvVchChannelEntry 4 }

deployProvVchChannelBundle OBJECT-TYPE
    SYNTAX      SonetVcBundleAllocation
    MAX-ACCESS  read-write
    STATUS      current
    DESCRIPTION
        "List of VC4/VC3/STS1/STS3c/STS24c/STS48c containers used in the BUNDLE" 
    ::=  { deployProvVchChannelEntry 5 }

deployProvVchChannelCir OBJECT-TYPE
    SYNTAX      Unsigned32 
    UNITS       "Mbps"
    MAX-ACCESS  read-write
    STATUS      current
    DESCRIPTION
        "CIR (Committed Information Rate ) is used on Ethernet Interfaces with a policing function" 
    ::=  { deployProvVchChannelEntry 6 }

deployProvVchChannelAdmin OBJECT-TYPE
    SYNTAX      FspR7AdminState
    MAX-ACCESS  read-write
    STATUS      current
    DESCRIPTION
        "Administrative State is displayed in the GUI and Craft. Transition to Unassigend requires the entity to be deleted." 
    ::=  { deployProvVchChannelEntry 7 }

deployProvVchChannelSigDegThresOdu OBJECT-TYPE
    SYNTAX      Integer32 (1..100 | -2147483648) 
    UNITS       "%"
    MAX-ACCESS  read-write
    STATUS      current
    DESCRIPTION
        "Background-Block-Error-Based Signal Degradation Definition for ODU" 
    ::=  { deployProvVchChannelEntry 8 }

deployProvVchChannelSigDegPeriodOdu OBJECT-TYPE
    SYNTAX      Unsigned32 (2..10 | 4294967295) 
    UNITS       "s"
    MAX-ACCESS  read-write
    STATUS      current
    DESCRIPTION
        "Integration Period for Signal degrade" 
    ::=  { deployProvVchChannelEntry 9 }

deployProvVchChannelTraceExpectedOdu OBJECT-TYPE
    SYNTAX      OCTET STRING (SIZE(0..15))
    MAX-ACCESS  read-write
    STATUS      current
    DESCRIPTION   "Expected SAPI part of the ODU trace (15 character).
         NULL TRACE implies that no trace comparison is made."
    ::=  { deployProvVchChannelEntry 10 }

deployProvVchChannelTraceTransmitSapiOdu OBJECT-TYPE
    SYNTAX      OCTET STRING (SIZE(0..15))
    MAX-ACCESS  read-write
    STATUS      current
    DESCRIPTION
        "The transmitted SAPI part of the ODU trace (15 character)" 
    ::=  { deployProvVchChannelEntry 11 }

deployProvVchChannelTraceTransmitDapiOdu OBJECT-TYPE
    SYNTAX      OCTET STRING (SIZE(0..15))
    MAX-ACCESS  read-write
    STATUS      current
    DESCRIPTION
        "The transmitted DAPI part of the ODU trace (15 character)" 
    ::=  { deployProvVchChannelEntry 12 }

deployProvVchChannelTraceTransmitOpspOdu OBJECT-TYPE
    SYNTAX      OCTET STRING (SIZE(0..32))
    MAX-ACCESS  read-write
    STATUS      current
    DESCRIPTION
        "The transmitted Operator Specific part of the ODU trace (32 character)" 
    ::=  { deployProvVchChannelEntry 13 }

deployProvVchChannelTimModeOdu OBJECT-TYPE
    SYNTAX      TimMode
    MAX-ACCESS  read-write
    STATUS      current
    DESCRIPTION
        "Detection of TIM-ODU Condition can be configured" 
    ::=  { deployProvVchChannelEntry 14 }

deployProvVchChannelEqlzAdmin OBJECT-TYPE
    SYNTAX      FspR7EqlzAdminState
    MAX-ACCESS  read-write
    STATUS      current
    DESCRIPTION   "Scheduled Equalization Administration"
    ::=  { deployProvVchChannelEntry 15 }

deployProvVchChannelCapTable OBJECT-TYPE
    SYNTAX      SEQUENCE OF DeployProvVchChannelCapEntry
    MAX-ACCESS  not-accessible
    STATUS      current
    DESCRIPTION   "Contains entries for provisioning of interfaces."
    ::=  { facilityDeployProv 5  }

deployProvVchChannelCapEntry OBJECT-TYPE
    SYNTAX      DeployProvVchChannelCapEntry
    MAX-ACCESS  not-accessible
    STATUS      current
    DESCRIPTION   "All interfaces which are provisioned(or are during
         provisioning) will have an entry in this table."
    INDEX       { entityIndex }
    ::=  { deployProvVchChannelCapTable 1 }

DeployProvVchChannelCapEntry ::=  SEQUENCE
  { deployProvVchChannelCapRowStatus FspR7RowStatusCaps,
    deployProvVchChannelCapForceDestroy FspR7ForcedStatusCaps,
    deployProvVchChannelCapType FspR7InterfaceTypeCaps,
    deployProvVchChannelCapVcgType VirtualContainerTypeCaps,
    deployProvVchChannelCapBundle SonetVcBundleAllocationCaps,
    deployProvVchChannelCapCir FspR7Unsigned32Caps,
    deployProvVchChannelCapAdmin FspR7AdminStateCaps,
    deployProvVchChannelCapSigDegThresOdu FspR7Integer32Caps,
    deployProvVchChannelCapSigDegPeriodOdu FspR7Unsigned32Caps,
    deployProvVchChannelCapTraceExpectedOdu Integer32,
    deployProvVchChannelCapTraceTransmitSapiOdu Integer32,
    deployProvVchChannelCapTraceTransmitDapiOdu Integer32,
    deployProvVchChannelCapTraceTransmitOpspOdu Integer32,
    deployProvVchChannelCapTimModeOdu TimModeCaps,
    deployProvVchChannelCapEqlzAdmin FspR7EqlzAdminStateCaps }

deployProvVchChannelCapRowStatus OBJECT-TYPE
    SYNTAX      FspR7RowStatusCaps
    MAX-ACCESS  read-only
    STATUS      current
    DESCRIPTION   "RowStatus"
    ::=  { deployProvVchChannelCapEntry 1 }

deployProvVchChannelCapForceDestroy OBJECT-TYPE
    SYNTAX      FspR7ForcedStatusCaps
    MAX-ACCESS  read-only
    STATUS      current
    DESCRIPTION
        "Forced Destroy" 
    ::=  { deployProvVchChannelCapEntry 2 }

deployProvVchChannelCapType OBJECT-TYPE
    SYNTAX      FspR7InterfaceTypeCaps
    MAX-ACCESS  read-only
    STATUS      current
    DESCRIPTION   "The TYPE defines the transport service type as wrapper
         with wrapper layer termination OR else as payload"
    ::=  { deployProvVchChannelCapEntry 3 }

deployProvVchChannelCapVcgType OBJECT-TYPE
    SYNTAX      VirtualContainerTypeCaps
    MAX-ACCESS  read-only
    STATUS      current
    DESCRIPTION
        "Virtual Container Group Type" 
    ::=  { deployProvVchChannelCapEntry 4 }

deployProvVchChannelCapBundle OBJECT-TYPE
    SYNTAX      SonetVcBundleAllocationCaps
    MAX-ACCESS  read-only
    STATUS      current
    DESCRIPTION
        "List of VC4/VC3/STS1/STS3c/STS24c/STS48c containers used in the BUNDLE" 
    ::=  { deployProvVchChannelCapEntry 5 }

deployProvVchChannelCapCir OBJECT-TYPE
    SYNTAX      FspR7Unsigned32Caps
    UNITS       "Mbps"
    MAX-ACCESS  read-only
    STATUS      current
    DESCRIPTION
        "CIR (Committed Information Rate ) is used on Ethernet Interfaces with a policing function" 
    ::=  { deployProvVchChannelCapEntry 6 }

deployProvVchChannelCapAdmin OBJECT-TYPE
    SYNTAX      FspR7AdminStateCaps
    MAX-ACCESS  read-only
    STATUS      current
    DESCRIPTION
        "Administrative State is displayed in the GUI and Craft. Transition to Unassigend requires the entity to be deleted." 
    ::=  { deployProvVchChannelCapEntry 7 }

deployProvVchChannelCapSigDegThresOdu OBJECT-TYPE
    SYNTAX      FspR7Integer32Caps
    UNITS       "%"
    MAX-ACCESS  read-only
    STATUS      current
    DESCRIPTION
        "Background-Block-Error-Based Signal Degradation Definition for ODU" 
    ::=  { deployProvVchChannelCapEntry 8 }

deployProvVchChannelCapSigDegPeriodOdu OBJECT-TYPE
    SYNTAX      FspR7Unsigned32Caps
    UNITS       "s"
    MAX-ACCESS  read-only
    STATUS      current
    DESCRIPTION
        "Integration Period for Signal degrade" 
    ::=  { deployProvVchChannelCapEntry 9 }

deployProvVchChannelCapTraceExpectedOdu OBJECT-TYPE
    SYNTAX      Integer32
    MAX-ACCESS  read-only
    STATUS      current
    DESCRIPTION   "Expected SAPI part of the ODU trace (15 character).
         NULL TRACE implies that no trace comparison is made."
    ::=  { deployProvVchChannelCapEntry 10 }

deployProvVchChannelCapTraceTransmitSapiOdu OBJECT-TYPE
    SYNTAX      Integer32
    MAX-ACCESS  read-only
    STATUS      current
    DESCRIPTION
        "The transmitted SAPI part of the ODU trace (15 character)" 
    ::=  { deployProvVchChannelCapEntry 11 }

deployProvVchChannelCapTraceTransmitDapiOdu OBJECT-TYPE
    SYNTAX      Integer32
    MAX-ACCESS  read-only
    STATUS      current
    DESCRIPTION
        "The transmitted DAPI part of the ODU trace (15 character)" 
    ::=  { deployProvVchChannelCapEntry 12 }

deployProvVchChannelCapTraceTransmitOpspOdu OBJECT-TYPE
    SYNTAX      Integer32
    MAX-ACCESS  read-only
    STATUS      current
    DESCRIPTION
        "The transmitted Operator Specific part of the ODU trace (32 character)" 
    ::=  { deployProvVchChannelCapEntry 13 }

deployProvVchChannelCapTimModeOdu OBJECT-TYPE
    SYNTAX      TimModeCaps
    MAX-ACCESS  read-only
    STATUS      current
    DESCRIPTION
        "Detection of TIM-ODU Condition can be configured" 
    ::=  { deployProvVchChannelCapEntry 14 }

deployProvVchChannelCapEqlzAdmin OBJECT-TYPE
    SYNTAX      FspR7EqlzAdminStateCaps
    MAX-ACCESS  read-only
    STATUS      current
    DESCRIPTION   "Scheduled Equalization Administration"
    ::=  { deployProvVchChannelCapEntry 15 }

deployProvVchChannelDefaultsTable  OBJECT-TYPE
    SYNTAX      SEQUENCE OF DeployProvVchChannelDefaultsEntry
    MAX-ACCESS  not-accessible
    STATUS      current
    DESCRIPTION   "Contains entries for provisioning of interfaces."
    ::=  { facilityDeployProv 6  }

deployProvVchChannelDefaultsEntry OBJECT-TYPE
    SYNTAX      DeployProvVchChannelDefaultsEntry
    MAX-ACCESS  not-accessible
    STATUS      current
    DESCRIPTION   "All interfaces which are provisioned(or are during
         provisioning) will have an entry in this table."
    INDEX       { entityIndex }
    ::=  { deployProvVchChannelDefaultsTable 1 }

DeployProvVchChannelDefaultsEntry ::=  SEQUENCE
  { deployProvVchChannelDefaultsRowStatus RowStatus,
    deployProvVchChannelDefaultsForceDestroy FspR7ForcedStatus,
    deployProvVchChannelDefaultsType FspR7InterfaceType,
    deployProvVchChannelDefaultsVcgType VirtualContainerType,
    deployProvVchChannelDefaultsBundle SonetVcBundleAllocation,
    deployProvVchChannelDefaultsCir Unsigned32,
    deployProvVchChannelDefaultsAdmin FspR7AdminState,
    deployProvVchChannelDefaultsSigDegThresOdu Integer32,
    deployProvVchChannelDefaultsSigDegPeriodOdu Unsigned32,
    deployProvVchChannelDefaultsTraceExpectedOdu OCTET STRING,
    deployProvVchChannelDefaultsTraceTransmitSapiOdu OCTET STRING,
    deployProvVchChannelDefaultsTraceTransmitDapiOdu OCTET STRING,
    deployProvVchChannelDefaultsTraceTransmitOpspOdu OCTET STRING,
    deployProvVchChannelDefaultsTimModeOdu TimMode,
    deployProvVchChannelDefaultsEqlzAdmin FspR7EqlzAdminState }

deployProvVchChannelDefaultsRowStatus OBJECT-TYPE
    SYNTAX      RowStatus
    MAX-ACCESS  read-only
    STATUS      current
    DESCRIPTION   "RowStatus"
    ::=  { deployProvVchChannelDefaultsEntry 1 }

deployProvVchChannelDefaultsForceDestroy OBJECT-TYPE
    SYNTAX      FspR7ForcedStatus
    MAX-ACCESS  read-only
    STATUS      current
    DESCRIPTION
        "Forced Destroy" 
    ::=  { deployProvVchChannelDefaultsEntry 2 }

deployProvVchChannelDefaultsType OBJECT-TYPE
    SYNTAX      FspR7InterfaceType
    MAX-ACCESS  read-only
    STATUS      current
    DESCRIPTION   "The TYPE defines the transport service type as wrapper
         with wrapper layer termination OR else as payload"
    ::=  { deployProvVchChannelDefaultsEntry 3 }

deployProvVchChannelDefaultsVcgType OBJECT-TYPE
    SYNTAX      VirtualContainerType
    MAX-ACCESS  read-only
    STATUS      current
    DESCRIPTION
        "Virtual Container Group Type" 
    ::=  { deployProvVchChannelDefaultsEntry 4 }

deployProvVchChannelDefaultsBundle OBJECT-TYPE
    SYNTAX      SonetVcBundleAllocation
    MAX-ACCESS  read-only
    STATUS      current
    DESCRIPTION
        "List of VC4/VC3/STS1/STS3c/STS24c/STS48c containers used in the BUNDLE" 
    ::=  { deployProvVchChannelDefaultsEntry 5 }

deployProvVchChannelDefaultsCir OBJECT-TYPE
    SYNTAX      Unsigned32 
    UNITS       "Mbps"
    MAX-ACCESS  read-only
    STATUS      current
    DESCRIPTION
        "CIR (Committed Information Rate ) is used on Ethernet Interfaces with a policing function" 
    ::=  { deployProvVchChannelDefaultsEntry 6 }

deployProvVchChannelDefaultsAdmin OBJECT-TYPE
    SYNTAX      FspR7AdminState
    MAX-ACCESS  read-only
    STATUS      current
    DESCRIPTION
        "Administrative State is displayed in the GUI and Craft. Transition to Unassigend requires the entity to be deleted." 
    ::=  { deployProvVchChannelDefaultsEntry 7 }

deployProvVchChannelDefaultsSigDegThresOdu OBJECT-TYPE
    SYNTAX      Integer32 (1..100 | -2147483648) 
    UNITS       "%"
    MAX-ACCESS  read-only
    STATUS      current
    DESCRIPTION
        "Background-Block-Error-Based Signal Degradation Definition for ODU" 
    ::=  { deployProvVchChannelDefaultsEntry 8 }

deployProvVchChannelDefaultsSigDegPeriodOdu OBJECT-TYPE
    SYNTAX      Unsigned32 (2..10 | 4294967295) 
    UNITS       "s"
    MAX-ACCESS  read-only
    STATUS      current
    DESCRIPTION
        "Integration Period for Signal degrade" 
    ::=  { deployProvVchChannelDefaultsEntry 9 }

deployProvVchChannelDefaultsTraceExpectedOdu OBJECT-TYPE
    SYNTAX      OCTET STRING (SIZE(0..15))
    MAX-ACCESS  read-only
    STATUS      current
    DESCRIPTION   "Expected SAPI part of the ODU trace (15 character).
         NULL TRACE implies that no trace comparison is made."
    ::=  { deployProvVchChannelDefaultsEntry 10 }

deployProvVchChannelDefaultsTraceTransmitSapiOdu OBJECT-TYPE
    SYNTAX      OCTET STRING (SIZE(0..15))
    MAX-ACCESS  read-only
    STATUS      current
    DESCRIPTION
        "The transmitted SAPI part of the ODU trace (15 character)" 
    ::=  { deployProvVchChannelDefaultsEntry 11 }

deployProvVchChannelDefaultsTraceTransmitDapiOdu OBJECT-TYPE
    SYNTAX      OCTET STRING (SIZE(0..15))
    MAX-ACCESS  read-only
    STATUS      current
    DESCRIPTION
        "The transmitted DAPI part of the ODU trace (15 character)" 
    ::=  { deployProvVchChannelDefaultsEntry 12 }

deployProvVchChannelDefaultsTraceTransmitOpspOdu OBJECT-TYPE
    SYNTAX      OCTET STRING (SIZE(0..32))
    MAX-ACCESS  read-only
    STATUS      current
    DESCRIPTION
        "The transmitted Operator Specific part of the ODU trace (32 character)" 
    ::=  { deployProvVchChannelDefaultsEntry 13 }

deployProvVchChannelDefaultsTimModeOdu OBJECT-TYPE
    SYNTAX      TimMode
    MAX-ACCESS  read-only
    STATUS      current
    DESCRIPTION
        "Detection of TIM-ODU Condition can be configured" 
    ::=  { deployProvVchChannelDefaultsEntry 14 }

deployProvVchChannelDefaultsEqlzAdmin OBJECT-TYPE
    SYNTAX      FspR7EqlzAdminState
    MAX-ACCESS  read-only
    STATUS      current
    DESCRIPTION   "Scheduled Equalization Administration"
    ::=  { deployProvVchChannelDefaultsEntry 15 }

deployProvApsTable OBJECT-TYPE
    SYNTAX      SEQUENCE OF DeployProvApsEntry
    MAX-ACCESS  not-accessible
    STATUS      current
    DESCRIPTION   "Contains entries for provisioning aps."
    ::=  { facilityDeployProv 7 }

deployProvApsEntry OBJECT-TYPE
    SYNTAX      DeployProvApsEntry
    MAX-ACCESS  not-accessible
    STATUS      current
    DESCRIPTION   "All protection groups which have been provisioned(or are during provisioning)
         will have an entry in this table."
    INDEX       {
                  entityIndex
                }
    ::=  { deployProvApsTable 1 }

DeployProvApsEntry ::=  SEQUENCE
  { deployProvApsRowStatus RowStatus,
    deployProvApsForceDestroy FspR7ForcedStatus,
    deployProvApsSDswitching EnableState,
    deployProvApsHoldOffTime ApsHoldoffTime,
    deployProvApsProtectionMech ProtectionMech,
    deployProvApsWorkingAid EntityIndex,
    deployProvApsProtectionAid EntityIndex,
    deployProvApsSignalDegradeSwitching EnableState,
    deployProvApsSignalFailureSwitching EnableState,
    deployProvApsFarEndIp IpAddress,
    deployProvApsPeerAid EntityIndex,
    deployProvApsApsType ApsType,
    deployProvApsRevertMode ApsRevertMode,
    deployProvApsWaitToRestore Unsigned32,
    deployProvApsDirection ApsDirection }

deployProvApsRowStatus OBJECT-TYPE
    SYNTAX      RowStatus
    MAX-ACCESS  read-write
    STATUS      current
    DESCRIPTION   "RowStatus"
    ::=  { deployProvApsEntry 1 }

deployProvApsForceDestroy OBJECT-TYPE
    SYNTAX      FspR7ForcedStatus
    MAX-ACCESS  read-write
    STATUS      current
    DESCRIPTION
        "Forced Destroy" 
    ::=  { deployProvApsEntry 2 }

deployProvApsSDswitching OBJECT-TYPE
    SYNTAX      EnableState
    MAX-ACCESS  read-write
    STATUS      current
    DESCRIPTION   "This state controls whether the switch criteria for the APS group will
         include the Signal Degrade alarm."
    ::=  { deployProvApsEntry 3 }

deployProvApsHoldOffTime OBJECT-TYPE
    SYNTAX      ApsHoldoffTime
    MAX-ACCESS  read-write
    STATUS      current
    DESCRIPTION   "This value controls the switch delay (0 to 10 seconds in
         100ms steps) for the protection group. Changing the hold-off
         time when the timer is active will not affect the active
         timer. The change will take effect the next time the timer
         is active."
    ::=  { deployProvApsEntry 4 }

deployProvApsProtectionMech OBJECT-TYPE
    SYNTAX      ProtectionMech
    MAX-ACCESS  read-write
    STATUS      current
    DESCRIPTION   "The protection type of this protection group."
    ::=  { deployProvApsEntry 5 }

deployProvApsWorkingAid OBJECT-TYPE
    SYNTAX      EntityIndex
    MAX-ACCESS  read-write
    STATUS      current
    DESCRIPTION
        "AID of working port involved in the protection group." 
    ::=  { deployProvApsEntry 6 }

deployProvApsProtectionAid OBJECT-TYPE
    SYNTAX      EntityIndex
    MAX-ACCESS  read-write
    STATUS      current
    DESCRIPTION
        "(Protection AID) AID of protection entity involved in the protection group." 
    ::=  { deployProvApsEntry 7 }

deployProvApsSignalDegradeSwitching OBJECT-TYPE
    SYNTAX      EnableState
    MAX-ACCESS  read-write
    STATUS      current
    DESCRIPTION
        "Switch Trigger Additionally on Signal Degrade Link Detection" 
    ::=  { deployProvApsEntry 8 }

deployProvApsSignalFailureSwitching OBJECT-TYPE
    SYNTAX      EnableState
    MAX-ACCESS  read-write
    STATUS      current
    DESCRIPTION
        "Switch Trigger on Signal Failure Link Detection" 
    ::=  { deployProvApsEntry 9 }

deployProvApsFarEndIp OBJECT-TYPE
    SYNTAX      IpAddress
    MAX-ACCESS  read-write
    STATUS      current
    DESCRIPTION   "IP Address assigned to PPP Termination Point on Far-End NE. Default
         is set by NE System on LINK establishment if FENDIPACPT = Y"
    ::=  { deployProvApsEntry 10 }

deployProvApsPeerAid OBJECT-TYPE
    SYNTAX      EntityIndex
    MAX-ACCESS  read-write
    STATUS      current
    DESCRIPTION
        "AID of Protection Partner involved in the protection group." 
    ::=  { deployProvApsEntry 11 }

deployProvApsApsType OBJECT-TYPE
    SYNTAX      ApsType
    MAX-ACCESS  read-write
    STATUS      current
    DESCRIPTION   "The type of APS implemented in this protection group."
    ::=  { deployProvApsEntry 12 }

deployProvApsRevertMode OBJECT-TYPE
    SYNTAX      ApsRevertMode
    MAX-ACCESS  read-write
    STATUS      current
    DESCRIPTION
        "Revertive Protection Switching" 
    ::=  { deployProvApsEntry 13 }

deployProvApsWaitToRestore OBJECT-TYPE
    SYNTAX      Unsigned32 (5..12 | 4294967295) 
    UNITS       "min"
    MAX-ACCESS  read-write
    STATUS      current
    DESCRIPTION
        "Wait to Restore Timer value" 
    ::=  { deployProvApsEntry 14 }

deployProvApsDirection OBJECT-TYPE
    SYNTAX      ApsDirection
    MAX-ACCESS  read-write
    STATUS      current
    DESCRIPTION   "Indicates whether the APS function is 'unidirectional' (single-ended)
         or 'bidirectional' (dual-ended)."
    ::=  { deployProvApsEntry 15 }

deployProvApsCapTable OBJECT-TYPE
    SYNTAX      SEQUENCE OF DeployProvApsCapEntry
    MAX-ACCESS  not-accessible
    STATUS      current
    DESCRIPTION   "Contains entries for provisioning aps."
    ::=  { facilityDeployProv 8  }

deployProvApsCapEntry OBJECT-TYPE
    SYNTAX      DeployProvApsCapEntry
    MAX-ACCESS  not-accessible
    STATUS      current
    DESCRIPTION   "All protection groups which have been provisioned(or are during provisioning)
         will have an entry in this table."
    INDEX       { entityIndex }
    ::=  { deployProvApsCapTable 1 }

DeployProvApsCapEntry ::=  SEQUENCE
  { deployProvApsCapRowStatus FspR7RowStatusCaps,
    deployProvApsCapForceDestroy FspR7ForcedStatusCaps,
    deployProvApsCapSDswitching EnableStateCaps,
    deployProvApsCapHoldOffTime ApsHoldoffTimeCaps,
    deployProvApsCapProtectionMech ProtectionMechCaps,
    deployProvApsCapWorkingAid Integer32,
    deployProvApsCapProtectionAid Integer32,
    deployProvApsCapSignalDegradeSwitching EnableStateCaps,
    deployProvApsCapSignalFailureSwitching EnableStateCaps,
    deployProvApsCapFarEndIp FspR7YesNo,
    deployProvApsCapPeerAid Integer32,
    deployProvApsCapApsType ApsTypeCaps,
    deployProvApsCapRevertMode ApsRevertModeCaps,
    deployProvApsCapWaitToRestore FspR7Unsigned32Caps,
    deployProvApsCapDirection ApsDirectionCaps }

deployProvApsCapRowStatus OBJECT-TYPE
    SYNTAX      FspR7RowStatusCaps
    MAX-ACCESS  read-only
    STATUS      current
    DESCRIPTION   "RowStatus"
    ::=  { deployProvApsCapEntry 1 }

deployProvApsCapForceDestroy OBJECT-TYPE
    SYNTAX      FspR7ForcedStatusCaps
    MAX-ACCESS  read-only
    STATUS      current
    DESCRIPTION
        "Forced Destroy" 
    ::=  { deployProvApsCapEntry 2 }

deployProvApsCapSDswitching OBJECT-TYPE
    SYNTAX      EnableStateCaps
    MAX-ACCESS  read-only
    STATUS      current
    DESCRIPTION   "This state controls whether the switch criteria for the APS group will
         include the Signal Degrade alarm."
    ::=  { deployProvApsCapEntry 3 }

deployProvApsCapHoldOffTime OBJECT-TYPE
    SYNTAX      ApsHoldoffTimeCaps
    MAX-ACCESS  read-only
    STATUS      current
    DESCRIPTION   "This value controls the switch delay (0 to 10 seconds in
         100ms steps) for the protection group. Changing the hold-off
         time when the timer is active will not affect the active
         timer. The change will take effect the next time the timer
         is active."
    ::=  { deployProvApsCapEntry 4 }

deployProvApsCapProtectionMech OBJECT-TYPE
    SYNTAX      ProtectionMechCaps
    MAX-ACCESS  read-only
    STATUS      current
    DESCRIPTION   "The protection type of this protection group."
    ::=  { deployProvApsCapEntry 5 }

deployProvApsCapWorkingAid OBJECT-TYPE
    SYNTAX      Integer32
    MAX-ACCESS  read-only
    STATUS      current
    DESCRIPTION
        "AID of working port involved in the protection group." 
    ::=  { deployProvApsCapEntry 6 }

deployProvApsCapProtectionAid OBJECT-TYPE
    SYNTAX      Integer32
    MAX-ACCESS  read-only
    STATUS      current
    DESCRIPTION
        "(Protection AID) AID of protection entity involved in the protection group." 
    ::=  { deployProvApsCapEntry 7 }

deployProvApsCapSignalDegradeSwitching OBJECT-TYPE
    SYNTAX      EnableStateCaps
    MAX-ACCESS  read-only
    STATUS      current
    DESCRIPTION
        "Switch Trigger Additionally on Signal Degrade Link Detection" 
    ::=  { deployProvApsCapEntry 8 }

deployProvApsCapSignalFailureSwitching OBJECT-TYPE
    SYNTAX      EnableStateCaps
    MAX-ACCESS  read-only
    STATUS      current
    DESCRIPTION
        "Switch Trigger on Signal Failure Link Detection" 
    ::=  { deployProvApsCapEntry 9 }

deployProvApsCapFarEndIp OBJECT-TYPE
    SYNTAX      FspR7YesNo
    MAX-ACCESS  read-only
    STATUS      current
    DESCRIPTION   "IP Address assigned to PPP Termination Point on Far-End NE. Default
         is set by NE System on LINK establishment if FENDIPACPT = Y"
    ::=  { deployProvApsCapEntry 10 }

deployProvApsCapPeerAid OBJECT-TYPE
    SYNTAX      Integer32
    MAX-ACCESS  read-only
    STATUS      current
    DESCRIPTION
        "AID of Protection Partner involved in the protection group." 
    ::=  { deployProvApsCapEntry 11 }

deployProvApsCapApsType OBJECT-TYPE
    SYNTAX      ApsTypeCaps
    MAX-ACCESS  read-only
    STATUS      current
    DESCRIPTION   "The type of APS implemented in this protection group."
    ::=  { deployProvApsCapEntry 12 }

deployProvApsCapRevertMode OBJECT-TYPE
    SYNTAX      ApsRevertModeCaps
    MAX-ACCESS  read-only
    STATUS      current
    DESCRIPTION
        "Revertive Protection Switching" 
    ::=  { deployProvApsCapEntry 13 }

deployProvApsCapWaitToRestore OBJECT-TYPE
    SYNTAX      FspR7Unsigned32Caps
    UNITS       "min"
    MAX-ACCESS  read-only
    STATUS      current
    DESCRIPTION
        "Wait to Restore Timer value" 
    ::=  { deployProvApsCapEntry 14 }

deployProvApsCapDirection OBJECT-TYPE
    SYNTAX      ApsDirectionCaps
    MAX-ACCESS  read-only
    STATUS      current
    DESCRIPTION   "Indicates whether the APS function is 'unidirectional' (single-ended)
         or 'bidirectional' (dual-ended)."
    ::=  { deployProvApsCapEntry 15 }

deployProvApsDefaultsTable  OBJECT-TYPE
    SYNTAX      SEQUENCE OF DeployProvApsDefaultsEntry
    MAX-ACCESS  not-accessible
    STATUS      current
    DESCRIPTION   "Contains entries for provisioning aps."
    ::=  { facilityDeployProv 9  }

deployProvApsDefaultsEntry OBJECT-TYPE
    SYNTAX      DeployProvApsDefaultsEntry
    MAX-ACCESS  not-accessible
    STATUS      current
    DESCRIPTION   "All protection groups which have been provisioned(or are during provisioning)
         will have an entry in this table."
    INDEX       { entityIndex }
    ::=  { deployProvApsDefaultsTable 1 }

DeployProvApsDefaultsEntry ::=  SEQUENCE
  { deployProvApsDefaultsRowStatus RowStatus,
    deployProvApsDefaultsForceDestroy FspR7ForcedStatus,
    deployProvApsDefaultsSDswitching EnableState,
    deployProvApsDefaultsHoldOffTime ApsHoldoffTime,
    deployProvApsDefaultsProtectionMech ProtectionMech,
    deployProvApsDefaultsWorkingAid EntityIndex,
    deployProvApsDefaultsProtectionAid EntityIndex,
    deployProvApsDefaultsSignalDegradeSwitching EnableState,
    deployProvApsDefaultsSignalFailureSwitching EnableState,
    deployProvApsDefaultsFarEndIp IpAddress,
    deployProvApsDefaultsPeerAid EntityIndex,
    deployProvApsDefaultsApsType ApsType,
    deployProvApsDefaultsRevertMode ApsRevertMode,
    deployProvApsDefaultsWaitToRestore Unsigned32,
    deployProvApsDefaultsDirection ApsDirection }

deployProvApsDefaultsRowStatus OBJECT-TYPE
    SYNTAX      RowStatus
    MAX-ACCESS  read-only
    STATUS      current
    DESCRIPTION   "RowStatus"
    ::=  { deployProvApsDefaultsEntry 1 }

deployProvApsDefaultsForceDestroy OBJECT-TYPE
    SYNTAX      FspR7ForcedStatus
    MAX-ACCESS  read-only
    STATUS      current
    DESCRIPTION
        "Forced Destroy" 
    ::=  { deployProvApsDefaultsEntry 2 }

deployProvApsDefaultsSDswitching OBJECT-TYPE
    SYNTAX      EnableState
    MAX-ACCESS  read-only
    STATUS      current
    DESCRIPTION   "This state controls whether the switch criteria for the APS group will
         include the Signal Degrade alarm."
    ::=  { deployProvApsDefaultsEntry 3 }

deployProvApsDefaultsHoldOffTime OBJECT-TYPE
    SYNTAX      ApsHoldoffTime
    MAX-ACCESS  read-only
    STATUS      current
    DESCRIPTION   "This value controls the switch delay (0 to 10 seconds in
         100ms steps) for the protection group. Changing the hold-off
         time when the timer is active will not affect the active
         timer. The change will take effect the next time the timer
         is active."
    ::=  { deployProvApsDefaultsEntry 4 }

deployProvApsDefaultsProtectionMech OBJECT-TYPE
    SYNTAX      ProtectionMech
    MAX-ACCESS  read-only
    STATUS      current
    DESCRIPTION   "The protection type of this protection group."
    ::=  { deployProvApsDefaultsEntry 5 }

deployProvApsDefaultsWorkingAid OBJECT-TYPE
    SYNTAX      EntityIndex
    MAX-ACCESS  read-only
    STATUS      current
    DESCRIPTION
        "AID of working port involved in the protection group." 
    ::=  { deployProvApsDefaultsEntry 6 }

deployProvApsDefaultsProtectionAid OBJECT-TYPE
    SYNTAX      EntityIndex
    MAX-ACCESS  read-only
    STATUS      current
    DESCRIPTION
        "(Protection AID) AID of protection entity involved in the protection group." 
    ::=  { deployProvApsDefaultsEntry 7 }

deployProvApsDefaultsSignalDegradeSwitching OBJECT-TYPE
    SYNTAX      EnableState
    MAX-ACCESS  read-only
    STATUS      current
    DESCRIPTION
        "Switch Trigger Additionally on Signal Degrade Link Detection" 
    ::=  { deployProvApsDefaultsEntry 8 }

deployProvApsDefaultsSignalFailureSwitching OBJECT-TYPE
    SYNTAX      EnableState
    MAX-ACCESS  read-only
    STATUS      current
    DESCRIPTION
        "Switch Trigger on Signal Failure Link Detection" 
    ::=  { deployProvApsDefaultsEntry 9 }

deployProvApsDefaultsFarEndIp OBJECT-TYPE
    SYNTAX      IpAddress
    MAX-ACCESS  read-only
    STATUS      current
    DESCRIPTION   "IP Address assigned to PPP Termination Point on Far-End NE. Default
         is set by NE System on LINK establishment if FENDIPACPT = Y"
    ::=  { deployProvApsDefaultsEntry 10 }

deployProvApsDefaultsPeerAid OBJECT-TYPE
    SYNTAX      EntityIndex
    MAX-ACCESS  read-only
    STATUS      current
    DESCRIPTION
        "AID of Protection Partner involved in the protection group." 
    ::=  { deployProvApsDefaultsEntry 11 }

deployProvApsDefaultsApsType OBJECT-TYPE
    SYNTAX      ApsType
    MAX-ACCESS  read-only
    STATUS      current
    DESCRIPTION   "The type of APS implemented in this protection group."
    ::=  { deployProvApsDefaultsEntry 12 }

deployProvApsDefaultsRevertMode OBJECT-TYPE
    SYNTAX      ApsRevertMode
    MAX-ACCESS  read-only
    STATUS      current
    DESCRIPTION
        "Revertive Protection Switching" 
    ::=  { deployProvApsDefaultsEntry 13 }

deployProvApsDefaultsWaitToRestore OBJECT-TYPE
    SYNTAX      Unsigned32 (5..12 | 4294967295) 
    UNITS       "min"
    MAX-ACCESS  read-only
    STATUS      current
    DESCRIPTION
        "Wait to Restore Timer value" 
    ::=  { deployProvApsDefaultsEntry 14 }

deployProvApsDefaultsDirection OBJECT-TYPE
    SYNTAX      ApsDirection
    MAX-ACCESS  read-only
    STATUS      current
    DESCRIPTION   "Indicates whether the APS function is 'unidirectional' (single-ended)
         or 'bidirectional' (dual-ended)."
    ::=  { deployProvApsDefaultsEntry 15 }

deployProvApsWorkingAidCapsTable OBJECT-TYPE
    SYNTAX      SEQUENCE OF DeployProvApsWorkingAidCapsEntry
    MAX-ACCESS  not-accessible
    STATUS      current
    DESCRIPTION   ""
    ::=  { facilityDeployProv 10 }

deployProvApsWorkingAidCapsEntry OBJECT-TYPE
    SYNTAX      DeployProvApsWorkingAidCapsEntry
    MAX-ACCESS  not-accessible
    STATUS      current
    DESCRIPTION   ""
    INDEX       {
                  entityIndex,
                  deployProvApsWorkingAidCapsIndex
                }
    ::=  { deployProvApsWorkingAidCapsTable 1 }

DeployProvApsWorkingAidCapsEntry ::=  SEQUENCE
  { deployProvApsWorkingAidCapsIndex EntityIndex }

deployProvApsWorkingAidCapsIndex OBJECT-TYPE
    SYNTAX      EntityIndex
    MAX-ACCESS  read-only
    STATUS      current
    DESCRIPTION
        "AID of working port involved in the protection group." 
    ::=  { deployProvApsWorkingAidCapsEntry 1 }

deployProvApsProtectingAidCapsTable OBJECT-TYPE
    SYNTAX      SEQUENCE OF DeployProvApsProtectingAidCapsEntry
    MAX-ACCESS  not-accessible
    STATUS      current
    DESCRIPTION   ""
    ::=  { facilityDeployProv 11 }

deployProvApsProtectingAidCapsEntry OBJECT-TYPE
    SYNTAX      DeployProvApsProtectingAidCapsEntry
    MAX-ACCESS  not-accessible
    STATUS      current
    DESCRIPTION   ""
    INDEX       {
                  entityIndex,
                  deployProvApsProtectingAidCapsIndex
                }
    ::=  { deployProvApsProtectingAidCapsTable 1 }

DeployProvApsProtectingAidCapsEntry ::=  SEQUENCE
  { deployProvApsProtectingAidCapsIndex EntityIndex }

deployProvApsProtectingAidCapsIndex OBJECT-TYPE
    SYNTAX      EntityIndex
    MAX-ACCESS  read-only
    STATUS      current
    DESCRIPTION
        "(Protection AID) AID of protection entity involved in the protection group." 
    ::=  { deployProvApsProtectingAidCapsEntry 1 }

deployProvDcnTable OBJECT-TYPE
    SYNTAX      SEQUENCE OF DeployProvDcnEntry
    MAX-ACCESS  not-accessible
    STATUS      current
    DESCRIPTION   "Contains entries for provisioning dcnChannel."
    ::=  { facilityDeployProv 12 }

deployProvDcnEntry OBJECT-TYPE
    SYNTAX      DeployProvDcnEntry
    MAX-ACCESS  not-accessible
    STATUS      current
    DESCRIPTION   "All dcnChannel which are provisioned(or are during provisioning)
         will have an entry in this table."
    INDEX       {
                  entityIndex
                }
    ::=  { deployProvDcnTable 1 }

DeployProvDcnEntry ::=  SEQUENCE
  { deployProvDcnRowStatus RowStatus,
    deployProvDcnForceDestroy FspR7ForcedStatus,
    deployProvDcnType FspR7InterfaceType,
    deployProvDcnAdmin FspR7AdminState,
    deployProvDcnExternalVid Unsigned32,
    deployProvDcnLanAid EntityIndex }

deployProvDcnRowStatus OBJECT-TYPE
    SYNTAX      RowStatus
    MAX-ACCESS  read-write
    STATUS      current
    DESCRIPTION
        "RowStatus" 
    ::=  { deployProvDcnEntry 1 }

deployProvDcnForceDestroy OBJECT-TYPE
    SYNTAX      FspR7ForcedStatus
    MAX-ACCESS  read-write
    STATUS      current
    DESCRIPTION
        "Forced Destroy" 
    ::=  { deployProvDcnEntry 2 }

deployProvDcnType OBJECT-TYPE
    SYNTAX      FspR7InterfaceType
    MAX-ACCESS  read-write
    STATUS      current
    DESCRIPTION   "The TYPE defines the transport service type as wrapper
         with wrapper layer termination OR else as payload"
    ::=  { deployProvDcnEntry 3 }

deployProvDcnAdmin OBJECT-TYPE
    SYNTAX      FspR7AdminState
    MAX-ACCESS  read-write
    STATUS      current
    DESCRIPTION
        "Administrative State is displayed in the GUI and Craft. Transition to Unassigend requires the entity to be deleted." 
    ::=  { deployProvDcnEntry 4 }

deployProvDcnExternalVid OBJECT-TYPE
    SYNTAX      Unsigned32 (1..4095 | 4294967295)
    MAX-ACCESS  read-write
    STATUS      current
    DESCRIPTION
        "External VID" 
    ::=  { deployProvDcnEntry 5 }

deployProvDcnLanAid OBJECT-TYPE
    SYNTAX      EntityIndex
    MAX-ACCESS  read-write
    STATUS      current
    DESCRIPTION
        "AID of LAN" 
    ::=  { deployProvDcnEntry 6 }

deployProvDcnCapTable OBJECT-TYPE
    SYNTAX      SEQUENCE OF DeployProvDcnCapEntry
    MAX-ACCESS  not-accessible
    STATUS      current
    DESCRIPTION   "Contains entries for provisioning dcnChannel."
    ::=  { facilityDeployProv 13  }

deployProvDcnCapEntry OBJECT-TYPE
    SYNTAX      DeployProvDcnCapEntry
    MAX-ACCESS  not-accessible
    STATUS      current
    DESCRIPTION   "All dcnChannel which are provisioned(or are during provisioning)
         will have an entry in this table."
    INDEX       { entityIndex }
    ::=  { deployProvDcnCapTable 1 }

DeployProvDcnCapEntry ::=  SEQUENCE
  { deployProvDcnCapRowStatus FspR7RowStatusCaps,
    deployProvDcnCapForceDestroy FspR7ForcedStatusCaps,
    deployProvDcnCapType FspR7InterfaceTypeCaps,
    deployProvDcnCapAdmin FspR7AdminStateCaps,
    deployProvDcnCapExternalVid Unsigned32,
    deployProvDcnCapLanAid Integer32 }

deployProvDcnCapRowStatus OBJECT-TYPE
    SYNTAX      FspR7RowStatusCaps
    MAX-ACCESS  read-only
    STATUS      current
    DESCRIPTION
        "RowStatus" 
    ::=  { deployProvDcnCapEntry 1 }

deployProvDcnCapForceDestroy OBJECT-TYPE
    SYNTAX      FspR7ForcedStatusCaps
    MAX-ACCESS  read-only
    STATUS      current
    DESCRIPTION
        "Forced Destroy" 
    ::=  { deployProvDcnCapEntry 2 }

deployProvDcnCapType OBJECT-TYPE
    SYNTAX      FspR7InterfaceTypeCaps
    MAX-ACCESS  read-only
    STATUS      current
    DESCRIPTION   "The TYPE defines the transport service type as wrapper
         with wrapper layer termination OR else as payload"
    ::=  { deployProvDcnCapEntry 3 }

deployProvDcnCapAdmin OBJECT-TYPE
    SYNTAX      FspR7AdminStateCaps
    MAX-ACCESS  read-only
    STATUS      current
    DESCRIPTION
        "Administrative State is displayed in the GUI and Craft. Transition to Unassigend requires the entity to be deleted." 
    ::=  { deployProvDcnCapEntry 4 }

deployProvDcnCapExternalVid OBJECT-TYPE
    SYNTAX      Unsigned32
    MAX-ACCESS  read-only
    STATUS      current
    DESCRIPTION
        "External VID" 
    ::=  { deployProvDcnCapEntry 5 }

deployProvDcnCapLanAid OBJECT-TYPE
    SYNTAX      Integer32
    MAX-ACCESS  read-only
    STATUS      current
    DESCRIPTION
        "AID of LAN" 
    ::=  { deployProvDcnCapEntry 6 }

deployProvDcnDefaultsTable  OBJECT-TYPE
    SYNTAX      SEQUENCE OF DeployProvDcnDefaultsEntry
    MAX-ACCESS  not-accessible
    STATUS      current
    DESCRIPTION   "Contains entries for provisioning dcnChannel."
    ::=  { facilityDeployProv 14  }

deployProvDcnDefaultsEntry OBJECT-TYPE
    SYNTAX      DeployProvDcnDefaultsEntry
    MAX-ACCESS  not-accessible
    STATUS      current
    DESCRIPTION   "All dcnChannel which are provisioned(or are during provisioning)
         will have an entry in this table."
    INDEX       { entityIndex }
    ::=  { deployProvDcnDefaultsTable 1 }

DeployProvDcnDefaultsEntry ::=  SEQUENCE
  { deployProvDcnDefaultsRowStatus RowStatus,
    deployProvDcnDefaultsForceDestroy FspR7ForcedStatus,
    deployProvDcnDefaultsType FspR7InterfaceType,
    deployProvDcnDefaultsAdmin FspR7AdminState,
    deployProvDcnDefaultsExternalVid Unsigned32,
    deployProvDcnDefaultsLanAid EntityIndex }

deployProvDcnDefaultsRowStatus OBJECT-TYPE
    SYNTAX      RowStatus
    MAX-ACCESS  read-only
    STATUS      current
    DESCRIPTION
        "RowStatus" 
    ::=  { deployProvDcnDefaultsEntry 1 }

deployProvDcnDefaultsForceDestroy OBJECT-TYPE
    SYNTAX      FspR7ForcedStatus
    MAX-ACCESS  read-only
    STATUS      current
    DESCRIPTION
        "Forced Destroy" 
    ::=  { deployProvDcnDefaultsEntry 2 }

deployProvDcnDefaultsType OBJECT-TYPE
    SYNTAX      FspR7InterfaceType
    MAX-ACCESS  read-only
    STATUS      current
    DESCRIPTION   "The TYPE defines the transport service type as wrapper
         with wrapper layer termination OR else as payload"
    ::=  { deployProvDcnDefaultsEntry 3 }

deployProvDcnDefaultsAdmin OBJECT-TYPE
    SYNTAX      FspR7AdminState
    MAX-ACCESS  read-only
    STATUS      current
    DESCRIPTION
        "Administrative State is displayed in the GUI and Craft. Transition to Unassigend requires the entity to be deleted." 
    ::=  { deployProvDcnDefaultsEntry 4 }

deployProvDcnDefaultsExternalVid OBJECT-TYPE
    SYNTAX      Unsigned32 (1..4095 | 4294967295)
    MAX-ACCESS  read-only
    STATUS      current
    DESCRIPTION
        "External VID" 
    ::=  { deployProvDcnDefaultsEntry 5 }

deployProvDcnDefaultsLanAid OBJECT-TYPE
    SYNTAX      EntityIndex
    MAX-ACCESS  read-only
    STATUS      current
    DESCRIPTION
        "AID of LAN" 
    ::=  { deployProvDcnDefaultsEntry 6 }

deployProvPppIpTable OBJECT-TYPE
    SYNTAX      SEQUENCE OF DeployProvPppIpEntry
    MAX-ACCESS  not-accessible
    STATUS      current
    DESCRIPTION   "Contains entries for provisioning PppIp."
    ::=  { facilityDeployProv 15 }

deployProvPppIpEntry OBJECT-TYPE
    SYNTAX      DeployProvPppIpEntry
    MAX-ACCESS  not-accessible
    STATUS      current
    DESCRIPTION   "All PppIp which are provisioned(or are during provisioning) will
         have an entry in this table."
    INDEX       {
                  entityIndex
                }
    ::=  { deployProvPppIpTable 1 }

DeployProvPppIpEntry ::=  SEQUENCE
  { deployProvPppIpRowStatus RowStatus,
    deployProvPppIpForceDestroy FspR7ForcedStatus,
    deployProvPppIpType FspR7InterfaceType,
    deployProvPppIpNearEndIp IpAddress,
    deployProvPppIpFarEndIp IpAddress,
    deployProvPppIpBitrate Unsigned32,
    deployProvPppIpOspf FspR7OspfMode,
    deployProvPppIpMetric Unsigned32,
    deployProvPppIpDefaultGateway IpAddress,
    deployProvPppIpProxyArp FspR7NoYes,
    deployProvPppIpAdmin FspR7AdminState,
    deployProvPppIpAreaId IpAddress,
    deployProvPppIpBaud FspR7Baund,
    deployProvPppIpFlowControl FspR7FlowControlMode,
    deployProvPppIpIpType FspR7IpType,
    deployProvPppIpAuthType FspR7CpAuthType,
    deployProvPppIpAuthString SnmpAdminString }

deployProvPppIpRowStatus OBJECT-TYPE
    SYNTAX      RowStatus
    MAX-ACCESS  read-write
    STATUS      current
    DESCRIPTION
        "RowStatus" 
    ::=  { deployProvPppIpEntry 1 }

deployProvPppIpForceDestroy OBJECT-TYPE
    SYNTAX      FspR7ForcedStatus
    MAX-ACCESS  read-write
    STATUS      current
    DESCRIPTION
        "Forced Destroy" 
    ::=  { deployProvPppIpEntry 2 }

deployProvPppIpType OBJECT-TYPE
    SYNTAX      FspR7InterfaceType
    MAX-ACCESS  read-write
    STATUS      current
    DESCRIPTION   "The TYPE defines the transport service type as wrapper
         with wrapper layer termination OR else as payload"
    ::=  { deployProvPppIpEntry 3 }

deployProvPppIpNearEndIp OBJECT-TYPE
    SYNTAX      IpAddress
    MAX-ACCESS  read-write
    STATUS      current
    DESCRIPTION   "IP Address assigned to PPP Termination Point on Near-End NE.
         Defaults to System IP address"
    ::=  { deployProvPppIpEntry 4 }

deployProvPppIpFarEndIp OBJECT-TYPE
    SYNTAX      IpAddress
    MAX-ACCESS  read-write
    STATUS      current
    DESCRIPTION   "IP Address assigned to PPP Termination Point on Far-End NE. Default
         is set by NE System on LINK establishment if FENDIPACPT = Y"
    ::=  { deployProvPppIpEntry 5 }

deployProvPppIpBitrate OBJECT-TYPE
    SYNTAX      Unsigned32 (1..13702 | 4294967295) 
    UNITS       "kbps"
    MAX-ACCESS  read-write
    STATUS      current
    DESCRIPTION
        "Maximum provisioned bit rate for PPP/IP Link of transmitter for an ECC" 
    ::=  { deployProvPppIpEntry 6 }

deployProvPppIpOspf OBJECT-TYPE
    SYNTAX      FspR7OspfMode
    MAX-ACCESS  read-write
    STATUS      current
    DESCRIPTION
        "OSPF Routing (Dynamic)" 
    ::=  { deployProvPppIpEntry 7 }

deployProvPppIpMetric OBJECT-TYPE
    SYNTAX      Unsigned32 (0..65535 | 4294967295)
    MAX-ACCESS  read-write
    STATUS      current
    DESCRIPTION
        "Routing Metric" 
    ::=  { deployProvPppIpEntry 8 }

deployProvPppIpDefaultGateway OBJECT-TYPE
    SYNTAX      IpAddress
    MAX-ACCESS  read-write
    STATUS      deprecated
    DESCRIPTION   "If Y then a default router entry with thid PPPIP as gateway
         will be set in the routing table if no default router is present
         yet. It can be enabled on multiple PPPIP instances. But this
         were an unlogical configuration."
    ::=  { deployProvPppIpEntry 9 }

deployProvPppIpProxyArp OBJECT-TYPE
    SYNTAX      FspR7NoYes
    MAX-ACCESS  read-write
    STATUS      current
    DESCRIPTION   "If enabled then ARP requests for FENDIP (coming in on another
         interface in the same subnet as FENDIP) will be replied too."
    ::=  { deployProvPppIpEntry 10 }

deployProvPppIpAdmin OBJECT-TYPE
    SYNTAX      FspR7AdminState
    MAX-ACCESS  read-write
    STATUS      current
    DESCRIPTION
        "Administrative State is displayed in the GUI and Craft. Transition to Unassigend requires the entity to be deleted." 
    ::=  { deployProvPppIpEntry 11 }

deployProvPppIpAreaId OBJECT-TYPE
    SYNTAX      IpAddress
    MAX-ACCESS  read-write
    STATUS      current
    DESCRIPTION
        "OSPF Area ID for IP Interface" 
    ::=  { deployProvPppIpEntry 12 }

deployProvPppIpBaud OBJECT-TYPE
    SYNTAX      FspR7Baund
    MAX-ACCESS  read-write
    STATUS      current
    DESCRIPTION
        "Baud rate of the serial interface" 
    ::=  { deployProvPppIpEntry 13 }

deployProvPppIpFlowControl OBJECT-TYPE
    SYNTAX      FspR7FlowControlMode
    MAX-ACCESS  read-write
    STATUS      current
    DESCRIPTION
        "Flow Control mechanism" 
    ::=  { deployProvPppIpEntry 14 }

deployProvPppIpIpType OBJECT-TYPE
    SYNTAX      FspR7IpType
    MAX-ACCESS  read-write
    STATUS      current
    DESCRIPTION
        "Type of IP configuration" 
    ::=  { deployProvPppIpEntry 15 }

deployProvPppIpAuthType OBJECT-TYPE
    SYNTAX      FspR7CpAuthType
    MAX-ACCESS  read-write
    STATUS      current
    DESCRIPTION
        "OSPF Authentication Type" 
    ::=  { deployProvPppIpEntry 16 }

deployProvPppIpAuthString OBJECT-TYPE
    SYNTAX      SnmpAdminString
    MAX-ACCESS  read-write
    STATUS      current
    DESCRIPTION
        "OSPF Authentication Key/String depending on Authentication Type" 
    ::=  { deployProvPppIpEntry 17 }

deployProvPppIpCapTable OBJECT-TYPE
    SYNTAX      SEQUENCE OF DeployProvPppIpCapEntry
    MAX-ACCESS  not-accessible
    STATUS      current
    DESCRIPTION   "Contains entries for provisioning PppIp."
    ::=  { facilityDeployProv 16  }

deployProvPppIpCapEntry OBJECT-TYPE
    SYNTAX      DeployProvPppIpCapEntry
    MAX-ACCESS  not-accessible
    STATUS      current
    DESCRIPTION   "All PppIp which are provisioned(or are during provisioning) will
         have an entry in this table."
    INDEX       { entityIndex }
    ::=  { deployProvPppIpCapTable 1 }

DeployProvPppIpCapEntry ::=  SEQUENCE
  { deployProvPppIpCapRowStatus FspR7RowStatusCaps,
    deployProvPppIpCapForceDestroy FspR7ForcedStatusCaps,
    deployProvPppIpCapType FspR7InterfaceTypeCaps,
    deployProvPppIpCapNearEndIp FspR7YesNo,
    deployProvPppIpCapFarEndIp FspR7YesNo,
    deployProvPppIpCapBitrate FspR7Unsigned32Caps,
    deployProvPppIpCapOspf FspR7OspfModeCaps,
    deployProvPppIpCapMetric FspR7Unsigned32Caps,
    deployProvPppIpCapDefaultGateway FspR7YesNo,
    deployProvPppIpCapProxyArp FspR7NoYesCaps,
    deployProvPppIpCapAdmin FspR7AdminStateCaps,
    deployProvPppIpCapAreaId FspR7YesNo,
    deployProvPppIpCapBaud FspR7BaundCaps,
    deployProvPppIpCapFlowControl FspR7FlowControlModeCaps,
    deployProvPppIpCapIpType FspR7IpTypeCaps,
    deployProvPppIpCapAuthType FspR7CpAuthTypeCaps,
    deployProvPppIpCapAuthString Integer32 }

deployProvPppIpCapRowStatus OBJECT-TYPE
    SYNTAX      FspR7RowStatusCaps
    MAX-ACCESS  read-only
    STATUS      current
    DESCRIPTION
        "RowStatus" 
    ::=  { deployProvPppIpCapEntry 1 }

deployProvPppIpCapForceDestroy OBJECT-TYPE
    SYNTAX      FspR7ForcedStatusCaps
    MAX-ACCESS  read-only
    STATUS      current
    DESCRIPTION
        "Forced Destroy" 
    ::=  { deployProvPppIpCapEntry 2 }

deployProvPppIpCapType OBJECT-TYPE
    SYNTAX      FspR7InterfaceTypeCaps
    MAX-ACCESS  read-only
    STATUS      current
    DESCRIPTION   "The TYPE defines the transport service type as wrapper
         with wrapper layer termination OR else as payload"
    ::=  { deployProvPppIpCapEntry 3 }

deployProvPppIpCapNearEndIp OBJECT-TYPE
    SYNTAX      FspR7YesNo
    MAX-ACCESS  read-only
    STATUS      current
    DESCRIPTION   "IP Address assigned to PPP Termination Point on Near-End NE.
         Defaults to System IP address"
    ::=  { deployProvPppIpCapEntry 4 }

deployProvPppIpCapFarEndIp OBJECT-TYPE
    SYNTAX      FspR7YesNo
    MAX-ACCESS  read-only
    STATUS      current
    DESCRIPTION   "IP Address assigned to PPP Termination Point on Far-End NE. Default
         is set by NE System on LINK establishment if FENDIPACPT = Y"
    ::=  { deployProvPppIpCapEntry 5 }

deployProvPppIpCapBitrate OBJECT-TYPE
    SYNTAX      FspR7Unsigned32Caps
    UNITS       "kbps"
    MAX-ACCESS  read-only
    STATUS      current
    DESCRIPTION
        "Maximum provisioned bit rate for PPP/IP Link of transmitter for an ECC" 
    ::=  { deployProvPppIpCapEntry 6 }

deployProvPppIpCapOspf OBJECT-TYPE
    SYNTAX      FspR7OspfModeCaps
    MAX-ACCESS  read-only
    STATUS      current
    DESCRIPTION
        "OSPF Routing (Dynamic)" 
    ::=  { deployProvPppIpCapEntry 7 }

deployProvPppIpCapMetric OBJECT-TYPE
    SYNTAX      FspR7Unsigned32Caps
    MAX-ACCESS  read-only
    STATUS      current
    DESCRIPTION
        "Routing Metric" 
    ::=  { deployProvPppIpCapEntry 8 }

deployProvPppIpCapDefaultGateway OBJECT-TYPE
    SYNTAX      FspR7YesNo
    MAX-ACCESS  read-only
    STATUS      deprecated
    DESCRIPTION   "If Y then a default router entry with thid PPPIP as gateway
         will be set in the routing table if no default router is present
         yet. It can be enabled on multiple PPPIP instances. But this
         were an unlogical configuration."
    ::=  { deployProvPppIpCapEntry 9 }

deployProvPppIpCapProxyArp OBJECT-TYPE
    SYNTAX      FspR7NoYesCaps
    MAX-ACCESS  read-only
    STATUS      current
    DESCRIPTION   "If enabled then ARP requests for FENDIP (coming in on another
         interface in the same subnet as FENDIP) will be replied too."
    ::=  { deployProvPppIpCapEntry 10 }

deployProvPppIpCapAdmin OBJECT-TYPE
    SYNTAX      FspR7AdminStateCaps
    MAX-ACCESS  read-only
    STATUS      current
    DESCRIPTION
        "Administrative State is displayed in the GUI and Craft. Transition to Unassigend requires the entity to be deleted." 
    ::=  { deployProvPppIpCapEntry 11 }

deployProvPppIpCapAreaId OBJECT-TYPE
    SYNTAX      FspR7YesNo
    MAX-ACCESS  read-only
    STATUS      current
    DESCRIPTION
        "OSPF Area ID for IP Interface" 
    ::=  { deployProvPppIpCapEntry 12 }

deployProvPppIpCapBaud OBJECT-TYPE
    SYNTAX      FspR7BaundCaps
    MAX-ACCESS  read-only
    STATUS      current
    DESCRIPTION
        "Baud rate of the serial interface" 
    ::=  { deployProvPppIpCapEntry 13 }

deployProvPppIpCapFlowControl OBJECT-TYPE
    SYNTAX      FspR7FlowControlModeCaps
    MAX-ACCESS  read-only
    STATUS      current
    DESCRIPTION
        "Flow Control mechanism" 
    ::=  { deployProvPppIpCapEntry 14 }

deployProvPppIpCapIpType OBJECT-TYPE
    SYNTAX      FspR7IpTypeCaps
    MAX-ACCESS  read-only
    STATUS      current
    DESCRIPTION
        "Type of IP configuration" 
    ::=  { deployProvPppIpCapEntry 15 }

deployProvPppIpCapAuthType OBJECT-TYPE
    SYNTAX      FspR7CpAuthTypeCaps
    MAX-ACCESS  read-only
    STATUS      current
    DESCRIPTION
        "OSPF Authentication Type" 
    ::=  { deployProvPppIpCapEntry 16 }

deployProvPppIpCapAuthString OBJECT-TYPE
    SYNTAX      Integer32
    MAX-ACCESS  read-only
    STATUS      current
    DESCRIPTION
        "OSPF Authentication Key/String depending on Authentication Type" 
    ::=  { deployProvPppIpCapEntry 17 }

deployProvPppIpDefaultsTable  OBJECT-TYPE
    SYNTAX      SEQUENCE OF DeployProvPppIpDefaultsEntry
    MAX-ACCESS  not-accessible
    STATUS      current
    DESCRIPTION   "Contains entries for provisioning PppIp."
    ::=  { facilityDeployProv 17  }

deployProvPppIpDefaultsEntry OBJECT-TYPE
    SYNTAX      DeployProvPppIpDefaultsEntry
    MAX-ACCESS  not-accessible
    STATUS      current
    DESCRIPTION   "All PppIp which are provisioned(or are during provisioning) will
         have an entry in this table."
    INDEX       { entityIndex }
    ::=  { deployProvPppIpDefaultsTable 1 }

DeployProvPppIpDefaultsEntry ::=  SEQUENCE
  { deployProvPppIpDefaultsRowStatus RowStatus,
    deployProvPppIpDefaultsForceDestroy FspR7ForcedStatus,
    deployProvPppIpDefaultsType FspR7InterfaceType,
    deployProvPppIpDefaultsNearEndIp IpAddress,
    deployProvPppIpDefaultsFarEndIp IpAddress,
    deployProvPppIpDefaultsBitrate Unsigned32,
    deployProvPppIpDefaultsOspf FspR7OspfMode,
    deployProvPppIpDefaultsMetric Unsigned32,
    deployProvPppIpDefaultsDefaultGateway IpAddress,
    deployProvPppIpDefaultsProxyArp FspR7NoYes,
    deployProvPppIpDefaultsAdmin FspR7AdminState,
    deployProvPppIpDefaultsAreaId IpAddress,
    deployProvPppIpDefaultsBaud FspR7Baund,
    deployProvPppIpDefaultsFlowControl FspR7FlowControlMode,
    deployProvPppIpDefaultsIpType FspR7IpType,
    deployProvPppIpDefaultsAuthType FspR7CpAuthType,
    deployProvPppIpDefaultsAuthString SnmpAdminString }

deployProvPppIpDefaultsRowStatus OBJECT-TYPE
    SYNTAX      RowStatus
    MAX-ACCESS  read-only
    STATUS      current
    DESCRIPTION
        "RowStatus" 
    ::=  { deployProvPppIpDefaultsEntry 1 }

deployProvPppIpDefaultsForceDestroy OBJECT-TYPE
    SYNTAX      FspR7ForcedStatus
    MAX-ACCESS  read-only
    STATUS      current
    DESCRIPTION
        "Forced Destroy" 
    ::=  { deployProvPppIpDefaultsEntry 2 }

deployProvPppIpDefaultsType OBJECT-TYPE
    SYNTAX      FspR7InterfaceType
    MAX-ACCESS  read-only
    STATUS      current
    DESCRIPTION   "The TYPE defines the transport service type as wrapper
         with wrapper layer termination OR else as payload"
    ::=  { deployProvPppIpDefaultsEntry 3 }

deployProvPppIpDefaultsNearEndIp OBJECT-TYPE
    SYNTAX      IpAddress
    MAX-ACCESS  read-only
    STATUS      current
    DESCRIPTION   "IP Address assigned to PPP Termination Point on Near-End NE.
         Defaults to System IP address"
    ::=  { deployProvPppIpDefaultsEntry 4 }

deployProvPppIpDefaultsFarEndIp OBJECT-TYPE
    SYNTAX      IpAddress
    MAX-ACCESS  read-only
    STATUS      current
    DESCRIPTION   "IP Address assigned to PPP Termination Point on Far-End NE. Default
         is set by NE System on LINK establishment if FENDIPACPT = Y"
    ::=  { deployProvPppIpDefaultsEntry 5 }

deployProvPppIpDefaultsBitrate OBJECT-TYPE
    SYNTAX      Unsigned32 (1..13702 | 4294967295) 
    UNITS       "kbps"
    MAX-ACCESS  read-only
    STATUS      current
    DESCRIPTION
        "Maximum provisioned bit rate for PPP/IP Link of transmitter for an ECC" 
    ::=  { deployProvPppIpDefaultsEntry 6 }

deployProvPppIpDefaultsOspf OBJECT-TYPE
    SYNTAX      FspR7OspfMode
    MAX-ACCESS  read-only
    STATUS      current
    DESCRIPTION
        "OSPF Routing (Dynamic)" 
    ::=  { deployProvPppIpDefaultsEntry 7 }

deployProvPppIpDefaultsMetric OBJECT-TYPE
    SYNTAX      Unsigned32 (0..65535 | 4294967295)
    MAX-ACCESS  read-only
    STATUS      current
    DESCRIPTION
        "Routing Metric" 
    ::=  { deployProvPppIpDefaultsEntry 8 }

deployProvPppIpDefaultsDefaultGateway OBJECT-TYPE
    SYNTAX      IpAddress
    MAX-ACCESS  read-only
    STATUS      deprecated
    DESCRIPTION   "If Y then a default router entry with thid PPPIP as gateway
         will be set in the routing table if no default router is present
         yet. It can be enabled on multiple PPPIP instances. But this
         were an unlogical configuration."
    ::=  { deployProvPppIpDefaultsEntry 9 }

deployProvPppIpDefaultsProxyArp OBJECT-TYPE
    SYNTAX      FspR7NoYes
    MAX-ACCESS  read-only
    STATUS      current
    DESCRIPTION   "If enabled then ARP requests for FENDIP (coming in on another
         interface in the same subnet as FENDIP) will be replied too."
    ::=  { deployProvPppIpDefaultsEntry 10 }

deployProvPppIpDefaultsAdmin OBJECT-TYPE
    SYNTAX      FspR7AdminState
    MAX-ACCESS  read-only
    STATUS      current
    DESCRIPTION
        "Administrative State is displayed in the GUI and Craft. Transition to Unassigend requires the entity to be deleted." 
    ::=  { deployProvPppIpDefaultsEntry 11 }

deployProvPppIpDefaultsAreaId OBJECT-TYPE
    SYNTAX      IpAddress
    MAX-ACCESS  read-only
    STATUS      current
    DESCRIPTION
        "OSPF Area ID for IP Interface" 
    ::=  { deployProvPppIpDefaultsEntry 12 }

deployProvPppIpDefaultsBaud OBJECT-TYPE
    SYNTAX      FspR7Baund
    MAX-ACCESS  read-only
    STATUS      current
    DESCRIPTION
        "Baud rate of the serial interface" 
    ::=  { deployProvPppIpDefaultsEntry 13 }

deployProvPppIpDefaultsFlowControl OBJECT-TYPE
    SYNTAX      FspR7FlowControlMode
    MAX-ACCESS  read-only
    STATUS      current
    DESCRIPTION
        "Flow Control mechanism" 
    ::=  { deployProvPppIpDefaultsEntry 14 }

deployProvPppIpDefaultsIpType OBJECT-TYPE
    SYNTAX      FspR7IpType
    MAX-ACCESS  read-only
    STATUS      current
    DESCRIPTION
        "Type of IP configuration" 
    ::=  { deployProvPppIpDefaultsEntry 15 }

deployProvPppIpDefaultsAuthType OBJECT-TYPE
    SYNTAX      FspR7CpAuthType
    MAX-ACCESS  read-only
    STATUS      current
    DESCRIPTION
        "OSPF Authentication Type" 
    ::=  { deployProvPppIpDefaultsEntry 16 }

deployProvPppIpDefaultsAuthString OBJECT-TYPE
    SYNTAX      SnmpAdminString
    MAX-ACCESS  read-only
    STATUS      current
    DESCRIPTION
        "OSPF Authentication Key/String depending on Authentication Type" 
    ::=  { deployProvPppIpDefaultsEntry 17 }

deployProvCrsDcnTable OBJECT-TYPE
    SYNTAX      SEQUENCE OF DeployProvCrsDcnEntry
    MAX-ACCESS  not-accessible
    STATUS      current
    DESCRIPTION   "Contains entries for provisioning CrsDcn."
    ::=  { facilityDeployProv 18 }

deployProvCrsDcnEntry OBJECT-TYPE
    SYNTAX      DeployProvCrsDcnEntry
    MAX-ACCESS  not-accessible
    STATUS      current
    DESCRIPTION   "All CrsDcn which are provisioned(or are during provisioning)
         will have an entry in this table."
    INDEX       {
                  entityIndex
                }
    ::=  { deployProvCrsDcnTable 1 }

DeployProvCrsDcnEntry ::=  SEQUENCE
  { deployProvCrsDcnRowStatus RowStatus,
    deployProvCrsDcnForceDestroy FspR7ForcedStatus,
    deployProvCrsDcnType FspR7TypeConnection,
    deployProvCrsDcnLink EntityIndex,
    deployProvCrsDcnEcc EntityIndex }

deployProvCrsDcnRowStatus OBJECT-TYPE
    SYNTAX      RowStatus
    MAX-ACCESS  read-write
    STATUS      current
    DESCRIPTION
        "RowStatus" 
    ::=  { deployProvCrsDcnEntry 1 }

deployProvCrsDcnForceDestroy OBJECT-TYPE
    SYNTAX      FspR7ForcedStatus
    MAX-ACCESS  read-write
    STATUS      current
    DESCRIPTION
        "Forced Destroy" 
    ::=  { deployProvCrsDcnEntry 2 }

deployProvCrsDcnType OBJECT-TYPE
    SYNTAX      FspR7TypeConnection
    MAX-ACCESS  read-write
    STATUS      current
    DESCRIPTION
        "Type of Cross-Connect" 
    ::=  { deployProvCrsDcnEntry 3 }

deployProvCrsDcnLink OBJECT-TYPE
    SYNTAX      EntityIndex
    MAX-ACCESS  read-write
    STATUS      current
    DESCRIPTION
        "Address Identifier of PPPIP LINK Entity." 
    ::=  { deployProvCrsDcnEntry 4 }

deployProvCrsDcnEcc OBJECT-TYPE
    SYNTAX      EntityIndex
    MAX-ACCESS  read-write
    STATUS      current
    DESCRIPTION
        "Address Identifier of ECC Entity." 
    ::=  { deployProvCrsDcnEntry 5 }

deployProvCrsDcnCapTable OBJECT-TYPE
    SYNTAX      SEQUENCE OF DeployProvCrsDcnCapEntry
    MAX-ACCESS  not-accessible
    STATUS      current
    DESCRIPTION   "Contains entries for provisioning CrsDcn."
    ::=  { facilityDeployProv 19  }

deployProvCrsDcnCapEntry OBJECT-TYPE
    SYNTAX      DeployProvCrsDcnCapEntry
    MAX-ACCESS  not-accessible
    STATUS      current
    DESCRIPTION   "All CrsDcn which are provisioned(or are during provisioning)
         will have an entry in this table."
    INDEX       { entityIndex }
    ::=  { deployProvCrsDcnCapTable 1 }

DeployProvCrsDcnCapEntry ::=  SEQUENCE
  { deployProvCrsDcnCapRowStatus FspR7RowStatusCaps,
    deployProvCrsDcnCapForceDestroy FspR7ForcedStatusCaps,
    deployProvCrsDcnCapType FspR7TypeConnectionCaps,
    deployProvCrsDcnCapLink Integer32,
    deployProvCrsDcnCapEcc Integer32 }

deployProvCrsDcnCapRowStatus OBJECT-TYPE
    SYNTAX      FspR7RowStatusCaps
    MAX-ACCESS  read-only
    STATUS      current
    DESCRIPTION
        "RowStatus" 
    ::=  { deployProvCrsDcnCapEntry 1 }

deployProvCrsDcnCapForceDestroy OBJECT-TYPE
    SYNTAX      FspR7ForcedStatusCaps
    MAX-ACCESS  read-only
    STATUS      current
    DESCRIPTION
        "Forced Destroy" 
    ::=  { deployProvCrsDcnCapEntry 2 }

deployProvCrsDcnCapType OBJECT-TYPE
    SYNTAX      FspR7TypeConnectionCaps
    MAX-ACCESS  read-only
    STATUS      current
    DESCRIPTION
        "Type of Cross-Connect" 
    ::=  { deployProvCrsDcnCapEntry 3 }

deployProvCrsDcnCapLink OBJECT-TYPE
    SYNTAX      Integer32
    MAX-ACCESS  read-only
    STATUS      current
    DESCRIPTION
        "Address Identifier of PPPIP LINK Entity." 
    ::=  { deployProvCrsDcnCapEntry 4 }

deployProvCrsDcnCapEcc OBJECT-TYPE
    SYNTAX      Integer32
    MAX-ACCESS  read-only
    STATUS      current
    DESCRIPTION
        "Address Identifier of ECC Entity." 
    ::=  { deployProvCrsDcnCapEntry 5 }

deployProvCrsDcnDefaultsTable  OBJECT-TYPE
    SYNTAX      SEQUENCE OF DeployProvCrsDcnDefaultsEntry
    MAX-ACCESS  not-accessible
    STATUS      current
    DESCRIPTION   "Contains entries for provisioning CrsDcn."
    ::=  { facilityDeployProv 20  }

deployProvCrsDcnDefaultsEntry OBJECT-TYPE
    SYNTAX      DeployProvCrsDcnDefaultsEntry
    MAX-ACCESS  not-accessible
    STATUS      current
    DESCRIPTION   "All CrsDcn which are provisioned(or are during provisioning)
         will have an entry in this table."
    INDEX       { entityIndex }
    ::=  { deployProvCrsDcnDefaultsTable 1 }

DeployProvCrsDcnDefaultsEntry ::=  SEQUENCE
  { deployProvCrsDcnDefaultsRowStatus RowStatus,
    deployProvCrsDcnDefaultsForceDestroy FspR7ForcedStatus,
    deployProvCrsDcnDefaultsType FspR7TypeConnection,
    deployProvCrsDcnDefaultsLink EntityIndex,
    deployProvCrsDcnDefaultsEcc EntityIndex }

deployProvCrsDcnDefaultsRowStatus OBJECT-TYPE
    SYNTAX      RowStatus
    MAX-ACCESS  read-only
    STATUS      current
    DESCRIPTION
        "RowStatus" 
    ::=  { deployProvCrsDcnDefaultsEntry 1 }

deployProvCrsDcnDefaultsForceDestroy OBJECT-TYPE
    SYNTAX      FspR7ForcedStatus
    MAX-ACCESS  read-only
    STATUS      current
    DESCRIPTION
        "Forced Destroy" 
    ::=  { deployProvCrsDcnDefaultsEntry 2 }

deployProvCrsDcnDefaultsType OBJECT-TYPE
    SYNTAX      FspR7TypeConnection
    MAX-ACCESS  read-only
    STATUS      current
    DESCRIPTION
        "Type of Cross-Connect" 
    ::=  { deployProvCrsDcnDefaultsEntry 3 }

deployProvCrsDcnDefaultsLink OBJECT-TYPE
    SYNTAX      EntityIndex
    MAX-ACCESS  read-only
    STATUS      current
    DESCRIPTION
        "Address Identifier of PPPIP LINK Entity." 
    ::=  { deployProvCrsDcnDefaultsEntry 4 }

deployProvCrsDcnDefaultsEcc OBJECT-TYPE
    SYNTAX      EntityIndex
    MAX-ACCESS  read-only
    STATUS      current
    DESCRIPTION
        "Address Identifier of ECC Entity." 
    ::=  { deployProvCrsDcnDefaultsEntry 5 }

deployProvCrsDcnLinkAidCapsTable OBJECT-TYPE
    SYNTAX      SEQUENCE OF DeployProvCrsDcnLinkAidCapsEntry
    MAX-ACCESS  not-accessible
    STATUS      current
    DESCRIPTION   ""
    ::=  { facilityDeployProv 21 }

deployProvCrsDcnLinkAidCapsEntry OBJECT-TYPE
    SYNTAX      DeployProvCrsDcnLinkAidCapsEntry
    MAX-ACCESS  not-accessible
    STATUS      current
    DESCRIPTION   ""
    INDEX       {
                  entityIndex,
                  deployProvCrsDcnLinkAidCapsIndex
                }
    ::=  { deployProvCrsDcnLinkAidCapsTable 1 }

DeployProvCrsDcnLinkAidCapsEntry ::=  SEQUENCE
  { deployProvCrsDcnLinkAidCapsIndex EntityIndex }

deployProvCrsDcnLinkAidCapsIndex OBJECT-TYPE
    SYNTAX      EntityIndex
    MAX-ACCESS  read-only
    STATUS      current
    DESCRIPTION
        "Address Identifier of PPPIP LINK Entity." 
    ::=  { deployProvCrsDcnLinkAidCapsEntry 1 }

deployProvCrsDcnEccAidCapsTable OBJECT-TYPE
    SYNTAX      SEQUENCE OF DeployProvCrsDcnEccAidCapsEntry
    MAX-ACCESS  not-accessible
    STATUS      current
    DESCRIPTION   ""
    ::=  { facilityDeployProv 22 }

deployProvCrsDcnEccAidCapsEntry OBJECT-TYPE
    SYNTAX      DeployProvCrsDcnEccAidCapsEntry
    MAX-ACCESS  not-accessible
    STATUS      current
    DESCRIPTION   ""
    INDEX       {
                  entityIndex,
                  deployProvCrsDcnLinkAidCapsIndex
                }
    ::=  { deployProvCrsDcnEccAidCapsTable 1 }

DeployProvCrsDcnEccAidCapsEntry ::=  SEQUENCE
  { deployProvCrsDcnEccAidCapsIndex EntityIndex }

deployProvCrsDcnEccAidCapsIndex OBJECT-TYPE
    SYNTAX      EntityIndex
    MAX-ACCESS  read-only
    STATUS      current
    DESCRIPTION
        "Address Identifier of ECC Entity." 
    ::=  { deployProvCrsDcnEccAidCapsEntry 1 }

deployProvApsPeerAidCapsTable OBJECT-TYPE
    SYNTAX      SEQUENCE OF DeployProvApsPeerAidCapsEntry
    MAX-ACCESS  not-accessible
    STATUS      current
    DESCRIPTION   ""
    ::=  { facilityDeployProv 23 }

deployProvApsPeerAidCapsEntry OBJECT-TYPE
    SYNTAX      DeployProvApsPeerAidCapsEntry
    MAX-ACCESS  not-accessible
    STATUS      current
    DESCRIPTION   ""
    INDEX       {
                  entityIndex,
                  deployProvApsWorkingAidCapsIndex
                }
    ::=  { deployProvApsPeerAidCapsTable 1 }

DeployProvApsPeerAidCapsEntry ::=  SEQUENCE
  { deployProvApsPeerAidCapsIndex EntityIndex }

deployProvApsPeerAidCapsIndex OBJECT-TYPE
    SYNTAX      EntityIndex
    MAX-ACCESS  read-only
    STATUS      current
    DESCRIPTION
        "AID of Protection Partner involved in the protection group." 
    ::=  { deployProvApsPeerAidCapsEntry 1 }

deployProvLanTable OBJECT-TYPE
    SYNTAX      SEQUENCE OF DeployProvLanEntry
    MAX-ACCESS  not-accessible
    STATUS      current
    DESCRIPTION   "Contains entries for provisioning LANIp."
    ::=  { facilityDeployProv 24 }

deployProvLanEntry OBJECT-TYPE
    SYNTAX      DeployProvLanEntry
    MAX-ACCESS  not-accessible
    STATUS      current
    DESCRIPTION   "All LANIp which are provisioned(or are during provisioning) will
         have an entry in this table."
    INDEX       {
                  entityIndex
                }
    ::=  { deployProvLanTable 1 }

DeployProvLanEntry ::=  SEQUENCE
  { deployProvLanRowStatus RowStatus,
    deployProvLanForceDestroy FspR7ForcedStatus,
    deployProvLanType FspR7InterfaceType,
    deployProvLanOspf FspR7OspfMode,
    deployProvLanMetric Unsigned32,
    deployProvLanAdmin FspR7AdminState,
    deployProvLanAreaId IpAddress,
    deployProvLanIpType FspR7IpType,
    deployProvLanIpAddr IpAddress,
    deployProvLanIpMask IpAddress,
    deployProvLanPrio Unsigned32,
    deployProvLanAuthType FspR7CpAuthType,
    deployProvLanAuthString SnmpAdminString }

deployProvLanRowStatus OBJECT-TYPE
    SYNTAX      RowStatus
    MAX-ACCESS  read-write
    STATUS      current
    DESCRIPTION
        "RowStatus" 
    ::=  { deployProvLanEntry 1 }

deployProvLanForceDestroy OBJECT-TYPE
    SYNTAX      FspR7ForcedStatus
    MAX-ACCESS  read-write
    STATUS      current
    DESCRIPTION
        "Forced Destroy" 
    ::=  { deployProvLanEntry 2 }

deployProvLanType OBJECT-TYPE
    SYNTAX      FspR7InterfaceType
    MAX-ACCESS  read-write
    STATUS      current
    DESCRIPTION
        "The TYPE defines the transport service type as wrapper with wrapper layer termination OR else as payload" 
    ::=  { deployProvLanEntry 3 }

deployProvLanOspf OBJECT-TYPE
    SYNTAX      FspR7OspfMode
    MAX-ACCESS  read-write
    STATUS      current
    DESCRIPTION
        "OSPF Routing (Dynamic)" 
    ::=  { deployProvLanEntry 4 }

deployProvLanMetric OBJECT-TYPE
    SYNTAX      Unsigned32 (0..65535 | 4294967295)
    MAX-ACCESS  read-write
    STATUS      current
    DESCRIPTION
        "Routing Metric" 
    ::=  { deployProvLanEntry 5 }

deployProvLanAdmin OBJECT-TYPE
    SYNTAX      FspR7AdminState
    MAX-ACCESS  read-write
    STATUS      current
    DESCRIPTION
        "Administrative State is displayed in the GUI and Craft. Transition to Unassigend requires the entity to be deleted." 
    ::=  { deployProvLanEntry 6 }

deployProvLanAreaId OBJECT-TYPE
    SYNTAX      IpAddress
    MAX-ACCESS  read-write
    STATUS      current
    DESCRIPTION
        "OSPF Area ID for IP Interface" 
    ::=  { deployProvLanEntry 7 }

deployProvLanIpType OBJECT-TYPE
    SYNTAX      FspR7IpType
    MAX-ACCESS  read-write
    STATUS      current
    DESCRIPTION
        "Type of IP configuration" 
    ::=  { deployProvLanEntry 8 }

deployProvLanIpAddr OBJECT-TYPE
    SYNTAX      IpAddress
    MAX-ACCESS  read-write
    STATUS      current
    DESCRIPTION
        "IP Address assigned to LAN IP Interface" 
    ::=  { deployProvLanEntry 9 }

deployProvLanIpMask OBJECT-TYPE
    SYNTAX      IpAddress
    MAX-ACCESS  read-write
    STATUS      current
    DESCRIPTION
        "IP MASK assigned to LAN IP Interface" 
    ::=  { deployProvLanEntry 10 }

deployProvLanPrio OBJECT-TYPE
    SYNTAX      Unsigned32 (0..255 | 4294967295)
    MAX-ACCESS  read-write
    STATUS      current
    DESCRIPTION
        "Priority" 
    ::=  { deployProvLanEntry 11 }

deployProvLanAuthType OBJECT-TYPE
    SYNTAX      FspR7CpAuthType
    MAX-ACCESS  read-write
    STATUS      current
    DESCRIPTION
        "OSPF Authentication Type" 
    ::=  { deployProvLanEntry 12 }

deployProvLanAuthString OBJECT-TYPE
    SYNTAX      SnmpAdminString
    MAX-ACCESS  read-write
    STATUS      current
    DESCRIPTION
        "OSPF Authentication Key/String depending on Authentication Type" 
    ::=  { deployProvLanEntry 13 }

deployProvLanCapTable OBJECT-TYPE
    SYNTAX      SEQUENCE OF DeployProvLanCapEntry
    MAX-ACCESS  not-accessible
    STATUS      current
    DESCRIPTION   "Contains entries for provisioning LANIp."
    ::=  { facilityDeployProv 25  }

deployProvLanCapEntry OBJECT-TYPE
    SYNTAX      DeployProvLanCapEntry
    MAX-ACCESS  not-accessible
    STATUS      current
    DESCRIPTION   "All LANIp which are provisioned(or are during provisioning) will
         have an entry in this table."
    INDEX       { entityIndex }
    ::=  { deployProvLanCapTable 1 }

DeployProvLanCapEntry ::=  SEQUENCE
  { deployProvLanCapRowStatus FspR7RowStatusCaps,
    deployProvLanCapForceDestroy FspR7ForcedStatusCaps,
    deployProvLanCapType FspR7InterfaceTypeCaps,
    deployProvLanCapOspf FspR7OspfModeCaps,
    deployProvLanCapMetric FspR7Unsigned32Caps,
    deployProvLanCapAdmin FspR7AdminStateCaps,
    deployProvLanCapAreaId FspR7YesNo,
    deployProvLanCapIpType FspR7IpTypeCaps,
    deployProvLanCapIpAddr FspR7YesNo,
    deployProvLanCapIpMask FspR7YesNo,
    deployProvLanCapPrio FspR7Unsigned32Caps,
    deployProvLanCapAuthType FspR7CpAuthTypeCaps,
    deployProvLanCapAuthString Integer32 }

deployProvLanCapRowStatus OBJECT-TYPE
    SYNTAX      FspR7RowStatusCaps
    MAX-ACCESS  read-only
    STATUS      current
    DESCRIPTION
        "RowStatus" 
    ::=  { deployProvLanCapEntry 1 }

deployProvLanCapForceDestroy OBJECT-TYPE
    SYNTAX      FspR7ForcedStatusCaps
    MAX-ACCESS  read-only
    STATUS      current
    DESCRIPTION
        "Forced Destroy" 
    ::=  { deployProvLanCapEntry 2 }

deployProvLanCapType OBJECT-TYPE
    SYNTAX      FspR7InterfaceTypeCaps
    MAX-ACCESS  read-only
    STATUS      current
    DESCRIPTION
        "The TYPE defines the transport service type as wrapper with wrapper layer termination OR else as payload" 
    ::=  { deployProvLanCapEntry 3 }

deployProvLanCapOspf OBJECT-TYPE
    SYNTAX      FspR7OspfModeCaps
    MAX-ACCESS  read-only
    STATUS      current
    DESCRIPTION
        "OSPF Routing (Dynamic)" 
    ::=  { deployProvLanCapEntry 4 }

deployProvLanCapMetric OBJECT-TYPE
    SYNTAX      FspR7Unsigned32Caps
    MAX-ACCESS  read-only
    STATUS      current
    DESCRIPTION
        "Routing Metric" 
    ::=  { deployProvLanCapEntry 5 }

deployProvLanCapAdmin OBJECT-TYPE
    SYNTAX      FspR7AdminStateCaps
    MAX-ACCESS  read-only
    STATUS      current
    DESCRIPTION
        "Administrative State is displayed in the GUI and Craft. Transition to Unassigend requires the entity to be deleted." 
    ::=  { deployProvLanCapEntry 6 }

deployProvLanCapAreaId OBJECT-TYPE
    SYNTAX      FspR7YesNo
    MAX-ACCESS  read-only
    STATUS      current
    DESCRIPTION
        "OSPF Area ID for IP Interface" 
    ::=  { deployProvLanCapEntry 7 }

deployProvLanCapIpType OBJECT-TYPE
    SYNTAX      FspR7IpTypeCaps
    MAX-ACCESS  read-only
    STATUS      current
    DESCRIPTION
        "Type of IP configuration" 
    ::=  { deployProvLanCapEntry 8 }

deployProvLanCapIpAddr OBJECT-TYPE
    SYNTAX      FspR7YesNo
    MAX-ACCESS  read-only
    STATUS      current
    DESCRIPTION
        "IP Address assigned to LAN IP Interface" 
    ::=  { deployProvLanCapEntry 9 }

deployProvLanCapIpMask OBJECT-TYPE
    SYNTAX      FspR7YesNo
    MAX-ACCESS  read-only
    STATUS      current
    DESCRIPTION
        "IP MASK assigned to LAN IP Interface" 
    ::=  { deployProvLanCapEntry 10 }

deployProvLanCapPrio OBJECT-TYPE
    SYNTAX      FspR7Unsigned32Caps
    MAX-ACCESS  read-only
    STATUS      current
    DESCRIPTION
        "Priority" 
    ::=  { deployProvLanCapEntry 11 }

deployProvLanCapAuthType OBJECT-TYPE
    SYNTAX      FspR7CpAuthTypeCaps
    MAX-ACCESS  read-only
    STATUS      current
    DESCRIPTION
        "OSPF Authentication Type" 
    ::=  { deployProvLanCapEntry 12 }

deployProvLanCapAuthString OBJECT-TYPE
    SYNTAX      Integer32
    MAX-ACCESS  read-only
    STATUS      current
    DESCRIPTION
        "OSPF Authentication Key/String depending on Authentication Type" 
    ::=  { deployProvLanCapEntry 13 }

deployProvLanDefaultsTable  OBJECT-TYPE
    SYNTAX      SEQUENCE OF DeployProvLanDefaultsEntry
    MAX-ACCESS  not-accessible
    STATUS      current
    DESCRIPTION   "Contains entries for provisioning LANIp."
    ::=  { facilityDeployProv 26  }

deployProvLanDefaultsEntry OBJECT-TYPE
    SYNTAX      DeployProvLanDefaultsEntry
    MAX-ACCESS  not-accessible
    STATUS      current
    DESCRIPTION   "All LANIp which are provisioned(or are during provisioning) will
         have an entry in this table."
    INDEX       { entityIndex }
    ::=  { deployProvLanDefaultsTable 1 }

DeployProvLanDefaultsEntry ::=  SEQUENCE
  { deployProvLanDefaultsRowStatus RowStatus,
    deployProvLanDefaultsForceDestroy FspR7ForcedStatus,
    deployProvLanDefaultsType FspR7InterfaceType,
    deployProvLanDefaultsOspf FspR7OspfMode,
    deployProvLanDefaultsMetric Unsigned32,
    deployProvLanDefaultsAdmin FspR7AdminState,
    deployProvLanDefaultsAreaId IpAddress,
    deployProvLanDefaultsIpType FspR7IpType,
    deployProvLanDefaultsIpAddr IpAddress,
    deployProvLanDefaultsIpMask IpAddress,
    deployProvLanDefaultsPrio Unsigned32,
    deployProvLanDefaultsAuthType FspR7CpAuthType,
    deployProvLanDefaultsAuthString SnmpAdminString }

deployProvLanDefaultsRowStatus OBJECT-TYPE
    SYNTAX      RowStatus
    MAX-ACCESS  read-only
    STATUS      current
    DESCRIPTION
        "RowStatus" 
    ::=  { deployProvLanDefaultsEntry 1 }

deployProvLanDefaultsForceDestroy OBJECT-TYPE
    SYNTAX      FspR7ForcedStatus
    MAX-ACCESS  read-only
    STATUS      current
    DESCRIPTION
        "Forced Destroy" 
    ::=  { deployProvLanDefaultsEntry 2 }

deployProvLanDefaultsType OBJECT-TYPE
    SYNTAX      FspR7InterfaceType
    MAX-ACCESS  read-only
    STATUS      current
    DESCRIPTION
        "The TYPE defines the transport service type as wrapper with wrapper layer termination OR else as payload" 
    ::=  { deployProvLanDefaultsEntry 3 }

deployProvLanDefaultsOspf OBJECT-TYPE
    SYNTAX      FspR7OspfMode
    MAX-ACCESS  read-only
    STATUS      current
    DESCRIPTION
        "OSPF Routing (Dynamic)" 
    ::=  { deployProvLanDefaultsEntry 4 }

deployProvLanDefaultsMetric OBJECT-TYPE
    SYNTAX      Unsigned32 (0..65535 | 4294967295)
    MAX-ACCESS  read-only
    STATUS      current
    DESCRIPTION
        "Routing Metric" 
    ::=  { deployProvLanDefaultsEntry 5 }

deployProvLanDefaultsAdmin OBJECT-TYPE
    SYNTAX      FspR7AdminState
    MAX-ACCESS  read-only
    STATUS      current
    DESCRIPTION
        "Administrative State is displayed in the GUI and Craft. Transition to Unassigend requires the entity to be deleted." 
    ::=  { deployProvLanDefaultsEntry 6 }

deployProvLanDefaultsAreaId OBJECT-TYPE
    SYNTAX      IpAddress
    MAX-ACCESS  read-only
    STATUS      current
    DESCRIPTION
        "OSPF Area ID for IP Interface" 
    ::=  { deployProvLanDefaultsEntry 7 }

deployProvLanDefaultsIpType OBJECT-TYPE
    SYNTAX      FspR7IpType
    MAX-ACCESS  read-only
    STATUS      current
    DESCRIPTION
        "Type of IP configuration" 
    ::=  { deployProvLanDefaultsEntry 8 }

deployProvLanDefaultsIpAddr OBJECT-TYPE
    SYNTAX      IpAddress
    MAX-ACCESS  read-only
    STATUS      current
    DESCRIPTION
        "IP Address assigned to LAN IP Interface" 
    ::=  { deployProvLanDefaultsEntry 9 }

deployProvLanDefaultsIpMask OBJECT-TYPE
    SYNTAX      IpAddress
    MAX-ACCESS  read-only
    STATUS      current
    DESCRIPTION
        "IP MASK assigned to LAN IP Interface" 
    ::=  { deployProvLanDefaultsEntry 10 }

deployProvLanDefaultsPrio OBJECT-TYPE
    SYNTAX      Unsigned32 (0..255 | 4294967295)
    MAX-ACCESS  read-only
    STATUS      current
    DESCRIPTION
        "Priority" 
    ::=  { deployProvLanDefaultsEntry 11 }

deployProvLanDefaultsAuthType OBJECT-TYPE
    SYNTAX      FspR7CpAuthType
    MAX-ACCESS  read-only
    STATUS      current
    DESCRIPTION
        "OSPF Authentication Type" 
    ::=  { deployProvLanDefaultsEntry 12 }

deployProvLanDefaultsAuthString OBJECT-TYPE
    SYNTAX      SnmpAdminString
    MAX-ACCESS  read-only
    STATUS      current
    DESCRIPTION
        "OSPF Authentication Key/String depending on Authentication Type" 
    ::=  { deployProvLanDefaultsEntry 13 }

deployProvModuleLanAidCapsTable OBJECT-TYPE
    SYNTAX      SEQUENCE OF DeployProvModuleLanAidCapsEntry
    MAX-ACCESS  not-accessible
    STATUS      current
    DESCRIPTION   ""
    ::=  { facilityDeployProv 27 }

deployProvModuleLanAidCapsEntry OBJECT-TYPE
    SYNTAX      DeployProvModuleLanAidCapsEntry
    MAX-ACCESS  not-accessible
    STATUS      current
    DESCRIPTION   ""
    INDEX       {
                  entityIndex,
                  deployProvModuleLanAidCapsIndex
                }
    ::=  { deployProvModuleLanAidCapsTable 1 }

DeployProvModuleLanAidCapsEntry ::=  SEQUENCE
  { deployProvModuleLanAidCapsIndex EntityIndex }

deployProvModuleLanAidCapsIndex OBJECT-TYPE
    SYNTAX      EntityIndex
    MAX-ACCESS  read-only
    STATUS      current
    DESCRIPTION
        "AID of LAN" 
    ::=  { deployProvModuleLanAidCapsEntry 1 }

deployProvTifInputTable OBJECT-TYPE
    SYNTAX      SEQUENCE OF DeployProvTifInputEntry
    MAX-ACCESS  not-accessible
    STATUS      current
    DESCRIPTION   "Contains entries for provisioning of TIF alarm."
    ::=  { facilityDeployProv 28 }

deployProvTifInputEntry OBJECT-TYPE
    SYNTAX      DeployProvTifInputEntry
    MAX-ACCESS  not-accessible
    STATUS      current
    DESCRIPTION   "All TIF alarms which are provisioned(or during deployProv)
         will have an entry in this table."
    INDEX       {
                  entityIndex
                }
    ::=  { deployProvTifInputTable 1 }

DeployProvTifInputEntry ::=  SEQUENCE
  { deployProvTifInputRowStatus RowStatus,
    deployProvTifInputForceDestroy FspR7ForcedStatus,
    deployProvTifInputType FspR7InterfaceType,
    deployProvTifInputTifAlarmType SnmpAdminString,
    deployProvTifInputTifAlarmMessage SnmpAdminString,
    deployProvTifInputInvertTifInputLogic FspR7InvertTelemetryInputLogic,
    deployProvTifInputAdmin FspR7AdminState }

deployProvTifInputRowStatus OBJECT-TYPE
    SYNTAX      RowStatus
    MAX-ACCESS  read-write
    STATUS      current
    DESCRIPTION   "RowStatus"
    ::=  { deployProvTifInputEntry 1 }

deployProvTifInputForceDestroy OBJECT-TYPE
    SYNTAX      FspR7ForcedStatus
    MAX-ACCESS  read-write
    STATUS      current
    DESCRIPTION
        "Forced Destroy" 
    ::=  { deployProvTifInputEntry 2 }

deployProvTifInputType OBJECT-TYPE
    SYNTAX      FspR7InterfaceType
    MAX-ACCESS  read-write
    STATUS      current
    DESCRIPTION
        "The TYPE defines the transport service type as wrapper with wrapper layer termination OR else as payload" 
    ::=  { deployProvTifInputEntry 3 }

deployProvTifInputTifAlarmType OBJECT-TYPE
    SYNTAX      SnmpAdminString
    MAX-ACCESS  read-write
    STATUS      current
    DESCRIPTION
        "Telemetry interface alarm type" 
    ::=  { deployProvTifInputEntry 4 }

deployProvTifInputTifAlarmMessage OBJECT-TYPE
    SYNTAX      SnmpAdminString
    MAX-ACCESS  read-write
    STATUS      current
    DESCRIPTION
        "Telemetry interface alarm message" 
    ::=  { deployProvTifInputEntry 5 }

deployProvTifInputInvertTifInputLogic OBJECT-TYPE
    SYNTAX      FspR7InvertTelemetryInputLogic
    MAX-ACCESS  read-write
    STATUS      current
    DESCRIPTION
        "Change telemetry interface input logic" 
    ::=  { deployProvTifInputEntry 6 }

deployProvTifInputAdmin OBJECT-TYPE
    SYNTAX      FspR7AdminState
    MAX-ACCESS  read-write
    STATUS      current
    DESCRIPTION   "The Adminstrative State."
    ::=  { deployProvTifInputEntry 7 }

deployProvTifInputCapTable OBJECT-TYPE
    SYNTAX      SEQUENCE OF DeployProvTifInputCapEntry
    MAX-ACCESS  not-accessible
    STATUS      current
    DESCRIPTION   "Contains entries for provisioning of TIF alarm."
    ::=  { facilityDeployProv 29  }

deployProvTifInputCapEntry OBJECT-TYPE
    SYNTAX      DeployProvTifInputCapEntry
    MAX-ACCESS  not-accessible
    STATUS      current
    DESCRIPTION   "All TIF alarms which are provisioned(or during deployProv)
         will have an entry in this table."
    INDEX       { entityIndex }
    ::=  { deployProvTifInputCapTable 1 }

DeployProvTifInputCapEntry ::=  SEQUENCE
  { deployProvTifInputCapRowStatus FspR7RowStatusCaps,
    deployProvTifInputCapForceDestroy FspR7ForcedStatusCaps,
    deployProvTifInputCapType FspR7InterfaceTypeCaps,
    deployProvTifInputCapTifAlarmType Integer32,
    deployProvTifInputCapTifAlarmMessage Integer32,
    deployProvTifInputCapInvertTifInputLogic FspR7InvertTelemetryInputLogicCaps,
    deployProvTifInputCapAdmin FspR7AdminStateCaps }

deployProvTifInputCapRowStatus OBJECT-TYPE
    SYNTAX      FspR7RowStatusCaps
    MAX-ACCESS  read-only
    STATUS      current
    DESCRIPTION   "RowStatus"
    ::=  { deployProvTifInputCapEntry 1 }

deployProvTifInputCapForceDestroy OBJECT-TYPE
    SYNTAX      FspR7ForcedStatusCaps
    MAX-ACCESS  read-only
    STATUS      current
    DESCRIPTION
        "Forced Destroy" 
    ::=  { deployProvTifInputCapEntry 2 }

deployProvTifInputCapType OBJECT-TYPE
    SYNTAX      FspR7InterfaceTypeCaps
    MAX-ACCESS  read-only
    STATUS      current
    DESCRIPTION
        "The TYPE defines the transport service type as wrapper with wrapper layer termination OR else as payload" 
    ::=  { deployProvTifInputCapEntry 3 }

deployProvTifInputCapTifAlarmType OBJECT-TYPE
    SYNTAX      Integer32
    MAX-ACCESS  read-only
    STATUS      current
    DESCRIPTION
        "Telemetry interface alarm type" 
    ::=  { deployProvTifInputCapEntry 4 }

deployProvTifInputCapTifAlarmMessage OBJECT-TYPE
    SYNTAX      Integer32
    MAX-ACCESS  read-only
    STATUS      current
    DESCRIPTION
        "Telemetry interface alarm message" 
    ::=  { deployProvTifInputCapEntry 5 }

deployProvTifInputCapInvertTifInputLogic OBJECT-TYPE
    SYNTAX      FspR7InvertTelemetryInputLogicCaps
    MAX-ACCESS  read-only
    STATUS      current
    DESCRIPTION
        "Change telemetry interface input logic" 
    ::=  { deployProvTifInputCapEntry 6 }

deployProvTifInputCapAdmin OBJECT-TYPE
    SYNTAX      FspR7AdminStateCaps
    MAX-ACCESS  read-only
    STATUS      current
    DESCRIPTION   "The Adminstrative State."
    ::=  { deployProvTifInputCapEntry 7 }

deployProvTifInputDefaultsTable  OBJECT-TYPE
    SYNTAX      SEQUENCE OF DeployProvTifInputDefaultsEntry
    MAX-ACCESS  not-accessible
    STATUS      current
    DESCRIPTION   "Contains entries for provisioning of TIF alarm."
    ::=  { facilityDeployProv 30  }

deployProvTifInputDefaultsEntry OBJECT-TYPE
    SYNTAX      DeployProvTifInputDefaultsEntry
    MAX-ACCESS  not-accessible
    STATUS      current
    DESCRIPTION   "All TIF alarms which are provisioned(or during deployProv)
         will have an entry in this table."
    INDEX       { entityIndex }
    ::=  { deployProvTifInputDefaultsTable 1 }

DeployProvTifInputDefaultsEntry ::=  SEQUENCE
  { deployProvTifInputDefaultsRowStatus RowStatus,
    deployProvTifInputDefaultsForceDestroy FspR7ForcedStatus,
    deployProvTifInputDefaultsType FspR7InterfaceType,
    deployProvTifInputDefaultsTifAlarmType SnmpAdminString,
    deployProvTifInputDefaultsTifAlarmMessage SnmpAdminString,
    deployProvTifInputDefaultsInvertTifInputLogic FspR7InvertTelemetryInputLogic,
    deployProvTifInputDefaultsAdmin FspR7AdminState }

deployProvTifInputDefaultsRowStatus OBJECT-TYPE
    SYNTAX      RowStatus
    MAX-ACCESS  read-only
    STATUS      current
    DESCRIPTION   "RowStatus"
    ::=  { deployProvTifInputDefaultsEntry 1 }

deployProvTifInputDefaultsForceDestroy OBJECT-TYPE
    SYNTAX      FspR7ForcedStatus
    MAX-ACCESS  read-only
    STATUS      current
    DESCRIPTION
        "Forced Destroy" 
    ::=  { deployProvTifInputDefaultsEntry 2 }

deployProvTifInputDefaultsType OBJECT-TYPE
    SYNTAX      FspR7InterfaceType
    MAX-ACCESS  read-only
    STATUS      current
    DESCRIPTION
        "The TYPE defines the transport service type as wrapper with wrapper layer termination OR else as payload" 
    ::=  { deployProvTifInputDefaultsEntry 3 }

deployProvTifInputDefaultsTifAlarmType OBJECT-TYPE
    SYNTAX      SnmpAdminString
    MAX-ACCESS  read-only
    STATUS      current
    DESCRIPTION
        "Telemetry interface alarm type" 
    ::=  { deployProvTifInputDefaultsEntry 4 }

deployProvTifInputDefaultsTifAlarmMessage OBJECT-TYPE
    SYNTAX      SnmpAdminString
    MAX-ACCESS  read-only
    STATUS      current
    DESCRIPTION
        "Telemetry interface alarm message" 
    ::=  { deployProvTifInputDefaultsEntry 5 }

deployProvTifInputDefaultsInvertTifInputLogic OBJECT-TYPE
    SYNTAX      FspR7InvertTelemetryInputLogic
    MAX-ACCESS  read-only
    STATUS      current
    DESCRIPTION
        "Change telemetry interface input logic" 
    ::=  { deployProvTifInputDefaultsEntry 6 }

deployProvTifInputDefaultsAdmin OBJECT-TYPE
    SYNTAX      FspR7AdminState
    MAX-ACCESS  read-only
    STATUS      current
    DESCRIPTION   "The Adminstrative State."
    ::=  { deployProvTifInputDefaultsEntry 7 }

deployProvTifOutputTable OBJECT-TYPE
    SYNTAX      SEQUENCE OF DeployProvTifOutputEntry
    MAX-ACCESS  not-accessible
    STATUS      current
    DESCRIPTION   "Contains entries for provisioning of TIF alarm."
    ::=  { facilityDeployProv 31 }

deployProvTifOutputEntry OBJECT-TYPE
    SYNTAX      DeployProvTifOutputEntry
    MAX-ACCESS  not-accessible
    STATUS      current
    DESCRIPTION   "All TIF alarms which are provisioned(or during deployProv)
         will have an entry in this table."
    INDEX       {
                  entityIndex
                }
    ::=  { deployProvTifOutputTable 1 }

DeployProvTifOutputEntry ::=  SEQUENCE
  { deployProvTifOutputRowStatus RowStatus,
    deployProvTifOutputForceDestroy FspR7ForcedStatus,
    deployProvTifOutputType FspR7InterfaceType,
    deployProvTifOutputTelemetry FspR7TelemetryOutput,
    deployProvTifOutputAdmin FspR7AdminState }

deployProvTifOutputRowStatus OBJECT-TYPE
    SYNTAX      RowStatus
    MAX-ACCESS  read-write
    STATUS      current
    DESCRIPTION   "RowStatus"
    ::=  { deployProvTifOutputEntry 1 }

deployProvTifOutputForceDestroy OBJECT-TYPE
    SYNTAX      FspR7ForcedStatus
    MAX-ACCESS  read-write
    STATUS      current
    DESCRIPTION
        "Forced Destroy" 
    ::=  { deployProvTifOutputEntry 2 }

deployProvTifOutputType OBJECT-TYPE
    SYNTAX      FspR7InterfaceType
    MAX-ACCESS  read-write
    STATUS      current
    DESCRIPTION
        "The TYPE defines the transport service type as wrapper with wrapper layer termination OR else as payload" 
    ::=  { deployProvTifOutputEntry 3 }

deployProvTifOutputTelemetry OBJECT-TYPE
    SYNTAX      FspR7TelemetryOutput
    MAX-ACCESS  read-write
    STATUS      current
    DESCRIPTION
        "Telemetry interface output provision" 
    ::=  { deployProvTifOutputEntry 4 }

deployProvTifOutputAdmin OBJECT-TYPE
    SYNTAX      FspR7AdminState
    MAX-ACCESS  read-write
    STATUS      current
    DESCRIPTION   "The Adminstrative State."
    ::=  { deployProvTifOutputEntry 5 }

deployProvTifOutputCapTable OBJECT-TYPE
    SYNTAX      SEQUENCE OF DeployProvTifOutputCapEntry
    MAX-ACCESS  not-accessible
    STATUS      current
    DESCRIPTION   "Contains entries for provisioning of TIF alarm."
    ::=  { facilityDeployProv 32  }

deployProvTifOutputCapEntry OBJECT-TYPE
    SYNTAX      DeployProvTifOutputCapEntry
    MAX-ACCESS  not-accessible
    STATUS      current
    DESCRIPTION   "All TIF alarms which are provisioned(or during deployProv)
         will have an entry in this table."
    INDEX       { entityIndex }
    ::=  { deployProvTifOutputCapTable 1 }

DeployProvTifOutputCapEntry ::=  SEQUENCE
  { deployProvTifOutputCapRowStatus FspR7RowStatusCaps,
    deployProvTifOutputCapForceDestroy FspR7ForcedStatusCaps,
    deployProvTifOutputCapType FspR7InterfaceTypeCaps,
    deployProvTifOutputCapTelemetry FspR7TelemetryOutputCaps,
    deployProvTifOutputCapAdmin FspR7AdminStateCaps }

deployProvTifOutputCapRowStatus OBJECT-TYPE
    SYNTAX      FspR7RowStatusCaps
    MAX-ACCESS  read-only
    STATUS      current
    DESCRIPTION   "RowStatus"
    ::=  { deployProvTifOutputCapEntry 1 }

deployProvTifOutputCapForceDestroy OBJECT-TYPE
    SYNTAX      FspR7ForcedStatusCaps
    MAX-ACCESS  read-only
    STATUS      current
    DESCRIPTION
        "Forced Destroy" 
    ::=  { deployProvTifOutputCapEntry 2 }

deployProvTifOutputCapType OBJECT-TYPE
    SYNTAX      FspR7InterfaceTypeCaps
    MAX-ACCESS  read-only
    STATUS      current
    DESCRIPTION
        "The TYPE defines the transport service type as wrapper with wrapper layer termination OR else as payload" 
    ::=  { deployProvTifOutputCapEntry 3 }

deployProvTifOutputCapTelemetry OBJECT-TYPE
    SYNTAX      FspR7TelemetryOutputCaps
    MAX-ACCESS  read-only
    STATUS      current
    DESCRIPTION
        "Telemetry interface output provision" 
    ::=  { deployProvTifOutputCapEntry 4 }

deployProvTifOutputCapAdmin OBJECT-TYPE
    SYNTAX      FspR7AdminStateCaps
    MAX-ACCESS  read-only
    STATUS      current
    DESCRIPTION   "The Adminstrative State."
    ::=  { deployProvTifOutputCapEntry 5 }

deployProvTifOutputDefaultsTable  OBJECT-TYPE
    SYNTAX      SEQUENCE OF DeployProvTifOutputDefaultsEntry
    MAX-ACCESS  not-accessible
    STATUS      current
    DESCRIPTION   "Contains entries for provisioning of TIF alarm."
    ::=  { facilityDeployProv 33  }

deployProvTifOutputDefaultsEntry OBJECT-TYPE
    SYNTAX      DeployProvTifOutputDefaultsEntry
    MAX-ACCESS  not-accessible
    STATUS      current
    DESCRIPTION   "All TIF alarms which are provisioned(or during deployProv)
         will have an entry in this table."
    INDEX       { entityIndex }
    ::=  { deployProvTifOutputDefaultsTable 1 }

DeployProvTifOutputDefaultsEntry ::=  SEQUENCE
  { deployProvTifOutputDefaultsRowStatus RowStatus,
    deployProvTifOutputDefaultsForceDestroy FspR7ForcedStatus,
    deployProvTifOutputDefaultsType FspR7InterfaceType,
    deployProvTifOutputDefaultsTelemetry FspR7TelemetryOutput,
    deployProvTifOutputDefaultsAdmin FspR7AdminState }

deployProvTifOutputDefaultsRowStatus OBJECT-TYPE
    SYNTAX      RowStatus
    MAX-ACCESS  read-only
    STATUS      current
    DESCRIPTION   "RowStatus"
    ::=  { deployProvTifOutputDefaultsEntry 1 }

deployProvTifOutputDefaultsForceDestroy OBJECT-TYPE
    SYNTAX      FspR7ForcedStatus
    MAX-ACCESS  read-only
    STATUS      current
    DESCRIPTION
        "Forced Destroy" 
    ::=  { deployProvTifOutputDefaultsEntry 2 }

deployProvTifOutputDefaultsType OBJECT-TYPE
    SYNTAX      FspR7InterfaceType
    MAX-ACCESS  read-only
    STATUS      current
    DESCRIPTION
        "The TYPE defines the transport service type as wrapper with wrapper layer termination OR else as payload" 
    ::=  { deployProvTifOutputDefaultsEntry 3 }

deployProvTifOutputDefaultsTelemetry OBJECT-TYPE
    SYNTAX      FspR7TelemetryOutput
    MAX-ACCESS  read-only
    STATUS      current
    DESCRIPTION
        "Telemetry interface output provision" 
    ::=  { deployProvTifOutputDefaultsEntry 4 }

deployProvTifOutputDefaultsAdmin OBJECT-TYPE
    SYNTAX      FspR7AdminState
    MAX-ACCESS  read-only
    STATUS      current
    DESCRIPTION   "The Adminstrative State."
    ::=  { deployProvTifOutputDefaultsEntry 5 }

changeServiceDeployProvIfTable OBJECT-TYPE
    SYNTAX      SEQUENCE OF ChangeServiceDeployProvIfEntry
    MAX-ACCESS  not-accessible
    STATUS      current
    DESCRIPTION   ""
    ::=  { facilityDeployProv 40 }

changeServiceDeployProvIfEntry OBJECT-TYPE
    SYNTAX      ChangeServiceDeployProvIfEntry
    MAX-ACCESS  not-accessible
    STATUS      current
    DESCRIPTION   ""
    INDEX       {
                  entityIndex
                }
    ::=  { changeServiceDeployProvIfTable 1 }

ChangeServiceDeployProvIfEntry ::=  SEQUENCE
  { changeServiceDeployProvIfRowStatus RowStatus,
    changeServiceDeployProvIfForceDestroy FspR7ForcedStatus,
    changeServiceDeployProvIfType FspR7InterfaceType,
    changeServiceDeployProvIfPayload OtnPayloadType,
    changeServiceDeployProvIfBehaviour FspR7PortBehaviour,
    changeServiceDeployProvIfTerminationLevel OhTerminationLevel,
    changeServiceDeployProvIfAlsMode FspR7AlsMode,
    changeServiceDeployProvIfErrorForwarding FspR7ErrorFwdMode,
    changeServiceDeployProvIfLaserOffDelayFunction EnableState,
    changeServiceDeployProvIfFecType FspR7FecType,
    changeServiceDeployProvIfTimingSource SonetTimingSource,
    changeServiceDeployProvIfTcmALevel OtnTcmLevel,
    changeServiceDeployProvIfTcmBLevel OtnTcmLevel,
    changeServiceDeployProvIfSigDegThresSonetLine FspR7BERThreshold,
    changeServiceDeployProvIfSigDegThresSdhMs Unsigned32,
    changeServiceDeployProvIfSignalDegradePeriod Unsigned32,
    changeServiceDeployProvIfAutonegotiation EnableState,
    changeServiceDeployProvIfBitrate FspR7Bitrate,
    changeServiceDeployProvIfDuplex EthDuplexMode,
    changeServiceDeployProvIfFlowControl FspR7FlowControlMode,
    changeServiceDeployProvIfOtnStuffing FspR7Stuff,
    changeServiceDeployProvIfSigDegThresOtu Integer32,
    changeServiceDeployProvIfSigDegPeriodOtu Unsigned32,
    changeServiceDeployProvIfSigDegThresOdu Integer32,
    changeServiceDeployProvIfSigDegPeriodOdu Unsigned32,
    changeServiceDeployProvIfSigDegThresOduTcmA Integer32,
    changeServiceDeployProvIfSigDegPeriodOduTcmA Unsigned32,
    changeServiceDeployProvIfSigDegThresOduTcmB Integer32,
    changeServiceDeployProvIfSigDegPeriodOduTcmB Unsigned32,
    changeServiceDeployProvIfTilt Integer32,
    changeServiceDeployProvIfGain FspR7Gain,
    changeServiceDeployProvIfAdmin FspR7AdminState,
    changeServiceDeployProvIfAttenuationGradient Unsigned32,
    changeServiceDeployProvIfSigDegThresReceiver Unsigned32,
    changeServiceDeployProvIfTcmCLevel OtnTcmLevel,
    changeServiceDeployProvIfSigDegThresOduTcmC Integer32,
    changeServiceDeployProvIfSigDegPeriodOduTcmC Unsigned32,
    changeServiceDeployProvIfDisparityCorrection EnableState,
    changeServiceDeployProvIfIpAddr IpAddress,
    changeServiceDeployProvIfIpMask IpAddress,
    changeServiceDeployProvIfOspf FspR7OspfMode,
    changeServiceDeployProvIfMetric Unsigned32,
    changeServiceDeployProvIfAreaId IpAddress,
    changeServiceDeployProvIfTraceFormSonetSection SonetTraceForm,
    changeServiceDeployProvIfTraceExpectedSonetSection OCTET STRING,
    changeServiceDeployProvIfTraceTransmitSonetSection OCTET STRING,
    changeServiceDeployProvIfTimModeSonetSection TimMode,
    changeServiceDeployProvIfTraceExpectedOtu OCTET STRING,
    changeServiceDeployProvIfTraceTransmitSapiOtu OCTET STRING,
    changeServiceDeployProvIfTraceTransmitDapiOtu OCTET STRING,
    changeServiceDeployProvIfTraceTransmitOpspOtu OCTET STRING,
    changeServiceDeployProvIfTimModeOtu TimMode,
    changeServiceDeployProvIfTraceExpectedOdu OCTET STRING,
    changeServiceDeployProvIfTraceTransmitSapiOdu OCTET STRING,
    changeServiceDeployProvIfTraceTransmitDapiOdu OCTET STRING,
    changeServiceDeployProvIfTraceTransmitOpspOdu OCTET STRING,
    changeServiceDeployProvIfTimModeOdu TimMode,
    changeServiceDeployProvIfTraceExpectedOduTcmA OCTET STRING,
    changeServiceDeployProvIfTraceTransmitSapiOduTcmA OCTET STRING,
    changeServiceDeployProvIfTraceTransmitDapiOduTcmA OCTET STRING,
    changeServiceDeployProvIfTraceTransmitOpspOduTcmA OCTET STRING,
    changeServiceDeployProvIfTimModeOduTcmA TimMode,
    changeServiceDeployProvIfTraceExpectedOduTcmB OCTET STRING,
    changeServiceDeployProvIfTraceTransmitSapiOduTcmB OCTET STRING,
    changeServiceDeployProvIfTraceTransmitDapiOduTcmB OCTET STRING,
    changeServiceDeployProvIfTraceTransmitOpspOduTcmB OCTET STRING,
    changeServiceDeployProvIfTimModeOduTcmB TimMode,
    changeServiceDeployProvIfTraceExpectedOduTcmC OCTET STRING,
    changeServiceDeployProvIfTraceTransmitSapiOduTcmC OCTET STRING,
    changeServiceDeployProvIfTraceTransmitDapiOduTcmC OCTET STRING,
    changeServiceDeployProvIfTraceTransmitOpspOduTcmC OCTET STRING,
    changeServiceDeployProvIfTimModeOduTcmC TimMode,
    changeServiceDeployProvIfChannelProvisioning FspR7ChannelIdentifier,
    changeServiceDeployProvIfVariableGain Unsigned32,
    changeServiceDeployProvIfBand FspR7OpticalBand,
    changeServiceDeployProvIfSigDegThreshold Unsigned32,
    changeServiceDeployProvIfSigDegPeriodIntegration Unsigned32,
    changeServiceDeployProvIfVoaMode FspR7VoaMode,
    changeServiceDeployProvIfOpticalSetPoint Integer32,
    changeServiceDeployProvIfVoaSetpoint Unsigned32,
    changeServiceDeployProvIfLanAid EntityIndex,
    changeServiceDeployProvIfAprHighThreshold Unsigned32,
    changeServiceDeployProvIfPumpPower Integer32,
    changeServiceDeployProvIfWdmRxChannel FspR7ChannelIdentifier,
    changeServiceDeployProvIfSigDegThresSonetSection FspR7BERThresholdSection,
    changeServiceDeployProvIfSigDegThresSdhSection Unsigned32,
    changeServiceDeployProvIfSigDegPeriodSdhSection Unsigned32,
    changeServiceDeployProvIfDispersionMode FspR7DispersionModes,
    changeServiceDeployProvIfDispersionSetting Integer32,
    changeServiceDeployProvIfIpType FspR7IpType,
    changeServiceDeployProvIfOffset Integer32,
    changeServiceDeployProvIfFunction FspR7InterfaceFunction,
    changeServiceDeployProvIfFarEndCommunication FspR7YesNo,
    changeServiceDeployProvIfEqlzAdmin FspR7EqlzAdminState,
    changeServiceDeployProvIfTxOffDelay FspR7EnableDisable,
    changeServiceDeployProvIfOpuPayloadType FspR7OpuPayloadType,
    changeServiceDeployProvIfOscOpticalSetpoint Integer32,
    changeServiceDeployProvIfFiberBrand FspR7FiberBrand,
    changeServiceDeployProvIfXfpDecisionThres FspR7XfpDecisionThres,
    changeServiceDeployProvIfLaserDelayTimer FspR7LaserDelayTimer,
    changeServiceDeployProvIfLaserOffTimer Unsigned32,
    changeServiceDeployProvIfLaserOnTimer Unsigned32,
    changeServiceDeployProvIfLaneChannelSetting FspR7ChannelIdentifier,
    changeServiceDeployProvIfBip FspR7Bip,
    changeServiceDeployProvIfCodeGain FspR7CodeGain }

changeServiceDeployProvIfRowStatus OBJECT-TYPE
    SYNTAX      RowStatus
    MAX-ACCESS  read-write
    STATUS      current
    DESCRIPTION   "RowStatus"
    ::=  { changeServiceDeployProvIfEntry 1 }

changeServiceDeployProvIfForceDestroy OBJECT-TYPE
    SYNTAX      FspR7ForcedStatus
    MAX-ACCESS  read-write
    STATUS      current
    DESCRIPTION
        "Forced Destroy" 
    ::=  { changeServiceDeployProvIfEntry 2 }

changeServiceDeployProvIfType OBJECT-TYPE
    SYNTAX      FspR7InterfaceType
    MAX-ACCESS  read-write
    STATUS      current
    DESCRIPTION   "The TYPE defines the transport service type as wrapper with wrapper layer
         termination OR else as payload"
    ::=  { changeServiceDeployProvIfEntry 3 }

changeServiceDeployProvIfPayload OBJECT-TYPE
    SYNTAX      OtnPayloadType
    MAX-ACCESS  read-write
    STATUS      current
    DESCRIPTION   "The payload of the interface (inside a transport overhead).
         Relevant e. g. for OTN cards which wrap a payload into an OTU1/2 wrapper."
    ::=  { changeServiceDeployProvIfEntry 4 }

changeServiceDeployProvIfBehaviour OBJECT-TYPE
    SYNTAX      FspR7PortBehaviour
    MAX-ACCESS  read-write
    STATUS      current
    DESCRIPTION   "The configured behaviour of the interface. If configured as
         a network interface, the interface will use a WDM laser."
    ::=  { changeServiceDeployProvIfEntry 5 }

changeServiceDeployProvIfTerminationLevel OBJECT-TYPE
    SYNTAX      OhTerminationLevel
    MAX-ACCESS  read-write
    STATUS      current
    DESCRIPTION
        "Highest signal level hardware removes then generates for transmission." 
    ::=  { changeServiceDeployProvIfEntry 6 }

changeServiceDeployProvIfAlsMode OBJECT-TYPE
    SYNTAX      FspR7AlsMode
    MAX-ACCESS  read-write
    STATUS      current
    DESCRIPTION   "A configuration request for the Automatic Laser Shutdown (ALS)
         function. Refer to FspR7AlsMode Textual Convention for details."
    ::=  { changeServiceDeployProvIfEntry 7 }

changeServiceDeployProvIfErrorForwarding OBJECT-TYPE
    SYNTAX      FspR7ErrorFwdMode
    MAX-ACCESS  read-write
    STATUS      current
    DESCRIPTION   "A configuration request for the error forwarding
         function. Refer to FspR7ErrorFwdMode Textual Convention for details."
    ::=  { changeServiceDeployProvIfEntry 8 }

changeServiceDeployProvIfLaserOffDelayFunction OBJECT-TYPE
    SYNTAX      EnableState
    MAX-ACCESS  read-write
    STATUS      current
    DESCRIPTION   "A configuration request for the Laser Off Delay function. This function
         delays turning off the laser as a consequent action to a defect."
    ::=  { changeServiceDeployProvIfEntry 9 }

changeServiceDeployProvIfFecType OBJECT-TYPE
    SYNTAX      FspR7FecType
    MAX-ACCESS  read-write
    STATUS      current
    DESCRIPTION   "Configuration of FEC type."
    ::=  { changeServiceDeployProvIfEntry 10 }

changeServiceDeployProvIfTimingSource OBJECT-TYPE
    SYNTAX      SonetTimingSource
    MAX-ACCESS  read-write
    STATUS      current
    DESCRIPTION   "The timing source for this interface.
         - internal: used in stand-alone, point-to-point topologies stand-alone (dedicated fiber operation).
         - loopTiming: e.g. used in point-to-point via SONET network and feeder topologies. The default is
         internal(1)."
    ::=  { changeServiceDeployProvIfEntry 11 }

changeServiceDeployProvIfTcmALevel OBJECT-TYPE
    SYNTAX      OtnTcmLevel
    MAX-ACCESS  read-write
    STATUS      current
    DESCRIPTION   "Configuration of TCMA level."
    ::=  { changeServiceDeployProvIfEntry 12 }

changeServiceDeployProvIfTcmBLevel OBJECT-TYPE
    SYNTAX      OtnTcmLevel
    MAX-ACCESS  read-write
    STATUS      current
    DESCRIPTION   "Configuration of TCMB level."
    ::=  { changeServiceDeployProvIfEntry 13 }

changeServiceDeployProvIfSigDegThresSonetLine OBJECT-TYPE
    SYNTAX      FspR7BERThreshold
    MAX-ACCESS  read-write
    STATUS      current
    DESCRIPTION
        "Bit-Error-Based Degradation Definition for SONET (standard integration period)" 
    ::=  { changeServiceDeployProvIfEntry 14 }

changeServiceDeployProvIfSigDegThresSdhMs OBJECT-TYPE
    SYNTAX      Unsigned32 (1..100 | 4294967295) 
    UNITS       "%"
    MAX-ACCESS  read-write
    STATUS      current
    DESCRIPTION
        "Block-Error-Based Degradation Definition for SDH (standard integration period).
         Defined as percentage Background Block Errors (30% default) evaluated
         over a defined period (SDPER-RS)." 
    ::=  { changeServiceDeployProvIfEntry 15 }

changeServiceDeployProvIfSignalDegradePeriod OBJECT-TYPE
    SYNTAX      Unsigned32 (2..10 | 4294967295) 
    UNITS       "s"
    MAX-ACCESS  read-write
    STATUS      current
    DESCRIPTION   "The measurement period in seconds used together with
         the deployProvIfSigDegThresSdhRegSect based on the block error counting method.
         The valid range is 2..10,
         The default being 7."
    ::=  { changeServiceDeployProvIfEntry 16 }

changeServiceDeployProvIfAutonegotiation OBJECT-TYPE
    SYNTAX      EnableState
    MAX-ACCESS  read-write
    STATUS      current
    DESCRIPTION
        "Auto Negotiation for the data rate" 
    ::=  { changeServiceDeployProvIfEntry 17 }

changeServiceDeployProvIfBitrate OBJECT-TYPE
    SYNTAX      FspR7Bitrate
    MAX-ACCESS  read-write
    STATUS      current
    DESCRIPTION
        "Provisioned data rate" 
    ::=  { changeServiceDeployProvIfEntry 18 }

changeServiceDeployProvIfDuplex OBJECT-TYPE
    SYNTAX      EthDuplexMode
    MAX-ACCESS  read-write
    STATUS      current
    DESCRIPTION
        "Duplex Mode (provision), available when Auto Negoiation is Disable (AUTONEG=DISABLE)" 
    ::=  { changeServiceDeployProvIfEntry 19 }

changeServiceDeployProvIfFlowControl OBJECT-TYPE
    SYNTAX      FspR7FlowControlMode
    MAX-ACCESS  read-write
    STATUS      current
    DESCRIPTION
        "Flow Control mechanism" 
    ::=  { changeServiceDeployProvIfEntry 20 }

changeServiceDeployProvIfOtnStuffing OBJECT-TYPE
    SYNTAX      FspR7Stuff
    MAX-ACCESS  read-write
    STATUS      current
    DESCRIPTION
        "Indicates if bit/byte stuffing is used in the transport signal." 
    ::=  { changeServiceDeployProvIfEntry 21 }

changeServiceDeployProvIfSigDegThresOtu OBJECT-TYPE
    SYNTAX      Integer32 (1..100 | -2147483648) 
    UNITS       "%"
    MAX-ACCESS  read-write
    STATUS      current
    DESCRIPTION
        "Background-Block-Error-Based Signal Degradation Definition for OTU" 
    ::=  { changeServiceDeployProvIfEntry 22 }

changeServiceDeployProvIfSigDegPeriodOtu OBJECT-TYPE
    SYNTAX      Unsigned32 (2..10 | 4294967295) 
    UNITS       "s"
    MAX-ACCESS  read-write
    STATUS      current
    DESCRIPTION
        "Integration Period for Signal degrade" 
    ::=  { changeServiceDeployProvIfEntry 23 }

changeServiceDeployProvIfSigDegThresOdu OBJECT-TYPE
    SYNTAX      Integer32 (1..100 | -2147483648) 
    UNITS       "%"
    MAX-ACCESS  read-write
    STATUS      current
    DESCRIPTION
        "Background-Block-Error-Based Signal Degradation Definition for ODU" 
    ::=  { changeServiceDeployProvIfEntry 24 }

changeServiceDeployProvIfSigDegPeriodOdu OBJECT-TYPE
    SYNTAX      Unsigned32 (2..10 | 4294967295) 
    UNITS       "s"
    MAX-ACCESS  read-write
    STATUS      current
    DESCRIPTION
        "Integration Period for Signal degrade" 
    ::=  { changeServiceDeployProvIfEntry 25 }

changeServiceDeployProvIfSigDegThresOduTcmA OBJECT-TYPE
    SYNTAX      Integer32 (1..100 | -2147483648) 
    UNITS       "%"
    MAX-ACCESS  read-write
    STATUS      current
    DESCRIPTION
        "Background-Block-Error-Based Signal Degradation Definition for TCM-A" 
    ::=  { changeServiceDeployProvIfEntry 26 }

changeServiceDeployProvIfSigDegPeriodOduTcmA OBJECT-TYPE
    SYNTAX      Unsigned32 (2..10 | 4294967295) 
    UNITS       "s"
    MAX-ACCESS  read-write
    STATUS      current
    DESCRIPTION
        "Integration Period for Signal degrade" 
    ::=  { changeServiceDeployProvIfEntry 27 }

changeServiceDeployProvIfSigDegThresOduTcmB OBJECT-TYPE
    SYNTAX      Integer32 (1..100 | -2147483648) 
    UNITS       "%"
    MAX-ACCESS  read-write
    STATUS      current
    DESCRIPTION
        "Background-Block-Error-Based Signal Degradation Definition for TCM-B" 
    ::=  { changeServiceDeployProvIfEntry 28 }

changeServiceDeployProvIfSigDegPeriodOduTcmB OBJECT-TYPE
    SYNTAX      Unsigned32 (2..10 | 4294967295) 
    UNITS       "s"
    MAX-ACCESS  read-write
    STATUS      current
    DESCRIPTION
        "Integration Period of TCMB Signal Segrade" 
    ::=  { changeServiceDeployProvIfEntry 29 }

changeServiceDeployProvIfTilt OBJECT-TYPE
    SYNTAX      Integer32 (-50..0 | -2147483648) 
    UNITS       "0.1 dB"
    MAX-ACCESS  read-write
    STATUS      current
    DESCRIPTION
        "Change of optical channel power in dB over the complete transmission band" 
    ::=  { changeServiceDeployProvIfEntry 30 }

changeServiceDeployProvIfGain OBJECT-TYPE
    SYNTAX      FspR7Gain
    MAX-ACCESS  read-write
    STATUS      current
    DESCRIPTION
        "Gain" 
    ::=  { changeServiceDeployProvIfEntry 31 }

changeServiceDeployProvIfAdmin OBJECT-TYPE
    SYNTAX      FspR7AdminState
    MAX-ACCESS  read-write
    STATUS      current
    DESCRIPTION   "The Adminstrative State."
    ::=  { changeServiceDeployProvIfEntry 32 }

changeServiceDeployProvIfAttenuationGradient OBJECT-TYPE
    SYNTAX      Unsigned32 (5..990 | 4294967295) 
    UNITS       "0.1 dB/min"
    MAX-ACCESS  read-write
    STATUS      current
    DESCRIPTION   "Attenuation Gradient Threshold on Receive Fiber. Applies to both
         TRMT and RCV directions; but threshold violation is reported for
         each direction separately by the 'tapping' alarms: INTRUDE-RCV
         and INTRUDE-TRMT."
    ::=  { changeServiceDeployProvIfEntry 33 }

changeServiceDeployProvIfSigDegThresReceiver OBJECT-TYPE
    SYNTAX      Unsigned32 
    UNITS       "0.1 dB"
    MAX-ACCESS  read-write
    STATUS      current
    DESCRIPTION
        "Signal Degrade Threshold on Receiver. Reported as ATTRMT-SDHT to far end." 
    ::=  { changeServiceDeployProvIfEntry 34 }

changeServiceDeployProvIfTcmCLevel OBJECT-TYPE
    SYNTAX      OtnTcmLevel
    MAX-ACCESS  read-write
    STATUS      current
    DESCRIPTION
        "Activation of Tandem Connection Monitoring Instance C" 
    ::=  { changeServiceDeployProvIfEntry 35 }

changeServiceDeployProvIfSigDegThresOduTcmC OBJECT-TYPE
    SYNTAX      Integer32 (1..100 | -2147483648) 
    UNITS       "%"
    MAX-ACCESS  read-write
    STATUS      current
    DESCRIPTION
        "Background-Block-Error-Based Signal Degradation Definition for TCM-C" 
    ::=  { changeServiceDeployProvIfEntry 36 }

changeServiceDeployProvIfSigDegPeriodOduTcmC OBJECT-TYPE
    SYNTAX      Unsigned32 (2..10 | 4294967295) 
    UNITS       "s"
    MAX-ACCESS  read-write
    STATUS      current
    DESCRIPTION
        "Integration Period of TCMC Signal Segrade" 
    ::=  { changeServiceDeployProvIfEntry 37 }

changeServiceDeployProvIfDisparityCorrection OBJECT-TYPE
    SYNTAX      EnableState
    MAX-ACCESS  read-write
    STATUS      current
    DESCRIPTION
        "Disparity correction" 
    ::=  { changeServiceDeployProvIfEntry 38 }

changeServiceDeployProvIfIpAddr OBJECT-TYPE
    SYNTAX      IpAddress
    MAX-ACCESS  read-write
    STATUS      current
    DESCRIPTION
        "IP Address assigned to LAN IP Interface" 
    ::=  { changeServiceDeployProvIfEntry 39 }

changeServiceDeployProvIfIpMask OBJECT-TYPE
    SYNTAX      IpAddress
    MAX-ACCESS  read-write
    STATUS      current
    DESCRIPTION
        "IP MASK assigned to LAN IP Interface" 
    ::=  { changeServiceDeployProvIfEntry 40 }

changeServiceDeployProvIfOspf OBJECT-TYPE
    SYNTAX      FspR7OspfMode
    MAX-ACCESS  read-write
    STATUS      current
    DESCRIPTION
        "OSPF Routing (Dynamic)" 
    ::=  { changeServiceDeployProvIfEntry 41 }

changeServiceDeployProvIfMetric OBJECT-TYPE
    SYNTAX      Unsigned32 (0..65535 | 4294967295)
    MAX-ACCESS  read-write
    STATUS      current
    DESCRIPTION
        "Routing Metric" 
    ::=  { changeServiceDeployProvIfEntry 42 }

changeServiceDeployProvIfAreaId OBJECT-TYPE
    SYNTAX      IpAddress
    MAX-ACCESS  read-write
    STATUS      current
    DESCRIPTION
        "OSPF Area ID for IP Interface" 
    ::=  { changeServiceDeployProvIfEntry 43 }

changeServiceDeployProvIfTraceFormSonetSection OBJECT-TYPE
    SYNTAX      SonetTraceForm
    MAX-ACCESS  read-write
    STATUS      current
    DESCRIPTION
        "Byte-Length of Trace Compared to Expected" 
    ::=  { changeServiceDeployProvIfEntry 44 }

changeServiceDeployProvIfTraceExpectedSonetSection OBJECT-TYPE
    SYNTAX      OCTET STRING (SIZE(0..62))
    MAX-ACCESS  read-write
    STATUS      current
    DESCRIPTION
        "Expected Sec/RS trace. NULL TRACE implies that no trace comparison is made." 
    ::=  { changeServiceDeployProvIfEntry 45 }

changeServiceDeployProvIfTraceTransmitSonetSection OBJECT-TYPE
    SYNTAX      OCTET STRING (SIZE(0..62))
    MAX-ACCESS  read-write
    STATUS      current
    DESCRIPTION
        "Sec/RS Trace to be Transmitted" 
    ::=  { changeServiceDeployProvIfEntry 46 }

changeServiceDeployProvIfTimModeSonetSection OBJECT-TYPE
    SYNTAX      TimMode
    MAX-ACCESS  read-write
    STATUS      current
    DESCRIPTION
        "SONET Section Trace Identifier Mismatch (TIM) detection/action for TIM defect." 
    ::=  { changeServiceDeployProvIfEntry 47 }

changeServiceDeployProvIfTraceExpectedOtu OBJECT-TYPE
    SYNTAX      OCTET STRING (SIZE(0..15))
    MAX-ACCESS  read-write
    STATUS      current
    DESCRIPTION   "Expected SAPI part of the OTU trace (15 character).
         NULL TRACE implies that no trace comparison is made."
    ::=  { changeServiceDeployProvIfEntry 48 }

changeServiceDeployProvIfTraceTransmitSapiOtu OBJECT-TYPE
    SYNTAX      OCTET STRING (SIZE(0..15))
    MAX-ACCESS  read-write
    STATUS      current
    DESCRIPTION
        "The transmitted SAPI part of the OTU trace (15 character)" 
    ::=  { changeServiceDeployProvIfEntry 49 }

changeServiceDeployProvIfTraceTransmitDapiOtu OBJECT-TYPE
    SYNTAX      OCTET STRING (SIZE(0..15))
    MAX-ACCESS  read-write
    STATUS      current
    DESCRIPTION
        "The transmitted DAPI part of the OTU trace (15 character)" 
    ::=  { changeServiceDeployProvIfEntry 50 }

changeServiceDeployProvIfTraceTransmitOpspOtu OBJECT-TYPE
    SYNTAX      OCTET STRING (SIZE(0..32))
    MAX-ACCESS  read-write
    STATUS      current
    DESCRIPTION
        "The transmitted Operator Specific part of the OTU trace (32 character)" 
    ::=  { changeServiceDeployProvIfEntry 51 }

changeServiceDeployProvIfTimModeOtu OBJECT-TYPE
    SYNTAX      TimMode
    MAX-ACCESS  read-write
    STATUS      current
    DESCRIPTION
        "OTU Trace Identifier Mismatch (TIM) detection/action for TIM defect." 
    ::=  { changeServiceDeployProvIfEntry 52 }

changeServiceDeployProvIfTraceExpectedOdu OBJECT-TYPE
    SYNTAX      OCTET STRING (SIZE(0..15))
    MAX-ACCESS  read-write
    STATUS      current
    DESCRIPTION   "Expected SAPI part of the ODU trace (15 character).
         NULL TRACE implies that no trace comparison is made."
    ::=  { changeServiceDeployProvIfEntry 53 }

changeServiceDeployProvIfTraceTransmitSapiOdu OBJECT-TYPE
    SYNTAX      OCTET STRING (SIZE(0..15))
    MAX-ACCESS  read-write
    STATUS      current
    DESCRIPTION
        "The transmitted SAPI part of the ODU trace (15 character)" 
    ::=  { changeServiceDeployProvIfEntry 54 }

changeServiceDeployProvIfTraceTransmitDapiOdu OBJECT-TYPE
    SYNTAX      OCTET STRING (SIZE(0..15))
    MAX-ACCESS  read-write
    STATUS      current
    DESCRIPTION
        "The transmitted DAPI part of the ODU trace (15 character)" 
    ::=  { changeServiceDeployProvIfEntry 55 }

changeServiceDeployProvIfTraceTransmitOpspOdu OBJECT-TYPE
    SYNTAX      OCTET STRING (SIZE(0..32))
    MAX-ACCESS  read-write
    STATUS      current
    DESCRIPTION
        "The transmitted Operator Specific part of the ODU trace (32 character)" 
    ::=  { changeServiceDeployProvIfEntry 56 }

changeServiceDeployProvIfTimModeOdu OBJECT-TYPE
    SYNTAX      TimMode
    MAX-ACCESS  read-write
    STATUS      current
    DESCRIPTION
        "Detection of TIM-ODU Condition can be configured" 
    ::=  { changeServiceDeployProvIfEntry 57 }

changeServiceDeployProvIfTraceExpectedOduTcmA OBJECT-TYPE
    SYNTAX      OCTET STRING (SIZE(0..15))
    MAX-ACCESS  read-write
    STATUS      current
    DESCRIPTION   "Expected SAPI part of the TCMA trace (15 character).
         NULL TRACE-TCM implies that no trace comparison is made."
    ::=  { changeServiceDeployProvIfEntry 58 }

changeServiceDeployProvIfTraceTransmitSapiOduTcmA OBJECT-TYPE
    SYNTAX      OCTET STRING (SIZE(0..15))
    MAX-ACCESS  read-write
    STATUS      current
    DESCRIPTION
        "The transmitted SAPI part of the TCMA trace (15 character)" 
    ::=  { changeServiceDeployProvIfEntry 59 }

changeServiceDeployProvIfTraceTransmitDapiOduTcmA OBJECT-TYPE
    SYNTAX      OCTET STRING (SIZE(0..15))
    MAX-ACCESS  read-write
    STATUS      current
    DESCRIPTION
        "The transmitted DAPI part of the TCMA trace (15 character)" 
    ::=  { changeServiceDeployProvIfEntry 60 }

changeServiceDeployProvIfTraceTransmitOpspOduTcmA OBJECT-TYPE
    SYNTAX      OCTET STRING (SIZE(0..32))
    MAX-ACCESS  read-write
    STATUS      current
    DESCRIPTION
        "The transmitted Operator Specific part of the TCMA trace (32 character)" 
    ::=  { changeServiceDeployProvIfEntry 61 }

changeServiceDeployProvIfTimModeOduTcmA OBJECT-TYPE
    SYNTAX      TimMode
    MAX-ACCESS  read-write
    STATUS      current
    DESCRIPTION
        "TCM_A Trace Identifier Mismatch (TIM) detection/action for TIM defect." 
    ::=  { changeServiceDeployProvIfEntry 62 }

changeServiceDeployProvIfTraceExpectedOduTcmB OBJECT-TYPE
    SYNTAX      OCTET STRING (SIZE(0..15))
    MAX-ACCESS  read-write
    STATUS      current
    DESCRIPTION
        "Expected SAPI part of the TCMB trace (15 character). NULL TRACE-TCM implies that no trace comparison is made." 
    ::=  { changeServiceDeployProvIfEntry 63 }

changeServiceDeployProvIfTraceTransmitSapiOduTcmB OBJECT-TYPE
    SYNTAX      OCTET STRING (SIZE(0..15))
    MAX-ACCESS  read-write
    STATUS      current
    DESCRIPTION
        "The transmitted SAPI part of the TCMB trace (15 character)" 
    ::=  { changeServiceDeployProvIfEntry 64 }

changeServiceDeployProvIfTraceTransmitDapiOduTcmB OBJECT-TYPE
    SYNTAX      OCTET STRING (SIZE(0..15))
    MAX-ACCESS  read-write
    STATUS      current
    DESCRIPTION
        "The transmitted DAPI part of the TCMB trace (15 character)" 
    ::=  { changeServiceDeployProvIfEntry 65 }

changeServiceDeployProvIfTraceTransmitOpspOduTcmB OBJECT-TYPE
    SYNTAX      OCTET STRING (SIZE(0..32))
    MAX-ACCESS  read-write
    STATUS      current
    DESCRIPTION
        "The transmitted Operator Specific part of the TCMB trace (32 character)" 
    ::=  { changeServiceDeployProvIfEntry 66 }

changeServiceDeployProvIfTimModeOduTcmB OBJECT-TYPE
    SYNTAX      TimMode
    MAX-ACCESS  read-write
    STATUS      current
    DESCRIPTION
        "TCM_B Trace Identifier Mismatch (TIM) detection/action for TIM defect." 
    ::=  { changeServiceDeployProvIfEntry 67 }

changeServiceDeployProvIfTraceExpectedOduTcmC OBJECT-TYPE
    SYNTAX      OCTET STRING (SIZE(0..15))
    MAX-ACCESS  read-write
    STATUS      current
    DESCRIPTION   "Expected SAPI part of the TCMC trace (15 character).
         NULL TRACE-TCM implies that no trace comparison is made."
    ::=  { changeServiceDeployProvIfEntry 68 }

changeServiceDeployProvIfTraceTransmitSapiOduTcmC OBJECT-TYPE
    SYNTAX      OCTET STRING (SIZE(0..15))
    MAX-ACCESS  read-write
    STATUS      current
    DESCRIPTION
        "The transmitted SAPI part of the TCMC trace (15 character)" 
    ::=  { changeServiceDeployProvIfEntry 69 }

changeServiceDeployProvIfTraceTransmitDapiOduTcmC OBJECT-TYPE
    SYNTAX      OCTET STRING (SIZE(0..15))
    MAX-ACCESS  read-write
    STATUS      current
    DESCRIPTION
        "The transmitted DAPI part of the TCMC trace (15 character)" 
    ::=  { changeServiceDeployProvIfEntry 70 }

changeServiceDeployProvIfTraceTransmitOpspOduTcmC OBJECT-TYPE
    SYNTAX      OCTET STRING (SIZE(0..32))
    MAX-ACCESS  read-write
    STATUS      current
    DESCRIPTION
        "The transmitted Operator Specific part of the TCMC trace (32 character)" 
    ::=  { changeServiceDeployProvIfEntry 71 }

changeServiceDeployProvIfTimModeOduTcmC OBJECT-TYPE
    SYNTAX      TimMode
    MAX-ACCESS  read-write
    STATUS      current
    DESCRIPTION
        "TCM_C Trace Identifier Mismatch (TIM) detection/action for TIM defect." 
    ::=  { changeServiceDeployProvIfEntry 72 }

changeServiceDeployProvIfChannelProvisioning OBJECT-TYPE
    SYNTAX      FspR7ChannelIdentifier
    MAX-ACCESS  read-write
    STATUS      current
    DESCRIPTION
        "Channel" 
    ::=  { changeServiceDeployProvIfEntry 73 }

changeServiceDeployProvIfVariableGain OBJECT-TYPE
    SYNTAX      Unsigned32 (0..350 | 4294967295) 
    UNITS       "0.1 dB"
    MAX-ACCESS  read-write
    STATUS      current
    DESCRIPTION
        "Variable Gain of EDFA" 
    ::=  { changeServiceDeployProvIfEntry 74 }

changeServiceDeployProvIfBand OBJECT-TYPE
    SYNTAX      FspR7OpticalBand
    MAX-ACCESS  read-write
    STATUS      current
    DESCRIPTION   "The The optical band of the module."
    ::=  { changeServiceDeployProvIfEntry 75 }

changeServiceDeployProvIfSigDegThreshold OBJECT-TYPE
    SYNTAX      Unsigned32 (1..10000 | 4294967295)
    MAX-ACCESS  read-write
    STATUS      current
    DESCRIPTION
        "Threshold for number of errors (CV or CV+DE) in one second" 
    ::=  { changeServiceDeployProvIfEntry 76 }

changeServiceDeployProvIfSigDegPeriodIntegration OBJECT-TYPE
    SYNTAX      Unsigned32 (1..10 | 4294967295) 
    UNITS       "s"
    MAX-ACCESS  read-write
    STATUS      current
    DESCRIPTION
        "Integration Period for Signal degrade" 
    ::=  { changeServiceDeployProvIfEntry 77 }

changeServiceDeployProvIfVoaMode OBJECT-TYPE
    SYNTAX      FspR7VoaMode
    MAX-ACCESS  read-write
    STATUS      current
    DESCRIPTION
        "VOA operating mode" 
    ::=  { changeServiceDeployProvIfEntry 78 }

changeServiceDeployProvIfOpticalSetPoint OBJECT-TYPE
    SYNTAX      Integer32 (-250..100 | -2147483648) 
    UNITS       "0.1 dBm"
    MAX-ACCESS  read-write
    STATUS      current
    DESCRIPTION
        "Sets the optical power for power equalization in ROADM or for channel power control in OPCM" 
    ::=  { changeServiceDeployProvIfEntry 79 }

changeServiceDeployProvIfVoaSetpoint OBJECT-TYPE
    SYNTAX      Unsigned32 (0..300 | 4294967295) 
    UNITS       "0.1 dB"
    MAX-ACCESS  read-write
    STATUS      current
    DESCRIPTION
        "Sets the optical attenuation of VOA" 
    ::=  { changeServiceDeployProvIfEntry 80 }

changeServiceDeployProvIfLanAid OBJECT-TYPE
    SYNTAX      EntityIndex
    MAX-ACCESS  read-write
    STATUS      current
    DESCRIPTION
        "AID of LAN" 
    ::=  { changeServiceDeployProvIfEntry 81 }

changeServiceDeployProvIfAprHighThreshold OBJECT-TYPE
    SYNTAX      Unsigned32 
    UNITS       "0.1 dBm"
    MAX-ACCESS  read-write
    STATUS      current
    DESCRIPTION
        "Automatic Power Reduction High Threshold" 
    ::=  { changeServiceDeployProvIfEntry 82 }

changeServiceDeployProvIfPumpPower OBJECT-TYPE
    SYNTAX      Integer32 (115..138 | -2147483648) 
    UNITS       "0.2 dBm"
    MAX-ACCESS  read-write
    STATUS      current
    DESCRIPTION
        "Total raman pump power" 
    ::=  { changeServiceDeployProvIfEntry 83 }

changeServiceDeployProvIfWdmRxChannel OBJECT-TYPE
    SYNTAX      FspR7ChannelIdentifier
    MAX-ACCESS  read-write
    STATUS      current
    DESCRIPTION
        "Configuration of Rx optical channel" 
    ::=  { changeServiceDeployProvIfEntry 84 }

changeServiceDeployProvIfSigDegThresSonetSection OBJECT-TYPE
    SYNTAX      FspR7BERThresholdSection
    MAX-ACCESS  read-write
    STATUS      current
    DESCRIPTION
        "Bit-Error-Based Degradation Definition for SONET (standard integration period)" 
    ::=  { changeServiceDeployProvIfEntry 85 }

changeServiceDeployProvIfSigDegThresSdhSection OBJECT-TYPE
    SYNTAX      Unsigned32 (1..100 | 4294967295) 
    UNITS       "%"
    MAX-ACCESS  read-write
    STATUS      current
    DESCRIPTION
        "Block-Error-Based Degradation Definition for SDH (standard integration period).
         Defined as percentage Background Block Errors (30% default) evaluated
         over a defined period (SDPER-RS)." 
    ::=  { changeServiceDeployProvIfEntry 86 }

changeServiceDeployProvIfSigDegPeriodSdhSection OBJECT-TYPE
    SYNTAX      Unsigned32 (2..10 | 4294967295) 
    UNITS       "s"
    MAX-ACCESS  read-write
    STATUS      current
    DESCRIPTION
        "Provisionable Signal Degrade Integration Period for SDH" 
    ::=  { changeServiceDeployProvIfEntry 87 }

changeServiceDeployProvIfDispersionMode OBJECT-TYPE
    SYNTAX      FspR7DispersionModes
    MAX-ACCESS  read-write
    STATUS      current
    DESCRIPTION
        "Chromatic Dispersion Compensation Mode" 
    ::=  { changeServiceDeployProvIfEntry 88 }

changeServiceDeployProvIfDispersionSetting OBJECT-TYPE
    SYNTAX      Integer32 (-50000..50000 | -2147483648) 
    UNITS       "ps/nm"
    MAX-ACCESS  read-write
    STATUS      current
    DESCRIPTION
        "Chromatic Dispersion Compensation setting on module" 
    ::=  { changeServiceDeployProvIfEntry 89 }

changeServiceDeployProvIfIpType OBJECT-TYPE
    SYNTAX      FspR7IpType
    MAX-ACCESS  read-write
    STATUS      current
    DESCRIPTION
        "Type of IP configuration" 
    ::=  { changeServiceDeployProvIfEntry 90 }

changeServiceDeployProvIfOffset OBJECT-TYPE
    SYNTAX      Integer32 (10..30 | -2147483648) 
    UNITS       "0.1 dB"
    MAX-ACCESS  read-write
    STATUS      current
    DESCRIPTION   "Sets the offset for the mean optical power for power equalization in ROADM"
    ::=  { changeServiceDeployProvIfEntry 91 }

changeServiceDeployProvIfFunction OBJECT-TYPE
    SYNTAX      FspR7InterfaceFunction
    MAX-ACCESS  read-write
    STATUS      current
    DESCRIPTION
        "Interface Function" 
    ::=  { changeServiceDeployProvIfEntry 92 }

changeServiceDeployProvIfFarEndCommunication OBJECT-TYPE
    SYNTAX      FspR7YesNo
    MAX-ACCESS  read-write
    STATUS      current
    DESCRIPTION
        "Used for Optojack plugs; Communication to Far End Plug is observed" 
    ::=  { changeServiceDeployProvIfEntry 93 }

changeServiceDeployProvIfEqlzAdmin OBJECT-TYPE
    SYNTAX      FspR7EqlzAdminState
    MAX-ACCESS  read-write
    STATUS      current
    DESCRIPTION   "Scheduled Equalization Administration"
    ::=  { changeServiceDeployProvIfEntry 94 }

changeServiceDeployProvIfTxOffDelay OBJECT-TYPE
    SYNTAX      FspR7EnableDisable
    MAX-ACCESS  read-write
    STATUS      current
    DESCRIPTION
        "Enable or disable TXOFFHOLD Period for Error Forwarding and LKDO-OFF Consequent Action." 
    ::=  { changeServiceDeployProvIfEntry 95 }

changeServiceDeployProvIfOpuPayloadType OBJECT-TYPE
    SYNTAX      FspR7OpuPayloadType
    MAX-ACCESS  read-write
    STATUS      current
    DESCRIPTION
        "OPU Payload Type Indicator" 
    ::=  { changeServiceDeployProvIfEntry 96 }

changeServiceDeployProvIfOscOpticalSetpoint OBJECT-TYPE
    SYNTAX      Integer32 (-250..50 | -2147483648) 
    UNITS       "0.1 dBm"
    MAX-ACCESS  read-write
    STATUS      current
    DESCRIPTION
        "Sets the OSC optical power" 
    ::=  { changeServiceDeployProvIfEntry 97 }

changeServiceDeployProvIfFiberBrand OBJECT-TYPE
    SYNTAX      FspR7FiberBrand
    MAX-ACCESS  read-write
    STATUS      current
    DESCRIPTION
        "Brand of fiber present in the fiber plant" 
    ::=  { changeServiceDeployProvIfEntry 98 }

changeServiceDeployProvIfXfpDecisionThres OBJECT-TYPE
    SYNTAX      FspR7XfpDecisionThres
    MAX-ACCESS  read-write
    STATUS      current
    DESCRIPTION
        "XFP Decision threshold setting" 
    ::=  { changeServiceDeployProvIfEntry 99 }

changeServiceDeployProvIfLaserDelayTimer OBJECT-TYPE
    SYNTAX      FspR7LaserDelayTimer
    MAX-ACCESS  read-write
    STATUS      current
    DESCRIPTION
        "Relevant only when ERRFWD=LSROFF. Enables/disables the
         possibility to delay turning off and on the laser.
         This applies to the case when turning off the laser
         is done as an error forwarding mechanism." 
    ::=  { changeServiceDeployProvIfEntry 100 }

changeServiceDeployProvIfLaserOffTimer OBJECT-TYPE
    SYNTAX      Unsigned32 (1..1000 | 4294967295) 
    UNITS       "ms"
    MAX-ACCESS  read-write
    STATUS      current
    DESCRIPTION
        "Delay before laser is swiched off" 
    ::=  { changeServiceDeployProvIfEntry 101 }

changeServiceDeployProvIfLaserOnTimer OBJECT-TYPE
    SYNTAX      Unsigned32 (1..1000 | 4294967295) 
    UNITS       "ms"
    MAX-ACCESS  read-write
    STATUS      current
    DESCRIPTION
        "Delay before laser is switched on" 
    ::=  { changeServiceDeployProvIfEntry 102 }

changeServiceDeployProvIfLaneChannelSetting OBJECT-TYPE
    SYNTAX      FspR7ChannelIdentifier
    MAX-ACCESS  read-write
    STATUS      current
    DESCRIPTION
        "Lane Channel Setting" 
    ::=  { changeServiceDeployProvIfEntry 103 }

changeServiceDeployProvIfBip OBJECT-TYPE
    SYNTAX      FspR7Bip
    MAX-ACCESS  read-write
    STATUS      current
    DESCRIPTION
        "Bit Interleaved Parity" 
    ::=  { changeServiceDeployProvIfEntry 104 }

changeServiceDeployProvIfCodeGain OBJECT-TYPE
    SYNTAX      FspR7CodeGain
    MAX-ACCESS  read-write
    STATUS      current
    DESCRIPTION
        "Forward Error Correction Coding gain" 
    ::=  { changeServiceDeployProvIfEntry 105 }

changeServiceDeployProvIfCapTable OBJECT-TYPE
    SYNTAX      SEQUENCE OF ChangeServiceDeployProvIfCapEntry
    MAX-ACCESS  not-accessible
    STATUS      current
    DESCRIPTION   ""
    ::=  { facilityDeployProv 41  }

changeServiceDeployProvIfCapEntry OBJECT-TYPE
    SYNTAX      ChangeServiceDeployProvIfCapEntry
    MAX-ACCESS  not-accessible
    STATUS      current
    DESCRIPTION   ""
    INDEX       { entityIndex }
    ::=  { changeServiceDeployProvIfCapTable 1 }

ChangeServiceDeployProvIfCapEntry ::=  SEQUENCE
  { changeServiceDeployProvIfCapRowStatus FspR7RowStatusCaps,
    changeServiceDeployProvIfCapForceDestroy FspR7ForcedStatusCaps,
    changeServiceDeployProvIfCapType FspR7InterfaceTypeCaps,
    changeServiceDeployProvIfCapPayload OtnPayloadTypeCaps,
    changeServiceDeployProvIfCapBehaviour FspR7PortBehaviourCaps,
    changeServiceDeployProvIfCapTerminationLevel OhTerminationLevelCaps,
    changeServiceDeployProvIfCapAlsMode FspR7AlsModeCaps,
    changeServiceDeployProvIfCapErrorForwarding FspR7ErrorFwdModeCaps,
    changeServiceDeployProvIfCapLaserOffDelayFunction EnableStateCaps,
    changeServiceDeployProvIfCapFecType FspR7FecTypeCaps,
    changeServiceDeployProvIfCapTimingSource SonetTimingSourceCaps,
    changeServiceDeployProvIfCapTcmALevel OtnTcmLevelCaps,
    changeServiceDeployProvIfCapTcmBLevel OtnTcmLevelCaps,
    changeServiceDeployProvIfCapSigDegThresSonetLine FspR7BERThresholdCaps,
    changeServiceDeployProvIfCapSigDegThresSdhMs FspR7Unsigned32Caps,
    changeServiceDeployProvIfCapSignalDegradePeriod FspR7Unsigned32Caps,
    changeServiceDeployProvIfCapAutonegotiation EnableStateCaps,
    changeServiceDeployProvIfCapBitrate FspR7BitrateCaps,
    changeServiceDeployProvIfCapDuplex EthDuplexModeCaps,
    changeServiceDeployProvIfCapFlowControl FspR7FlowControlModeCaps,
    changeServiceDeployProvIfCapOtnStuffing FspR7StuffCaps,
    changeServiceDeployProvIfCapSigDegThresOtu FspR7Integer32Caps,
    changeServiceDeployProvIfCapSigDegPeriodOtu FspR7Unsigned32Caps,
    changeServiceDeployProvIfCapSigDegThresOdu FspR7Integer32Caps,
    changeServiceDeployProvIfCapSigDegPeriodOdu FspR7Unsigned32Caps,
    changeServiceDeployProvIfCapSigDegThresOduTcmA FspR7Integer32Caps,
    changeServiceDeployProvIfCapSigDegPeriodOduTcmA FspR7Unsigned32Caps,
    changeServiceDeployProvIfCapSigDegThresOduTcmB FspR7Integer32Caps,
    changeServiceDeployProvIfCapSigDegPeriodOduTcmB FspR7Unsigned32Caps,
    changeServiceDeployProvIfCapTilt FspR7Integer32Caps,
    changeServiceDeployProvIfCapGain FspR7GainCaps,
    changeServiceDeployProvIfCapAdmin FspR7AdminStateCaps,
    changeServiceDeployProvIfCapAttenuationGradient FspR7Unsigned32Caps,
    changeServiceDeployProvIfCapSigDegThresReceiver FspR7Unsigned32Caps,
    changeServiceDeployProvIfCapTcmCLevel OtnTcmLevelCaps,
    changeServiceDeployProvIfCapSigDegThresOduTcmC FspR7Integer32Caps,
    changeServiceDeployProvIfCapSigDegPeriodOduTcmC FspR7Unsigned32Caps,
    changeServiceDeployProvIfCapDisparityCorrection EnableStateCaps,
    changeServiceDeployProvIfCapIpAddr FspR7YesNo,
    changeServiceDeployProvIfCapIpMask FspR7YesNo,
    changeServiceDeployProvIfCapOspf FspR7OspfModeCaps,
    changeServiceDeployProvIfCapMetric FspR7Unsigned32Caps,
    changeServiceDeployProvIfCapAreaId FspR7YesNo,
    changeServiceDeployProvIfCapTraceFormSonetSection SonetTraceFormCaps,
    changeServiceDeployProvIfCapTraceExpectedSonetSection Integer32,
    changeServiceDeployProvIfCapTraceTransmitSonetSection Integer32,
    changeServiceDeployProvIfCapTimModeSonetSection TimModeCaps,
    changeServiceDeployProvIfCapTraceExpectedOtu Integer32,
    changeServiceDeployProvIfCapTraceTransmitSapiOtu Integer32,
    changeServiceDeployProvIfCapTraceTransmitDapiOtu Integer32,
    changeServiceDeployProvIfCapTraceTransmitOpspOtu Integer32,
    changeServiceDeployProvIfCapTimModeOtu TimModeCaps,
    changeServiceDeployProvIfCapTraceExpectedOdu Integer32,
    changeServiceDeployProvIfCapTraceTransmitSapiOdu Integer32,
    changeServiceDeployProvIfCapTraceTransmitDapiOdu Integer32,
    changeServiceDeployProvIfCapTraceTransmitOpspOdu Integer32,
    changeServiceDeployProvIfCapTimModeOdu TimModeCaps,
    changeServiceDeployProvIfCapTraceExpectedOduTcmA Integer32,
    changeServiceDeployProvIfCapTraceTransmitSapiOduTcmA Integer32,
    changeServiceDeployProvIfCapTraceTransmitDapiOduTcmA Integer32,
    changeServiceDeployProvIfCapTraceTransmitOpspOduTcmA Integer32,
    changeServiceDeployProvIfCapTimModeOduTcmA TimModeCaps,
    changeServiceDeployProvIfCapTraceExpectedOduTcmB Integer32,
    changeServiceDeployProvIfCapTraceTransmitSapiOduTcmB Integer32,
    changeServiceDeployProvIfCapTraceTransmitDapiOduTcmB Integer32,
    changeServiceDeployProvIfCapTraceTransmitOpspOduTcmB Integer32,
    changeServiceDeployProvIfCapTimModeOduTcmB TimModeCaps,
    changeServiceDeployProvIfCapTraceExpectedOduTcmC Integer32,
    changeServiceDeployProvIfCapTraceTransmitSapiOduTcmC Integer32,
    changeServiceDeployProvIfCapTraceTransmitDapiOduTcmC Integer32,
    changeServiceDeployProvIfCapTraceTransmitOpspOduTcmC Integer32,
    changeServiceDeployProvIfCapTimModeOduTcmC TimModeCaps,
    changeServiceDeployProvIfCapChannelProvisioning FspR7ChannelIdentifierCaps,
    changeServiceDeployProvIfCapVariableGain FspR7Unsigned32Caps,
    changeServiceDeployProvIfCapBand FspR7OpticalBandCaps,
    changeServiceDeployProvIfCapSigDegThreshold FspR7Unsigned32Caps,
    changeServiceDeployProvIfCapSigDegPeriodIntegration FspR7Unsigned32Caps,
    changeServiceDeployProvIfCapVoaMode FspR7VoaModeCaps,
    changeServiceDeployProvIfCapOpticalSetPoint FspR7Integer32Caps,
    changeServiceDeployProvIfCapVoaSetpoint FspR7Unsigned32Caps,
    changeServiceDeployProvIfCapLanAid Integer32,
    changeServiceDeployProvIfCapAprHighThreshold FspR7Unsigned32Caps,
    changeServiceDeployProvIfCapPumpPower FspR7Integer32Caps,
    changeServiceDeployProvIfCapWdmRxChannel FspR7ChannelIdentifierCaps,
    changeServiceDeployProvIfCapSigDegThresSonetSection FspR7BERThresholdSectionCaps,
    changeServiceDeployProvIfCapSigDegThresSdhSection FspR7Unsigned32Caps,
    changeServiceDeployProvIfCapSigDegPeriodSdhSection FspR7Unsigned32Caps,
    changeServiceDeployProvIfCapDispersionMode FspR7DispersionModesCaps,
    changeServiceDeployProvIfCapDispersionSetting FspR7Integer32Caps,
    changeServiceDeployProvIfCapIpType FspR7IpTypeCaps,
    changeServiceDeployProvIfCapOffset FspR7Integer32Caps,
    changeServiceDeployProvIfCapFunction FspR7InterfaceFunctionCaps,
    changeServiceDeployProvIfCapFarEndCommunication FspR7YesNoCaps,
    changeServiceDeployProvIfCapEqlzAdmin FspR7EqlzAdminStateCaps,
    changeServiceDeployProvIfCapTxOffDelay FspR7EnableDisableCaps,
    changeServiceDeployProvIfCapOpuPayloadType FspR7OpuPayloadTypeCaps,
    changeServiceDeployProvIfCapOscOpticalSetpoint FspR7Integer32Caps,
    changeServiceDeployProvIfCapFiberBrand FspR7FiberBrandCaps,
    changeServiceDeployProvIfCapXfpDecisionThres FspR7XfpDecisionThresCaps,
    changeServiceDeployProvIfCapLaserDelayTimer FspR7LaserDelayTimerCaps,
    changeServiceDeployProvIfCapLaserOffTimer FspR7Unsigned32Caps,
    changeServiceDeployProvIfCapLaserOnTimer FspR7Unsigned32Caps,
    changeServiceDeployProvIfCapLaneChannelSetting FspR7ChannelIdentifierCaps,
    changeServiceDeployProvIfCapBip FspR7BipCaps,
    changeServiceDeployProvIfCapCodeGain FspR7CodeGainCaps }

changeServiceDeployProvIfCapRowStatus OBJECT-TYPE
    SYNTAX      FspR7RowStatusCaps
    MAX-ACCESS  read-only
    STATUS      current
    DESCRIPTION   "RowStatus"
    ::=  { changeServiceDeployProvIfCapEntry 1 }

changeServiceDeployProvIfCapForceDestroy OBJECT-TYPE
    SYNTAX      FspR7ForcedStatusCaps
    MAX-ACCESS  read-only
    STATUS      current
    DESCRIPTION
        "Forced Destroy" 
    ::=  { changeServiceDeployProvIfCapEntry 2 }

changeServiceDeployProvIfCapType OBJECT-TYPE
    SYNTAX      FspR7InterfaceTypeCaps
    MAX-ACCESS  read-only
    STATUS      current
    DESCRIPTION   "The TYPE defines the transport service type as wrapper with wrapper layer
         termination OR else as payload"
    ::=  { changeServiceDeployProvIfCapEntry 3 }

changeServiceDeployProvIfCapPayload OBJECT-TYPE
    SYNTAX      OtnPayloadTypeCaps
    MAX-ACCESS  read-only
    STATUS      current
    DESCRIPTION   "The payload of the interface (inside a transport overhead).
         Relevant e. g. for OTN cards which wrap a payload into an OTU1/2 wrapper."
    ::=  { changeServiceDeployProvIfCapEntry 4 }

changeServiceDeployProvIfCapBehaviour OBJECT-TYPE
    SYNTAX      FspR7PortBehaviourCaps
    MAX-ACCESS  read-only
    STATUS      current
    DESCRIPTION   "The configured behaviour of the interface. If configured as
         a network interface, the interface will use a WDM laser."
    ::=  { changeServiceDeployProvIfCapEntry 5 }

changeServiceDeployProvIfCapTerminationLevel OBJECT-TYPE
    SYNTAX      OhTerminationLevelCaps
    MAX-ACCESS  read-only
    STATUS      current
    DESCRIPTION
        "Highest signal level hardware removes then generates for transmission." 
    ::=  { changeServiceDeployProvIfCapEntry 6 }

changeServiceDeployProvIfCapAlsMode OBJECT-TYPE
    SYNTAX      FspR7AlsModeCaps
    MAX-ACCESS  read-only
    STATUS      current
    DESCRIPTION   "A configuration request for the Automatic Laser Shutdown (ALS)
         function. Refer to FspR7AlsMode Textual Convention for details."
    ::=  { changeServiceDeployProvIfCapEntry 7 }

changeServiceDeployProvIfCapErrorForwarding OBJECT-TYPE
    SYNTAX      FspR7ErrorFwdModeCaps
    MAX-ACCESS  read-only
    STATUS      current
    DESCRIPTION   "A configuration request for the error forwarding
         function. Refer to FspR7ErrorFwdMode Textual Convention for details."
    ::=  { changeServiceDeployProvIfCapEntry 8 }

changeServiceDeployProvIfCapLaserOffDelayFunction OBJECT-TYPE
    SYNTAX      EnableStateCaps
    MAX-ACCESS  read-only
    STATUS      current
    DESCRIPTION   "A configuration request for the Laser Off Delay function. This function
         delays turning off the laser as a consequent action to a defect."
    ::=  { changeServiceDeployProvIfCapEntry 9 }

changeServiceDeployProvIfCapFecType OBJECT-TYPE
    SYNTAX      FspR7FecTypeCaps
    MAX-ACCESS  read-only
    STATUS      current
    DESCRIPTION   "Configuration of FEC type."
    ::=  { changeServiceDeployProvIfCapEntry 10 }

changeServiceDeployProvIfCapTimingSource OBJECT-TYPE
    SYNTAX      SonetTimingSourceCaps
    MAX-ACCESS  read-only
    STATUS      current
    DESCRIPTION   "The timing source for this interface.
         - internal: used in stand-alone, point-to-point topologies stand-alone (dedicated fiber operation).
         - loopTiming: e.g. used in point-to-point via SONET network and feeder topologies. The default is
         internal(1)."
    ::=  { changeServiceDeployProvIfCapEntry 11 }

changeServiceDeployProvIfCapTcmALevel OBJECT-TYPE
    SYNTAX      OtnTcmLevelCaps
    MAX-ACCESS  read-only
    STATUS      current
    DESCRIPTION   "Configuration of TCMA level."
    ::=  { changeServiceDeployProvIfCapEntry 12 }

changeServiceDeployProvIfCapTcmBLevel OBJECT-TYPE
    SYNTAX      OtnTcmLevelCaps
    MAX-ACCESS  read-only
    STATUS      current
    DESCRIPTION   "Configuration of TCMB level."
    ::=  { changeServiceDeployProvIfCapEntry 13 }

changeServiceDeployProvIfCapSigDegThresSonetLine OBJECT-TYPE
    SYNTAX      FspR7BERThresholdCaps
    MAX-ACCESS  read-only
    STATUS      current
    DESCRIPTION
        "Bit-Error-Based Degradation Definition for SONET (standard integration period)" 
    ::=  { changeServiceDeployProvIfCapEntry 14 }

changeServiceDeployProvIfCapSigDegThresSdhMs OBJECT-TYPE
    SYNTAX      FspR7Unsigned32Caps
    UNITS       "%"
    MAX-ACCESS  read-only
    STATUS      current
    DESCRIPTION
        "Block-Error-Based Degradation Definition for SDH (standard integration period).
         Defined as percentage Background Block Errors (30% default) evaluated
         over a defined period (SDPER-RS)." 
    ::=  { changeServiceDeployProvIfCapEntry 15 }

changeServiceDeployProvIfCapSignalDegradePeriod OBJECT-TYPE
    SYNTAX      FspR7Unsigned32Caps
    UNITS       "s"
    MAX-ACCESS  read-only
    STATUS      current
    DESCRIPTION   "The measurement period in seconds used together with
         the deployProvIfSigDegThresSdhRegSect based on the block error counting method.
         The valid range is 2..10,
         The default being 7."
    ::=  { changeServiceDeployProvIfCapEntry 16 }

changeServiceDeployProvIfCapAutonegotiation OBJECT-TYPE
    SYNTAX      EnableStateCaps
    MAX-ACCESS  read-only
    STATUS      current
    DESCRIPTION
        "Auto Negotiation for the data rate" 
    ::=  { changeServiceDeployProvIfCapEntry 17 }

changeServiceDeployProvIfCapBitrate OBJECT-TYPE
    SYNTAX      FspR7BitrateCaps
    MAX-ACCESS  read-only
    STATUS      current
    DESCRIPTION
        "Provisioned data rate" 
    ::=  { changeServiceDeployProvIfCapEntry 18 }

changeServiceDeployProvIfCapDuplex OBJECT-TYPE
    SYNTAX      EthDuplexModeCaps
    MAX-ACCESS  read-only
    STATUS      current
    DESCRIPTION
        "Duplex Mode (provision), available when Auto Negoiation is Disable (AUTONEG=DISABLE)" 
    ::=  { changeServiceDeployProvIfCapEntry 19 }

changeServiceDeployProvIfCapFlowControl OBJECT-TYPE
    SYNTAX      FspR7FlowControlModeCaps
    MAX-ACCESS  read-only
    STATUS      current
    DESCRIPTION
        "Flow Control mechanism" 
    ::=  { changeServiceDeployProvIfCapEntry 20 }

changeServiceDeployProvIfCapOtnStuffing OBJECT-TYPE
    SYNTAX      FspR7StuffCaps
    MAX-ACCESS  read-only
    STATUS      current
    DESCRIPTION
        "Indicates if bit/byte stuffing is used in the transport signal." 
    ::=  { changeServiceDeployProvIfCapEntry 21 }

changeServiceDeployProvIfCapSigDegThresOtu OBJECT-TYPE
    SYNTAX      FspR7Integer32Caps
    UNITS       "%"
    MAX-ACCESS  read-only
    STATUS      current
    DESCRIPTION
        "Background-Block-Error-Based Signal Degradation Definition for OTU" 
    ::=  { changeServiceDeployProvIfCapEntry 22 }

changeServiceDeployProvIfCapSigDegPeriodOtu OBJECT-TYPE
    SYNTAX      FspR7Unsigned32Caps
    UNITS       "s"
    MAX-ACCESS  read-only
    STATUS      current
    DESCRIPTION
        "Integration Period for Signal degrade" 
    ::=  { changeServiceDeployProvIfCapEntry 23 }

changeServiceDeployProvIfCapSigDegThresOdu OBJECT-TYPE
    SYNTAX      FspR7Integer32Caps
    UNITS       "%"
    MAX-ACCESS  read-only
    STATUS      current
    DESCRIPTION
        "Background-Block-Error-Based Signal Degradation Definition for ODU" 
    ::=  { changeServiceDeployProvIfCapEntry 24 }

changeServiceDeployProvIfCapSigDegPeriodOdu OBJECT-TYPE
    SYNTAX      FspR7Unsigned32Caps
    UNITS       "s"
    MAX-ACCESS  read-only
    STATUS      current
    DESCRIPTION
        "Integration Period for Signal degrade" 
    ::=  { changeServiceDeployProvIfCapEntry 25 }

changeServiceDeployProvIfCapSigDegThresOduTcmA OBJECT-TYPE
    SYNTAX      FspR7Integer32Caps
    UNITS       "%"
    MAX-ACCESS  read-only
    STATUS      current
    DESCRIPTION
        "Background-Block-Error-Based Signal Degradation Definition for TCM-A" 
    ::=  { changeServiceDeployProvIfCapEntry 26 }

changeServiceDeployProvIfCapSigDegPeriodOduTcmA OBJECT-TYPE
    SYNTAX      FspR7Unsigned32Caps
    UNITS       "s"
    MAX-ACCESS  read-only
    STATUS      current
    DESCRIPTION
        "Integration Period for Signal degrade" 
    ::=  { changeServiceDeployProvIfCapEntry 27 }

changeServiceDeployProvIfCapSigDegThresOduTcmB OBJECT-TYPE
    SYNTAX      FspR7Integer32Caps
    UNITS       "%"
    MAX-ACCESS  read-only
    STATUS      current
    DESCRIPTION
        "Background-Block-Error-Based Signal Degradation Definition for TCM-B" 
    ::=  { changeServiceDeployProvIfCapEntry 28 }

changeServiceDeployProvIfCapSigDegPeriodOduTcmB OBJECT-TYPE
    SYNTAX      FspR7Unsigned32Caps
    UNITS       "s"
    MAX-ACCESS  read-only
    STATUS      current
    DESCRIPTION
        "Integration Period of TCMB Signal Segrade" 
    ::=  { changeServiceDeployProvIfCapEntry 29 }

changeServiceDeployProvIfCapTilt OBJECT-TYPE
    SYNTAX      FspR7Integer32Caps
    UNITS       "0.1 dB"
    MAX-ACCESS  read-only
    STATUS      current
    DESCRIPTION
        "Change of optical channel power in dB over the complete transmission band" 
    ::=  { changeServiceDeployProvIfCapEntry 30 }

changeServiceDeployProvIfCapGain OBJECT-TYPE
    SYNTAX      FspR7GainCaps
    MAX-ACCESS  read-only
    STATUS      current
    DESCRIPTION
        "Gain" 
    ::=  { changeServiceDeployProvIfCapEntry 31 }

changeServiceDeployProvIfCapAdmin OBJECT-TYPE
    SYNTAX      FspR7AdminStateCaps
    MAX-ACCESS  read-only
    STATUS      current
    DESCRIPTION   "The Adminstrative State."
    ::=  { changeServiceDeployProvIfCapEntry 32 }

changeServiceDeployProvIfCapAttenuationGradient OBJECT-TYPE
    SYNTAX      FspR7Unsigned32Caps
    UNITS       "0.1 dB/min"
    MAX-ACCESS  read-only
    STATUS      current
    DESCRIPTION   "Attenuation Gradient Threshold on Receive Fiber. Applies to both
         TRMT and RCV directions; but threshold violation is reported for
         each direction separately by the 'tapping' alarms: INTRUDE-RCV
         and INTRUDE-TRMT."
    ::=  { changeServiceDeployProvIfCapEntry 33 }

changeServiceDeployProvIfCapSigDegThresReceiver OBJECT-TYPE
    SYNTAX      FspR7Unsigned32Caps
    UNITS       "0.1 dB"
    MAX-ACCESS  read-only
    STATUS      current
    DESCRIPTION
        "Signal Degrade Threshold on Receiver. Reported as ATTRMT-SDHT to far end." 
    ::=  { changeServiceDeployProvIfCapEntry 34 }

changeServiceDeployProvIfCapTcmCLevel OBJECT-TYPE
    SYNTAX      OtnTcmLevelCaps
    MAX-ACCESS  read-only
    STATUS      current
    DESCRIPTION
        "Activation of Tandem Connection Monitoring Instance C" 
    ::=  { changeServiceDeployProvIfCapEntry 35 }

changeServiceDeployProvIfCapSigDegThresOduTcmC OBJECT-TYPE
    SYNTAX      FspR7Integer32Caps
    UNITS       "%"
    MAX-ACCESS  read-only
    STATUS      current
    DESCRIPTION
        "Background-Block-Error-Based Signal Degradation Definition for TCM-C" 
    ::=  { changeServiceDeployProvIfCapEntry 36 }

changeServiceDeployProvIfCapSigDegPeriodOduTcmC OBJECT-TYPE
    SYNTAX      FspR7Unsigned32Caps
    UNITS       "s"
    MAX-ACCESS  read-only
    STATUS      current
    DESCRIPTION
        "Integration Period of TCMC Signal Segrade" 
    ::=  { changeServiceDeployProvIfCapEntry 37 }

changeServiceDeployProvIfCapDisparityCorrection OBJECT-TYPE
    SYNTAX      EnableStateCaps
    MAX-ACCESS  read-only
    STATUS      current
    DESCRIPTION
        "Disparity correction" 
    ::=  { changeServiceDeployProvIfCapEntry 38 }

changeServiceDeployProvIfCapIpAddr OBJECT-TYPE
    SYNTAX      FspR7YesNo
    MAX-ACCESS  read-only
    STATUS      current
    DESCRIPTION
        "IP Address assigned to LAN IP Interface" 
    ::=  { changeServiceDeployProvIfCapEntry 39 }

changeServiceDeployProvIfCapIpMask OBJECT-TYPE
    SYNTAX      FspR7YesNo
    MAX-ACCESS  read-only
    STATUS      current
    DESCRIPTION
        "IP MASK assigned to LAN IP Interface" 
    ::=  { changeServiceDeployProvIfCapEntry 40 }

changeServiceDeployProvIfCapOspf OBJECT-TYPE
    SYNTAX      FspR7OspfModeCaps
    MAX-ACCESS  read-only
    STATUS      current
    DESCRIPTION
        "OSPF Routing (Dynamic)" 
    ::=  { changeServiceDeployProvIfCapEntry 41 }

changeServiceDeployProvIfCapMetric OBJECT-TYPE
    SYNTAX      FspR7Unsigned32Caps
    MAX-ACCESS  read-only
    STATUS      current
    DESCRIPTION
        "Routing Metric" 
    ::=  { changeServiceDeployProvIfCapEntry 42 }

changeServiceDeployProvIfCapAreaId OBJECT-TYPE
    SYNTAX      FspR7YesNo
    MAX-ACCESS  read-only
    STATUS      current
    DESCRIPTION
        "OSPF Area ID for IP Interface" 
    ::=  { changeServiceDeployProvIfCapEntry 43 }

changeServiceDeployProvIfCapTraceFormSonetSection OBJECT-TYPE
    SYNTAX      SonetTraceFormCaps
    MAX-ACCESS  read-only
    STATUS      current
    DESCRIPTION
        "Byte-Length of Trace Compared to Expected" 
    ::=  { changeServiceDeployProvIfCapEntry 44 }

changeServiceDeployProvIfCapTraceExpectedSonetSection OBJECT-TYPE
    SYNTAX      Integer32
    MAX-ACCESS  read-only
    STATUS      current
    DESCRIPTION
        "Expected Sec/RS trace. NULL TRACE implies that no trace comparison is made." 
    ::=  { changeServiceDeployProvIfCapEntry 45 }

changeServiceDeployProvIfCapTraceTransmitSonetSection OBJECT-TYPE
    SYNTAX      Integer32
    MAX-ACCESS  read-only
    STATUS      current
    DESCRIPTION
        "Sec/RS Trace to be Transmitted" 
    ::=  { changeServiceDeployProvIfCapEntry 46 }

changeServiceDeployProvIfCapTimModeSonetSection OBJECT-TYPE
    SYNTAX      TimModeCaps
    MAX-ACCESS  read-only
    STATUS      current
    DESCRIPTION
        "SONET Section Trace Identifier Mismatch (TIM) detection/action for TIM defect." 
    ::=  { changeServiceDeployProvIfCapEntry 47 }

changeServiceDeployProvIfCapTraceExpectedOtu OBJECT-TYPE
    SYNTAX      Integer32
    MAX-ACCESS  read-only
    STATUS      current
    DESCRIPTION   "Expected SAPI part of the OTU trace (15 character).
         NULL TRACE implies that no trace comparison is made."
    ::=  { changeServiceDeployProvIfCapEntry 48 }

changeServiceDeployProvIfCapTraceTransmitSapiOtu OBJECT-TYPE
    SYNTAX      Integer32
    MAX-ACCESS  read-only
    STATUS      current
    DESCRIPTION
        "The transmitted SAPI part of the OTU trace (15 character)" 
    ::=  { changeServiceDeployProvIfCapEntry 49 }

changeServiceDeployProvIfCapTraceTransmitDapiOtu OBJECT-TYPE
    SYNTAX      Integer32
    MAX-ACCESS  read-only
    STATUS      current
    DESCRIPTION
        "The transmitted DAPI part of the OTU trace (15 character)" 
    ::=  { changeServiceDeployProvIfCapEntry 50 }

changeServiceDeployProvIfCapTraceTransmitOpspOtu OBJECT-TYPE
    SYNTAX      Integer32
    MAX-ACCESS  read-only
    STATUS      current
    DESCRIPTION
        "The transmitted Operator Specific part of the OTU trace (32 character)" 
    ::=  { changeServiceDeployProvIfCapEntry 51 }

changeServiceDeployProvIfCapTimModeOtu OBJECT-TYPE
    SYNTAX      TimModeCaps
    MAX-ACCESS  read-only
    STATUS      current
    DESCRIPTION
        "OTU Trace Identifier Mismatch (TIM) detection/action for TIM defect." 
    ::=  { changeServiceDeployProvIfCapEntry 52 }

changeServiceDeployProvIfCapTraceExpectedOdu OBJECT-TYPE
    SYNTAX      Integer32
    MAX-ACCESS  read-only
    STATUS      current
    DESCRIPTION   "Expected SAPI part of the ODU trace (15 character).
         NULL TRACE implies that no trace comparison is made."
    ::=  { changeServiceDeployProvIfCapEntry 53 }

changeServiceDeployProvIfCapTraceTransmitSapiOdu OBJECT-TYPE
    SYNTAX      Integer32
    MAX-ACCESS  read-only
    STATUS      current
    DESCRIPTION
        "The transmitted SAPI part of the ODU trace (15 character)" 
    ::=  { changeServiceDeployProvIfCapEntry 54 }

changeServiceDeployProvIfCapTraceTransmitDapiOdu OBJECT-TYPE
    SYNTAX      Integer32
    MAX-ACCESS  read-only
    STATUS      current
    DESCRIPTION
        "The transmitted DAPI part of the ODU trace (15 character)" 
    ::=  { changeServiceDeployProvIfCapEntry 55 }

changeServiceDeployProvIfCapTraceTransmitOpspOdu OBJECT-TYPE
    SYNTAX      Integer32
    MAX-ACCESS  read-only
    STATUS      current
    DESCRIPTION
        "The transmitted Operator Specific part of the ODU trace (32 character)" 
    ::=  { changeServiceDeployProvIfCapEntry 56 }

changeServiceDeployProvIfCapTimModeOdu OBJECT-TYPE
    SYNTAX      TimModeCaps
    MAX-ACCESS  read-only
    STATUS      current
    DESCRIPTION
        "Detection of TIM-ODU Condition can be configured" 
    ::=  { changeServiceDeployProvIfCapEntry 57 }

changeServiceDeployProvIfCapTraceExpectedOduTcmA OBJECT-TYPE
    SYNTAX      Integer32
    MAX-ACCESS  read-only
    STATUS      current
    DESCRIPTION   "Expected SAPI part of the TCMA trace (15 character).
         NULL TRACE-TCM implies that no trace comparison is made."
    ::=  { changeServiceDeployProvIfCapEntry 58 }

changeServiceDeployProvIfCapTraceTransmitSapiOduTcmA OBJECT-TYPE
    SYNTAX      Integer32
    MAX-ACCESS  read-only
    STATUS      current
    DESCRIPTION
        "The transmitted SAPI part of the TCMA trace (15 character)" 
    ::=  { changeServiceDeployProvIfCapEntry 59 }

changeServiceDeployProvIfCapTraceTransmitDapiOduTcmA OBJECT-TYPE
    SYNTAX      Integer32
    MAX-ACCESS  read-only
    STATUS      current
    DESCRIPTION
        "The transmitted DAPI part of the TCMA trace (15 character)" 
    ::=  { changeServiceDeployProvIfCapEntry 60 }

changeServiceDeployProvIfCapTraceTransmitOpspOduTcmA OBJECT-TYPE
    SYNTAX      Integer32
    MAX-ACCESS  read-only
    STATUS      current
    DESCRIPTION
        "The transmitted Operator Specific part of the TCMA trace (32 character)" 
    ::=  { changeServiceDeployProvIfCapEntry 61 }

changeServiceDeployProvIfCapTimModeOduTcmA OBJECT-TYPE
    SYNTAX      TimModeCaps
    MAX-ACCESS  read-only
    STATUS      current
    DESCRIPTION
        "TCM_A Trace Identifier Mismatch (TIM) detection/action for TIM defect." 
    ::=  { changeServiceDeployProvIfCapEntry 62 }

changeServiceDeployProvIfCapTraceExpectedOduTcmB OBJECT-TYPE
    SYNTAX      Integer32
    MAX-ACCESS  read-only
    STATUS      current
    DESCRIPTION
        "Expected SAPI part of the TCMB trace (15 character). NULL TRACE-TCM implies that no trace comparison is made." 
    ::=  { changeServiceDeployProvIfCapEntry 63 }

changeServiceDeployProvIfCapTraceTransmitSapiOduTcmB OBJECT-TYPE
    SYNTAX      Integer32
    MAX-ACCESS  read-only
    STATUS      current
    DESCRIPTION
        "The transmitted SAPI part of the TCMB trace (15 character)" 
    ::=  { changeServiceDeployProvIfCapEntry 64 }

changeServiceDeployProvIfCapTraceTransmitDapiOduTcmB OBJECT-TYPE
    SYNTAX      Integer32
    MAX-ACCESS  read-only
    STATUS      current
    DESCRIPTION
        "The transmitted DAPI part of the TCMB trace (15 character)" 
    ::=  { changeServiceDeployProvIfCapEntry 65 }

changeServiceDeployProvIfCapTraceTransmitOpspOduTcmB OBJECT-TYPE
    SYNTAX      Integer32
    MAX-ACCESS  read-only
    STATUS      current
    DESCRIPTION
        "The transmitted Operator Specific part of the TCMB trace (32 character)" 
    ::=  { changeServiceDeployProvIfCapEntry 66 }

changeServiceDeployProvIfCapTimModeOduTcmB OBJECT-TYPE
    SYNTAX      TimModeCaps
    MAX-ACCESS  read-only
    STATUS      current
    DESCRIPTION
        "TCM_B Trace Identifier Mismatch (TIM) detection/action for TIM defect." 
    ::=  { changeServiceDeployProvIfCapEntry 67 }

changeServiceDeployProvIfCapTraceExpectedOduTcmC OBJECT-TYPE
    SYNTAX      Integer32
    MAX-ACCESS  read-only
    STATUS      current
    DESCRIPTION   "Expected SAPI part of the TCMC trace (15 character).
         NULL TRACE-TCM implies that no trace comparison is made."
    ::=  { changeServiceDeployProvIfCapEntry 68 }

changeServiceDeployProvIfCapTraceTransmitSapiOduTcmC OBJECT-TYPE
    SYNTAX      Integer32
    MAX-ACCESS  read-only
    STATUS      current
    DESCRIPTION
        "The transmitted SAPI part of the TCMC trace (15 character)" 
    ::=  { changeServiceDeployProvIfCapEntry 69 }

changeServiceDeployProvIfCapTraceTransmitDapiOduTcmC OBJECT-TYPE
    SYNTAX      Integer32
    MAX-ACCESS  read-only
    STATUS      current
    DESCRIPTION
        "The transmitted DAPI part of the TCMC trace (15 character)" 
    ::=  { changeServiceDeployProvIfCapEntry 70 }

changeServiceDeployProvIfCapTraceTransmitOpspOduTcmC OBJECT-TYPE
    SYNTAX      Integer32
    MAX-ACCESS  read-only
    STATUS      current
    DESCRIPTION
        "The transmitted Operator Specific part of the TCMC trace (32 character)" 
    ::=  { changeServiceDeployProvIfCapEntry 71 }

changeServiceDeployProvIfCapTimModeOduTcmC OBJECT-TYPE
    SYNTAX      TimModeCaps
    MAX-ACCESS  read-only
    STATUS      current
    DESCRIPTION
        "TCM_C Trace Identifier Mismatch (TIM) detection/action for TIM defect." 
    ::=  { changeServiceDeployProvIfCapEntry 72 }

changeServiceDeployProvIfCapChannelProvisioning OBJECT-TYPE
    SYNTAX      FspR7ChannelIdentifierCaps
    MAX-ACCESS  read-only
    STATUS      current
    DESCRIPTION
        "Channel" 
    ::=  { changeServiceDeployProvIfCapEntry 73 }

changeServiceDeployProvIfCapVariableGain OBJECT-TYPE
    SYNTAX      FspR7Unsigned32Caps
    UNITS       "0.1 dB"
    MAX-ACCESS  read-only
    STATUS      current
    DESCRIPTION
        "Variable Gain of EDFA" 
    ::=  { changeServiceDeployProvIfCapEntry 74 }

changeServiceDeployProvIfCapBand OBJECT-TYPE
    SYNTAX      FspR7OpticalBandCaps
    MAX-ACCESS  read-only
    STATUS      current
    DESCRIPTION   "The The optical band of the module."
    ::=  { changeServiceDeployProvIfCapEntry 75 }

changeServiceDeployProvIfCapSigDegThreshold OBJECT-TYPE
    SYNTAX      FspR7Unsigned32Caps
    MAX-ACCESS  read-only
    STATUS      current
    DESCRIPTION
        "Threshold for number of errors (CV or CV+DE) in one second" 
    ::=  { changeServiceDeployProvIfCapEntry 76 }

changeServiceDeployProvIfCapSigDegPeriodIntegration OBJECT-TYPE
    SYNTAX      FspR7Unsigned32Caps
    UNITS       "s"
    MAX-ACCESS  read-only
    STATUS      current
    DESCRIPTION
        "Integration Period for Signal degrade" 
    ::=  { changeServiceDeployProvIfCapEntry 77 }

changeServiceDeployProvIfCapVoaMode OBJECT-TYPE
    SYNTAX      FspR7VoaModeCaps
    MAX-ACCESS  read-only
    STATUS      current
    DESCRIPTION
        "VOA operating mode" 
    ::=  { changeServiceDeployProvIfCapEntry 78 }

changeServiceDeployProvIfCapOpticalSetPoint OBJECT-TYPE
    SYNTAX      FspR7Integer32Caps
    UNITS       "0.1 dBm"
    MAX-ACCESS  read-only
    STATUS      current
    DESCRIPTION
        "Sets the optical power for power equalization in ROADM or for channel power control in OPCM" 
    ::=  { changeServiceDeployProvIfCapEntry 79 }

changeServiceDeployProvIfCapVoaSetpoint OBJECT-TYPE
    SYNTAX      FspR7Unsigned32Caps
    UNITS       "0.1 dB"
    MAX-ACCESS  read-only
    STATUS      current
    DESCRIPTION
        "Sets the optical attenuation of VOA" 
    ::=  { changeServiceDeployProvIfCapEntry 80 }

changeServiceDeployProvIfCapLanAid OBJECT-TYPE
    SYNTAX      Integer32
    MAX-ACCESS  read-only
    STATUS      current
    DESCRIPTION
        "AID of LAN" 
    ::=  { changeServiceDeployProvIfCapEntry 81 }

changeServiceDeployProvIfCapAprHighThreshold OBJECT-TYPE
    SYNTAX      FspR7Unsigned32Caps
    UNITS       "0.1 dBm"
    MAX-ACCESS  read-only
    STATUS      current
    DESCRIPTION
        "Automatic Power Reduction High Threshold" 
    ::=  { changeServiceDeployProvIfCapEntry 82 }

changeServiceDeployProvIfCapPumpPower OBJECT-TYPE
    SYNTAX      FspR7Integer32Caps
    UNITS       "0.2 dBm"
    MAX-ACCESS  read-only
    STATUS      current
    DESCRIPTION
        "Total raman pump power" 
    ::=  { changeServiceDeployProvIfCapEntry 83 }

changeServiceDeployProvIfCapWdmRxChannel OBJECT-TYPE
    SYNTAX      FspR7ChannelIdentifierCaps
    MAX-ACCESS  read-only
    STATUS      current
    DESCRIPTION
        "Configuration of Rx optical channel" 
    ::=  { changeServiceDeployProvIfCapEntry 84 }

changeServiceDeployProvIfCapSigDegThresSonetSection OBJECT-TYPE
    SYNTAX      FspR7BERThresholdSectionCaps
    MAX-ACCESS  read-only
    STATUS      current
    DESCRIPTION
        "Bit-Error-Based Degradation Definition for SONET (standard integration period)" 
    ::=  { changeServiceDeployProvIfCapEntry 85 }

changeServiceDeployProvIfCapSigDegThresSdhSection OBJECT-TYPE
    SYNTAX      FspR7Unsigned32Caps
    UNITS       "%"
    MAX-ACCESS  read-only
    STATUS      current
    DESCRIPTION
        "Block-Error-Based Degradation Definition for SDH (standard integration period).
         Defined as percentage Background Block Errors (30% default) evaluated
         over a defined period (SDPER-RS)." 
    ::=  { changeServiceDeployProvIfCapEntry 86 }

changeServiceDeployProvIfCapSigDegPeriodSdhSection OBJECT-TYPE
    SYNTAX      FspR7Unsigned32Caps
    UNITS       "s"
    MAX-ACCESS  read-only
    STATUS      current
    DESCRIPTION
        "Provisionable Signal Degrade Integration Period for SDH" 
    ::=  { changeServiceDeployProvIfCapEntry 87 }

changeServiceDeployProvIfCapDispersionMode OBJECT-TYPE
    SYNTAX      FspR7DispersionModesCaps
    MAX-ACCESS  read-only
    STATUS      current
    DESCRIPTION
        "Chromatic Dispersion Compensation Mode" 
    ::=  { changeServiceDeployProvIfCapEntry 88 }

changeServiceDeployProvIfCapDispersionSetting OBJECT-TYPE
    SYNTAX      FspR7Integer32Caps
    UNITS       "ps/nm"
    MAX-ACCESS  read-only
    STATUS      current
    DESCRIPTION
        "Chromatic Dispersion Compensation setting on module" 
    ::=  { changeServiceDeployProvIfCapEntry 89 }

changeServiceDeployProvIfCapIpType OBJECT-TYPE
    SYNTAX      FspR7IpTypeCaps
    MAX-ACCESS  read-only
    STATUS      current
    DESCRIPTION
        "Type of IP configuration" 
    ::=  { changeServiceDeployProvIfCapEntry 90 }

changeServiceDeployProvIfCapOffset OBJECT-TYPE
    SYNTAX      FspR7Integer32Caps
    UNITS       "0.1 dB"
    MAX-ACCESS  read-only
    STATUS      current
    DESCRIPTION   "Sets the offset for the mean optical power for power equalization in ROADM"
    ::=  { changeServiceDeployProvIfCapEntry 91 }

changeServiceDeployProvIfCapFunction OBJECT-TYPE
    SYNTAX      FspR7InterfaceFunctionCaps
    MAX-ACCESS  read-only
    STATUS      current
    DESCRIPTION
        "Interface Function" 
    ::=  { changeServiceDeployProvIfCapEntry 92 }

changeServiceDeployProvIfCapFarEndCommunication OBJECT-TYPE
    SYNTAX      FspR7YesNoCaps
    MAX-ACCESS  read-only
    STATUS      current
    DESCRIPTION
        "Used for Optojack plugs; Communication to Far End Plug is observed" 
    ::=  { changeServiceDeployProvIfCapEntry 93 }

changeServiceDeployProvIfCapEqlzAdmin OBJECT-TYPE
    SYNTAX      FspR7EqlzAdminStateCaps
    MAX-ACCESS  read-only
    STATUS      current
    DESCRIPTION   "Scheduled Equalization Administration"
    ::=  { changeServiceDeployProvIfCapEntry 94 }

changeServiceDeployProvIfCapTxOffDelay OBJECT-TYPE
    SYNTAX      FspR7EnableDisableCaps
    MAX-ACCESS  read-only
    STATUS      current
    DESCRIPTION
        "Enable or disable TXOFFHOLD Period for Error Forwarding and LKDO-OFF Consequent Action." 
    ::=  { changeServiceDeployProvIfCapEntry 95 }

changeServiceDeployProvIfCapOpuPayloadType OBJECT-TYPE
    SYNTAX      FspR7OpuPayloadTypeCaps
    MAX-ACCESS  read-only
    STATUS      current
    DESCRIPTION
        "OPU Payload Type Indicator" 
    ::=  { changeServiceDeployProvIfCapEntry 96 }

changeServiceDeployProvIfCapOscOpticalSetpoint OBJECT-TYPE
    SYNTAX      FspR7Integer32Caps
    UNITS       "0.1 dBm"
    MAX-ACCESS  read-only
    STATUS      current
    DESCRIPTION
        "Sets the OSC optical power" 
    ::=  { changeServiceDeployProvIfCapEntry 97 }

changeServiceDeployProvIfCapFiberBrand OBJECT-TYPE
    SYNTAX      FspR7FiberBrandCaps
    MAX-ACCESS  read-only
    STATUS      current
    DESCRIPTION
        "Brand of fiber present in the fiber plant" 
    ::=  { changeServiceDeployProvIfCapEntry 98 }

changeServiceDeployProvIfCapXfpDecisionThres OBJECT-TYPE
    SYNTAX      FspR7XfpDecisionThresCaps
    MAX-ACCESS  read-only
    STATUS      current
    DESCRIPTION
        "XFP Decision threshold setting" 
    ::=  { changeServiceDeployProvIfCapEntry 99 }

changeServiceDeployProvIfCapLaserDelayTimer OBJECT-TYPE
    SYNTAX      FspR7LaserDelayTimerCaps
    MAX-ACCESS  read-only
    STATUS      current
    DESCRIPTION
        "Relevant only when ERRFWD=LSROFF. Enables/disables the
         possibility to delay turning off and on the laser.
         This applies to the case when turning off the laser
         is done as an error forwarding mechanism." 
    ::=  { changeServiceDeployProvIfCapEntry 100 }

changeServiceDeployProvIfCapLaserOffTimer OBJECT-TYPE
    SYNTAX      FspR7Unsigned32Caps
    UNITS       "ms"
    MAX-ACCESS  read-only
    STATUS      current
    DESCRIPTION
        "Delay before laser is swiched off" 
    ::=  { changeServiceDeployProvIfCapEntry 101 }

changeServiceDeployProvIfCapLaserOnTimer OBJECT-TYPE
    SYNTAX      FspR7Unsigned32Caps
    UNITS       "ms"
    MAX-ACCESS  read-only
    STATUS      current
    DESCRIPTION
        "Delay before laser is switched on" 
    ::=  { changeServiceDeployProvIfCapEntry 102 }

changeServiceDeployProvIfCapLaneChannelSetting OBJECT-TYPE
    SYNTAX      FspR7ChannelIdentifierCaps
    MAX-ACCESS  read-only
    STATUS      current
    DESCRIPTION
        "Lane Channel Setting" 
    ::=  { changeServiceDeployProvIfCapEntry 103 }

changeServiceDeployProvIfCapBip OBJECT-TYPE
    SYNTAX      FspR7BipCaps
    MAX-ACCESS  read-only
    STATUS      current
    DESCRIPTION
        "Bit Interleaved Parity" 
    ::=  { changeServiceDeployProvIfCapEntry 104 }

changeServiceDeployProvIfCapCodeGain OBJECT-TYPE
    SYNTAX      FspR7CodeGainCaps
    MAX-ACCESS  read-only
    STATUS      current
    DESCRIPTION
        "Forward Error Correction Coding gain" 
    ::=  { changeServiceDeployProvIfCapEntry 105 }

changeServiceDeployProvIfDefaultsTable  OBJECT-TYPE
    SYNTAX      SEQUENCE OF ChangeServiceDeployProvIfDefaultsEntry
    MAX-ACCESS  not-accessible
    STATUS      current
    DESCRIPTION   ""
    ::=  { facilityDeployProv 42  }

changeServiceDeployProvIfDefaultsEntry OBJECT-TYPE
    SYNTAX      ChangeServiceDeployProvIfDefaultsEntry
    MAX-ACCESS  not-accessible
    STATUS      current
    DESCRIPTION   ""
    INDEX       { entityIndex }
    ::=  { changeServiceDeployProvIfDefaultsTable 1 }

ChangeServiceDeployProvIfDefaultsEntry ::=  SEQUENCE
  { changeServiceDeployProvIfDefaultsRowStatus RowStatus,
    changeServiceDeployProvIfDefaultsForceDestroy FspR7ForcedStatus,
    changeServiceDeployProvIfDefaultsType FspR7InterfaceType,
    changeServiceDeployProvIfDefaultsPayload OtnPayloadType,
    changeServiceDeployProvIfDefaultsBehaviour FspR7PortBehaviour,
    changeServiceDeployProvIfDefaultsTerminationLevel OhTerminationLevel,
    changeServiceDeployProvIfDefaultsAlsMode FspR7AlsMode,
    changeServiceDeployProvIfDefaultsErrorForwarding FspR7ErrorFwdMode,
    changeServiceDeployProvIfDefaultsLaserOffDelayFunction EnableState,
    changeServiceDeployProvIfDefaultsFecType FspR7FecType,
    changeServiceDeployProvIfDefaultsTimingSource SonetTimingSource,
    changeServiceDeployProvIfDefaultsTcmALevel OtnTcmLevel,
    changeServiceDeployProvIfDefaultsTcmBLevel OtnTcmLevel,
    changeServiceDeployProvIfDefaultsSigDegThresSonetLine FspR7BERThreshold,
    changeServiceDeployProvIfDefaultsSigDegThresSdhMs Unsigned32,
    changeServiceDeployProvIfDefaultsSignalDegradePeriod Unsigned32,
    changeServiceDeployProvIfDefaultsAutonegotiation EnableState,
    changeServiceDeployProvIfDefaultsBitrate FspR7Bitrate,
    changeServiceDeployProvIfDefaultsDuplex EthDuplexMode,
    changeServiceDeployProvIfDefaultsFlowControl FspR7FlowControlMode,
    changeServiceDeployProvIfDefaultsOtnStuffing FspR7Stuff,
    changeServiceDeployProvIfDefaultsSigDegThresOtu Integer32,
    changeServiceDeployProvIfDefaultsSigDegPeriodOtu Unsigned32,
    changeServiceDeployProvIfDefaultsSigDegThresOdu Integer32,
    changeServiceDeployProvIfDefaultsSigDegPeriodOdu Unsigned32,
    changeServiceDeployProvIfDefaultsSigDegThresOduTcmA Integer32,
    changeServiceDeployProvIfDefaultsSigDegPeriodOduTcmA Unsigned32,
    changeServiceDeployProvIfDefaultsSigDegThresOduTcmB Integer32,
    changeServiceDeployProvIfDefaultsSigDegPeriodOduTcmB Unsigned32,
    changeServiceDeployProvIfDefaultsTilt Integer32,
    changeServiceDeployProvIfDefaultsGain FspR7Gain,
    changeServiceDeployProvIfDefaultsAdmin FspR7AdminState,
    changeServiceDeployProvIfDefaultsAttenuationGradient Unsigned32,
    changeServiceDeployProvIfDefaultsSigDegThresReceiver Unsigned32,
    changeServiceDeployProvIfDefaultsTcmCLevel OtnTcmLevel,
    changeServiceDeployProvIfDefaultsSigDegThresOduTcmC Integer32,
    changeServiceDeployProvIfDefaultsSigDegPeriodOduTcmC Unsigned32,
    changeServiceDeployProvIfDefaultsDisparityCorrection EnableState,
    changeServiceDeployProvIfDefaultsIpAddr IpAddress,
    changeServiceDeployProvIfDefaultsIpMask IpAddress,
    changeServiceDeployProvIfDefaultsOspf FspR7OspfMode,
    changeServiceDeployProvIfDefaultsMetric Unsigned32,
    changeServiceDeployProvIfDefaultsAreaId IpAddress,
    changeServiceDeployProvIfDefaultsTraceFormSonetSection SonetTraceForm,
    changeServiceDeployProvIfDefaultsTraceExpectedSonetSection OCTET STRING,
    changeServiceDeployProvIfDefaultsTraceTransmitSonetSection OCTET STRING,
    changeServiceDeployProvIfDefaultsTimModeSonetSection TimMode,
    changeServiceDeployProvIfDefaultsTraceExpectedOtu OCTET STRING,
    changeServiceDeployProvIfDefaultsTraceTransmitSapiOtu OCTET STRING,
    changeServiceDeployProvIfDefaultsTraceTransmitDapiOtu OCTET STRING,
    changeServiceDeployProvIfDefaultsTraceTransmitOpspOtu OCTET STRING,
    changeServiceDeployProvIfDefaultsTimModeOtu TimMode,
    changeServiceDeployProvIfDefaultsTraceExpectedOdu OCTET STRING,
    changeServiceDeployProvIfDefaultsTraceTransmitSapiOdu OCTET STRING,
    changeServiceDeployProvIfDefaultsTraceTransmitDapiOdu OCTET STRING,
    changeServiceDeployProvIfDefaultsTraceTransmitOpspOdu OCTET STRING,
    changeServiceDeployProvIfDefaultsTimModeOdu TimMode,
    changeServiceDeployProvIfDefaultsTraceExpectedOduTcmA OCTET STRING,
    changeServiceDeployProvIfDefaultsTraceTransmitSapiOduTcmA OCTET STRING,
    changeServiceDeployProvIfDefaultsTraceTransmitDapiOduTcmA OCTET STRING,
    changeServiceDeployProvIfDefaultsTraceTransmitOpspOduTcmA OCTET STRING,
    changeServiceDeployProvIfDefaultsTimModeOduTcmA TimMode,
    changeServiceDeployProvIfDefaultsTraceExpectedOduTcmB OCTET STRING,
    changeServiceDeployProvIfDefaultsTraceTransmitSapiOduTcmB OCTET STRING,
    changeServiceDeployProvIfDefaultsTraceTransmitDapiOduTcmB OCTET STRING,
    changeServiceDeployProvIfDefaultsTraceTransmitOpspOduTcmB OCTET STRING,
    changeServiceDeployProvIfDefaultsTimModeOduTcmB TimMode,
    changeServiceDeployProvIfDefaultsTraceExpectedOduTcmC OCTET STRING,
    changeServiceDeployProvIfDefaultsTraceTransmitSapiOduTcmC OCTET STRING,
    changeServiceDeployProvIfDefaultsTraceTransmitDapiOduTcmC OCTET STRING,
    changeServiceDeployProvIfDefaultsTraceTransmitOpspOduTcmC OCTET STRING,
    changeServiceDeployProvIfDefaultsTimModeOduTcmC TimMode,
    changeServiceDeployProvIfDefaultsChannelProvisioning FspR7ChannelIdentifier,
    changeServiceDeployProvIfDefaultsVariableGain Unsigned32,
    changeServiceDeployProvIfDefaultsBand FspR7OpticalBand,
    changeServiceDeployProvIfDefaultsSigDegThreshold Unsigned32,
    changeServiceDeployProvIfDefaultsSigDegPeriodIntegration Unsigned32,
    changeServiceDeployProvIfDefaultsVoaMode FspR7VoaMode,
    changeServiceDeployProvIfDefaultsOpticalSetPoint Integer32,
    changeServiceDeployProvIfDefaultsVoaSetpoint Unsigned32,
    changeServiceDeployProvIfDefaultsLanAid EntityIndex,
    changeServiceDeployProvIfDefaultsAprHighThreshold Unsigned32,
    changeServiceDeployProvIfDefaultsPumpPower Integer32,
    changeServiceDeployProvIfDefaultsWdmRxChannel FspR7ChannelIdentifier,
    changeServiceDeployProvIfDefaultsSigDegThresSonetSection FspR7BERThresholdSection,
    changeServiceDeployProvIfDefaultsSigDegThresSdhSection Unsigned32,
    changeServiceDeployProvIfDefaultsSigDegPeriodSdhSection Unsigned32,
    changeServiceDeployProvIfDefaultsDispersionMode FspR7DispersionModes,
    changeServiceDeployProvIfDefaultsDispersionSetting Integer32,
    changeServiceDeployProvIfDefaultsIpType FspR7IpType,
    changeServiceDeployProvIfDefaultsOffset Integer32,
    changeServiceDeployProvIfDefaultsFunction FspR7InterfaceFunction,
    changeServiceDeployProvIfDefaultsFarEndCommunication FspR7YesNo,
    changeServiceDeployProvIfDefaultsEqlzAdmin FspR7EqlzAdminState,
    changeServiceDeployProvIfDefaultsTxOffDelay FspR7EnableDisable,
    changeServiceDeployProvIfDefaultsOpuPayloadType FspR7OpuPayloadType,
    changeServiceDeployProvIfDefaultsOscOpticalSetpoint Integer32,
    changeServiceDeployProvIfDefaultsFiberBrand FspR7FiberBrand,
    changeServiceDeployProvIfDefaultsXfpDecisionThres FspR7XfpDecisionThres,
    changeServiceDeployProvIfDefaultsLaserDelayTimer FspR7LaserDelayTimer,
    changeServiceDeployProvIfDefaultsLaserOffTimer Unsigned32,
    changeServiceDeployProvIfDefaultsLaserOnTimer Unsigned32,
    changeServiceDeployProvIfDefaultsLaneChannelSetting FspR7ChannelIdentifier,
    changeServiceDeployProvIfDefaultsBip FspR7Bip,
    changeServiceDeployProvIfDefaultsCodeGain FspR7CodeGain }

changeServiceDeployProvIfDefaultsRowStatus OBJECT-TYPE
    SYNTAX      RowStatus
    MAX-ACCESS  read-only
    STATUS      current
    DESCRIPTION   "RowStatus"
    ::=  { changeServiceDeployProvIfDefaultsEntry 1 }

changeServiceDeployProvIfDefaultsForceDestroy OBJECT-TYPE
    SYNTAX      FspR7ForcedStatus
    MAX-ACCESS  read-only
    STATUS      current
    DESCRIPTION
        "Forced Destroy" 
    ::=  { changeServiceDeployProvIfDefaultsEntry 2 }

changeServiceDeployProvIfDefaultsType OBJECT-TYPE
    SYNTAX      FspR7InterfaceType
    MAX-ACCESS  read-only
    STATUS      current
    DESCRIPTION   "The TYPE defines the transport service type as wrapper with wrapper layer
         termination OR else as payload"
    ::=  { changeServiceDeployProvIfDefaultsEntry 3 }

changeServiceDeployProvIfDefaultsPayload OBJECT-TYPE
    SYNTAX      OtnPayloadType
    MAX-ACCESS  read-only
    STATUS      current
    DESCRIPTION   "The payload of the interface (inside a transport overhead).
         Relevant e. g. for OTN cards which wrap a payload into an OTU1/2 wrapper."
    ::=  { changeServiceDeployProvIfDefaultsEntry 4 }

changeServiceDeployProvIfDefaultsBehaviour OBJECT-TYPE
    SYNTAX      FspR7PortBehaviour
    MAX-ACCESS  read-only
    STATUS      current
    DESCRIPTION   "The configured behaviour of the interface. If configured as
         a network interface, the interface will use a WDM laser."
    ::=  { changeServiceDeployProvIfDefaultsEntry 5 }

changeServiceDeployProvIfDefaultsTerminationLevel OBJECT-TYPE
    SYNTAX      OhTerminationLevel
    MAX-ACCESS  read-only
    STATUS      current
    DESCRIPTION
        "Highest signal level hardware removes then generates for transmission." 
    ::=  { changeServiceDeployProvIfDefaultsEntry 6 }

changeServiceDeployProvIfDefaultsAlsMode OBJECT-TYPE
    SYNTAX      FspR7AlsMode
    MAX-ACCESS  read-only
    STATUS      current
    DESCRIPTION   "A configuration request for the Automatic Laser Shutdown (ALS)
         function. Refer to FspR7AlsMode Textual Convention for details."
    ::=  { changeServiceDeployProvIfDefaultsEntry 7 }

changeServiceDeployProvIfDefaultsErrorForwarding OBJECT-TYPE
    SYNTAX      FspR7ErrorFwdMode
    MAX-ACCESS  read-only
    STATUS      current
    DESCRIPTION   "A configuration request for the error forwarding
         function. Refer to FspR7ErrorFwdMode Textual Convention for details."
    ::=  { changeServiceDeployProvIfDefaultsEntry 8 }

changeServiceDeployProvIfDefaultsLaserOffDelayFunction OBJECT-TYPE
    SYNTAX      EnableState
    MAX-ACCESS  read-only
    STATUS      current
    DESCRIPTION   "A configuration request for the Laser Off Delay function. This function
         delays turning off the laser as a consequent action to a defect."
    ::=  { changeServiceDeployProvIfDefaultsEntry 9 }

changeServiceDeployProvIfDefaultsFecType OBJECT-TYPE
    SYNTAX      FspR7FecType
    MAX-ACCESS  read-only
    STATUS      current
    DESCRIPTION   "Configuration of FEC type."
    ::=  { changeServiceDeployProvIfDefaultsEntry 10 }

changeServiceDeployProvIfDefaultsTimingSource OBJECT-TYPE
    SYNTAX      SonetTimingSource
    MAX-ACCESS  read-only
    STATUS      current
    DESCRIPTION   "The timing source for this interface.
         - internal: used in stand-alone, point-to-point topologies stand-alone (dedicated fiber operation).
         - loopTiming: e.g. used in point-to-point via SONET network and feeder topologies. The default is
         internal(1)."
    ::=  { changeServiceDeployProvIfDefaultsEntry 11 }

changeServiceDeployProvIfDefaultsTcmALevel OBJECT-TYPE
    SYNTAX      OtnTcmLevel
    MAX-ACCESS  read-only
    STATUS      current
    DESCRIPTION   "Configuration of TCMA level."
    ::=  { changeServiceDeployProvIfDefaultsEntry 12 }

changeServiceDeployProvIfDefaultsTcmBLevel OBJECT-TYPE
    SYNTAX      OtnTcmLevel
    MAX-ACCESS  read-only
    STATUS      current
    DESCRIPTION   "Configuration of TCMB level."
    ::=  { changeServiceDeployProvIfDefaultsEntry 13 }

changeServiceDeployProvIfDefaultsSigDegThresSonetLine OBJECT-TYPE
    SYNTAX      FspR7BERThreshold
    MAX-ACCESS  read-only
    STATUS      current
    DESCRIPTION
        "Bit-Error-Based Degradation Definition for SONET (standard integration period)" 
    ::=  { changeServiceDeployProvIfDefaultsEntry 14 }

changeServiceDeployProvIfDefaultsSigDegThresSdhMs OBJECT-TYPE
    SYNTAX      Unsigned32 (1..100 | 4294967295) 
    UNITS       "%"
    MAX-ACCESS  read-only
    STATUS      current
    DESCRIPTION
        "Block-Error-Based Degradation Definition for SDH (standard integration period).
         Defined as percentage Background Block Errors (30% default) evaluated
         over a defined period (SDPER-RS)." 
    ::=  { changeServiceDeployProvIfDefaultsEntry 15 }

changeServiceDeployProvIfDefaultsSignalDegradePeriod OBJECT-TYPE
    SYNTAX      Unsigned32 (2..10 | 4294967295) 
    UNITS       "s"
    MAX-ACCESS  read-only
    STATUS      current
    DESCRIPTION   "The measurement period in seconds used together with
         the deployProvIfSigDegThresSdhRegSect based on the block error counting method.
         The valid range is 2..10,
         The default being 7."
    ::=  { changeServiceDeployProvIfDefaultsEntry 16 }

changeServiceDeployProvIfDefaultsAutonegotiation OBJECT-TYPE
    SYNTAX      EnableState
    MAX-ACCESS  read-only
    STATUS      current
    DESCRIPTION
        "Auto Negotiation for the data rate" 
    ::=  { changeServiceDeployProvIfDefaultsEntry 17 }

changeServiceDeployProvIfDefaultsBitrate OBJECT-TYPE
    SYNTAX      FspR7Bitrate
    MAX-ACCESS  read-only
    STATUS      current
    DESCRIPTION
        "Provisioned data rate" 
    ::=  { changeServiceDeployProvIfDefaultsEntry 18 }

changeServiceDeployProvIfDefaultsDuplex OBJECT-TYPE
    SYNTAX      EthDuplexMode
    MAX-ACCESS  read-only
    STATUS      current
    DESCRIPTION
        "Duplex Mode (provision), available when Auto Negoiation is Disable (AUTONEG=DISABLE)" 
    ::=  { changeServiceDeployProvIfDefaultsEntry 19 }

changeServiceDeployProvIfDefaultsFlowControl OBJECT-TYPE
    SYNTAX      FspR7FlowControlMode
    MAX-ACCESS  read-only
    STATUS      current
    DESCRIPTION
        "Flow Control mechanism" 
    ::=  { changeServiceDeployProvIfDefaultsEntry 20 }

changeServiceDeployProvIfDefaultsOtnStuffing OBJECT-TYPE
    SYNTAX      FspR7Stuff
    MAX-ACCESS  read-only
    STATUS      current
    DESCRIPTION
        "Indicates if bit/byte stuffing is used in the transport signal." 
    ::=  { changeServiceDeployProvIfDefaultsEntry 21 }

changeServiceDeployProvIfDefaultsSigDegThresOtu OBJECT-TYPE
    SYNTAX      Integer32 (1..100 | -2147483648) 
    UNITS       "%"
    MAX-ACCESS  read-only
    STATUS      current
    DESCRIPTION
        "Background-Block-Error-Based Signal Degradation Definition for OTU" 
    ::=  { changeServiceDeployProvIfDefaultsEntry 22 }

changeServiceDeployProvIfDefaultsSigDegPeriodOtu OBJECT-TYPE
    SYNTAX      Unsigned32 (2..10 | 4294967295) 
    UNITS       "s"
    MAX-ACCESS  read-only
    STATUS      current
    DESCRIPTION
        "Integration Period for Signal degrade" 
    ::=  { changeServiceDeployProvIfDefaultsEntry 23 }

changeServiceDeployProvIfDefaultsSigDegThresOdu OBJECT-TYPE
    SYNTAX      Integer32 (1..100 | -2147483648) 
    UNITS       "%"
    MAX-ACCESS  read-only
    STATUS      current
    DESCRIPTION
        "Background-Block-Error-Based Signal Degradation Definition for ODU" 
    ::=  { changeServiceDeployProvIfDefaultsEntry 24 }

changeServiceDeployProvIfDefaultsSigDegPeriodOdu OBJECT-TYPE
    SYNTAX      Unsigned32 (2..10 | 4294967295) 
    UNITS       "s"
    MAX-ACCESS  read-only
    STATUS      current
    DESCRIPTION
        "Integration Period for Signal degrade" 
    ::=  { changeServiceDeployProvIfDefaultsEntry 25 }

changeServiceDeployProvIfDefaultsSigDegThresOduTcmA OBJECT-TYPE
    SYNTAX      Integer32 (1..100 | -2147483648) 
    UNITS       "%"
    MAX-ACCESS  read-only
    STATUS      current
    DESCRIPTION
        "Background-Block-Error-Based Signal Degradation Definition for TCM-A" 
    ::=  { changeServiceDeployProvIfDefaultsEntry 26 }

changeServiceDeployProvIfDefaultsSigDegPeriodOduTcmA OBJECT-TYPE
    SYNTAX      Unsigned32 (2..10 | 4294967295) 
    UNITS       "s"
    MAX-ACCESS  read-only
    STATUS      current
    DESCRIPTION
        "Integration Period for Signal degrade" 
    ::=  { changeServiceDeployProvIfDefaultsEntry 27 }

changeServiceDeployProvIfDefaultsSigDegThresOduTcmB OBJECT-TYPE
    SYNTAX      Integer32 (1..100 | -2147483648) 
    UNITS       "%"
    MAX-ACCESS  read-only
    STATUS      current
    DESCRIPTION
        "Background-Block-Error-Based Signal Degradation Definition for TCM-B" 
    ::=  { changeServiceDeployProvIfDefaultsEntry 28 }

changeServiceDeployProvIfDefaultsSigDegPeriodOduTcmB OBJECT-TYPE
    SYNTAX      Unsigned32 (2..10 | 4294967295) 
    UNITS       "s"
    MAX-ACCESS  read-only
    STATUS      current
    DESCRIPTION
        "Integration Period of TCMB Signal Segrade" 
    ::=  { changeServiceDeployProvIfDefaultsEntry 29 }

changeServiceDeployProvIfDefaultsTilt OBJECT-TYPE
    SYNTAX      Integer32 (-50..0 | -2147483648) 
    UNITS       "0.1 dB"
    MAX-ACCESS  read-only
    STATUS      current
    DESCRIPTION
        "Change of optical channel power in dB over the complete transmission band" 
    ::=  { changeServiceDeployProvIfDefaultsEntry 30 }

changeServiceDeployProvIfDefaultsGain OBJECT-TYPE
    SYNTAX      FspR7Gain
    MAX-ACCESS  read-only
    STATUS      current
    DESCRIPTION
        "Gain" 
    ::=  { changeServiceDeployProvIfDefaultsEntry 31 }

changeServiceDeployProvIfDefaultsAdmin OBJECT-TYPE
    SYNTAX      FspR7AdminState
    MAX-ACCESS  read-only
    STATUS      current
    DESCRIPTION   "The Adminstrative State."
    ::=  { changeServiceDeployProvIfDefaultsEntry 32 }

changeServiceDeployProvIfDefaultsAttenuationGradient OBJECT-TYPE
    SYNTAX      Unsigned32 (5..990 | 4294967295) 
    UNITS       "0.1 dB/min"
    MAX-ACCESS  read-only
    STATUS      current
    DESCRIPTION   "Attenuation Gradient Threshold on Receive Fiber. Applies to both
         TRMT and RCV directions; but threshold violation is reported for
         each direction separately by the 'tapping' alarms: INTRUDE-RCV
         and INTRUDE-TRMT."
    ::=  { changeServiceDeployProvIfDefaultsEntry 33 }

changeServiceDeployProvIfDefaultsSigDegThresReceiver OBJECT-TYPE
    SYNTAX      Unsigned32 
    UNITS       "0.1 dB"
    MAX-ACCESS  read-only
    STATUS      current
    DESCRIPTION
        "Signal Degrade Threshold on Receiver. Reported as ATTRMT-SDHT to far end." 
    ::=  { changeServiceDeployProvIfDefaultsEntry 34 }

changeServiceDeployProvIfDefaultsTcmCLevel OBJECT-TYPE
    SYNTAX      OtnTcmLevel
    MAX-ACCESS  read-only
    STATUS      current
    DESCRIPTION
        "Activation of Tandem Connection Monitoring Instance C" 
    ::=  { changeServiceDeployProvIfDefaultsEntry 35 }

changeServiceDeployProvIfDefaultsSigDegThresOduTcmC OBJECT-TYPE
    SYNTAX      Integer32 (1..100 | -2147483648) 
    UNITS       "%"
    MAX-ACCESS  read-only
    STATUS      current
    DESCRIPTION
        "Background-Block-Error-Based Signal Degradation Definition for TCM-C" 
    ::=  { changeServiceDeployProvIfDefaultsEntry 36 }

changeServiceDeployProvIfDefaultsSigDegPeriodOduTcmC OBJECT-TYPE
    SYNTAX      Unsigned32 (2..10 | 4294967295) 
    UNITS       "s"
    MAX-ACCESS  read-only
    STATUS      current
    DESCRIPTION
        "Integration Period of TCMC Signal Segrade" 
    ::=  { changeServiceDeployProvIfDefaultsEntry 37 }

changeServiceDeployProvIfDefaultsDisparityCorrection OBJECT-TYPE
    SYNTAX      EnableState
    MAX-ACCESS  read-only
    STATUS      current
    DESCRIPTION
        "Disparity correction" 
    ::=  { changeServiceDeployProvIfDefaultsEntry 38 }

changeServiceDeployProvIfDefaultsIpAddr OBJECT-TYPE
    SYNTAX      IpAddress
    MAX-ACCESS  read-only
    STATUS      current
    DESCRIPTION
        "IP Address assigned to LAN IP Interface" 
    ::=  { changeServiceDeployProvIfDefaultsEntry 39 }

changeServiceDeployProvIfDefaultsIpMask OBJECT-TYPE
    SYNTAX      IpAddress
    MAX-ACCESS  read-only
    STATUS      current
    DESCRIPTION
        "IP MASK assigned to LAN IP Interface" 
    ::=  { changeServiceDeployProvIfDefaultsEntry 40 }

changeServiceDeployProvIfDefaultsOspf OBJECT-TYPE
    SYNTAX      FspR7OspfMode
    MAX-ACCESS  read-only
    STATUS      current
    DESCRIPTION
        "OSPF Routing (Dynamic)" 
    ::=  { changeServiceDeployProvIfDefaultsEntry 41 }

changeServiceDeployProvIfDefaultsMetric OBJECT-TYPE
    SYNTAX      Unsigned32 (0..65535 | 4294967295)
    MAX-ACCESS  read-only
    STATUS      current
    DESCRIPTION
        "Routing Metric" 
    ::=  { changeServiceDeployProvIfDefaultsEntry 42 }

changeServiceDeployProvIfDefaultsAreaId OBJECT-TYPE
    SYNTAX      IpAddress
    MAX-ACCESS  read-only
    STATUS      current
    DESCRIPTION
        "OSPF Area ID for IP Interface" 
    ::=  { changeServiceDeployProvIfDefaultsEntry 43 }

changeServiceDeployProvIfDefaultsTraceFormSonetSection OBJECT-TYPE
    SYNTAX      SonetTraceForm
    MAX-ACCESS  read-only
    STATUS      current
    DESCRIPTION
        "Byte-Length of Trace Compared to Expected" 
    ::=  { changeServiceDeployProvIfDefaultsEntry 44 }

changeServiceDeployProvIfDefaultsTraceExpectedSonetSection OBJECT-TYPE
    SYNTAX      OCTET STRING (SIZE(0..62))
    MAX-ACCESS  read-only
    STATUS      current
    DESCRIPTION
        "Expected Sec/RS trace. NULL TRACE implies that no trace comparison is made." 
    ::=  { changeServiceDeployProvIfDefaultsEntry 45 }

changeServiceDeployProvIfDefaultsTraceTransmitSonetSection OBJECT-TYPE
    SYNTAX      OCTET STRING (SIZE(0..62))
    MAX-ACCESS  read-only
    STATUS      current
    DESCRIPTION
        "Sec/RS Trace to be Transmitted" 
    ::=  { changeServiceDeployProvIfDefaultsEntry 46 }

changeServiceDeployProvIfDefaultsTimModeSonetSection OBJECT-TYPE
    SYNTAX      TimMode
    MAX-ACCESS  read-only
    STATUS      current
    DESCRIPTION
        "SONET Section Trace Identifier Mismatch (TIM) detection/action for TIM defect." 
    ::=  { changeServiceDeployProvIfDefaultsEntry 47 }

changeServiceDeployProvIfDefaultsTraceExpectedOtu OBJECT-TYPE
    SYNTAX      OCTET STRING (SIZE(0..15))
    MAX-ACCESS  read-only
    STATUS      current
    DESCRIPTION   "Expected SAPI part of the OTU trace (15 character).
         NULL TRACE implies that no trace comparison is made."
    ::=  { changeServiceDeployProvIfDefaultsEntry 48 }

changeServiceDeployProvIfDefaultsTraceTransmitSapiOtu OBJECT-TYPE
    SYNTAX      OCTET STRING (SIZE(0..15))
    MAX-ACCESS  read-only
    STATUS      current
    DESCRIPTION
        "The transmitted SAPI part of the OTU trace (15 character)" 
    ::=  { changeServiceDeployProvIfDefaultsEntry 49 }

changeServiceDeployProvIfDefaultsTraceTransmitDapiOtu OBJECT-TYPE
    SYNTAX      OCTET STRING (SIZE(0..15))
    MAX-ACCESS  read-only
    STATUS      current
    DESCRIPTION
        "The transmitted DAPI part of the OTU trace (15 character)" 
    ::=  { changeServiceDeployProvIfDefaultsEntry 50 }

changeServiceDeployProvIfDefaultsTraceTransmitOpspOtu OBJECT-TYPE
    SYNTAX      OCTET STRING (SIZE(0..32))
    MAX-ACCESS  read-only
    STATUS      current
    DESCRIPTION
        "The transmitted Operator Specific part of the OTU trace (32 character)" 
    ::=  { changeServiceDeployProvIfDefaultsEntry 51 }

changeServiceDeployProvIfDefaultsTimModeOtu OBJECT-TYPE
    SYNTAX      TimMode
    MAX-ACCESS  read-only
    STATUS      current
    DESCRIPTION
        "OTU Trace Identifier Mismatch (TIM) detection/action for TIM defect." 
    ::=  { changeServiceDeployProvIfDefaultsEntry 52 }

changeServiceDeployProvIfDefaultsTraceExpectedOdu OBJECT-TYPE
    SYNTAX      OCTET STRING (SIZE(0..15))
    MAX-ACCESS  read-only
    STATUS      current
    DESCRIPTION   "Expected SAPI part of the ODU trace (15 character).
         NULL TRACE implies that no trace comparison is made."
    ::=  { changeServiceDeployProvIfDefaultsEntry 53 }

changeServiceDeployProvIfDefaultsTraceTransmitSapiOdu OBJECT-TYPE
    SYNTAX      OCTET STRING (SIZE(0..15))
    MAX-ACCESS  read-only
    STATUS      current
    DESCRIPTION
        "The transmitted SAPI part of the ODU trace (15 character)" 
    ::=  { changeServiceDeployProvIfDefaultsEntry 54 }

changeServiceDeployProvIfDefaultsTraceTransmitDapiOdu OBJECT-TYPE
    SYNTAX      OCTET STRING (SIZE(0..15))
    MAX-ACCESS  read-only
    STATUS      current
    DESCRIPTION
        "The transmitted DAPI part of the ODU trace (15 character)" 
    ::=  { changeServiceDeployProvIfDefaultsEntry 55 }

changeServiceDeployProvIfDefaultsTraceTransmitOpspOdu OBJECT-TYPE
    SYNTAX      OCTET STRING (SIZE(0..32))
    MAX-ACCESS  read-only
    STATUS      current
    DESCRIPTION
        "The transmitted Operator Specific part of the ODU trace (32 character)" 
    ::=  { changeServiceDeployProvIfDefaultsEntry 56 }

changeServiceDeployProvIfDefaultsTimModeOdu OBJECT-TYPE
    SYNTAX      TimMode
    MAX-ACCESS  read-only
    STATUS      current
    DESCRIPTION
        "Detection of TIM-ODU Condition can be configured" 
    ::=  { changeServiceDeployProvIfDefaultsEntry 57 }

changeServiceDeployProvIfDefaultsTraceExpectedOduTcmA OBJECT-TYPE
    SYNTAX      OCTET STRING (SIZE(0..15))
    MAX-ACCESS  read-only
    STATUS      current
    DESCRIPTION   "Expected SAPI part of the TCMA trace (15 character).
         NULL TRACE-TCM implies that no trace comparison is made."
    ::=  { changeServiceDeployProvIfDefaultsEntry 58 }

changeServiceDeployProvIfDefaultsTraceTransmitSapiOduTcmA OBJECT-TYPE
    SYNTAX      OCTET STRING (SIZE(0..15))
    MAX-ACCESS  read-only
    STATUS      current
    DESCRIPTION
        "The transmitted SAPI part of the TCMA trace (15 character)" 
    ::=  { changeServiceDeployProvIfDefaultsEntry 59 }

changeServiceDeployProvIfDefaultsTraceTransmitDapiOduTcmA OBJECT-TYPE
    SYNTAX      OCTET STRING (SIZE(0..15))
    MAX-ACCESS  read-only
    STATUS      current
    DESCRIPTION
        "The transmitted DAPI part of the TCMA trace (15 character)" 
    ::=  { changeServiceDeployProvIfDefaultsEntry 60 }

changeServiceDeployProvIfDefaultsTraceTransmitOpspOduTcmA OBJECT-TYPE
    SYNTAX      OCTET STRING (SIZE(0..32))
    MAX-ACCESS  read-only
    STATUS      current
    DESCRIPTION
        "The transmitted Operator Specific part of the TCMA trace (32 character)" 
    ::=  { changeServiceDeployProvIfDefaultsEntry 61 }

changeServiceDeployProvIfDefaultsTimModeOduTcmA OBJECT-TYPE
    SYNTAX      TimMode
    MAX-ACCESS  read-only
    STATUS      current
    DESCRIPTION
        "TCM_A Trace Identifier Mismatch (TIM) detection/action for TIM defect." 
    ::=  { changeServiceDeployProvIfDefaultsEntry 62 }

changeServiceDeployProvIfDefaultsTraceExpectedOduTcmB OBJECT-TYPE
    SYNTAX      OCTET STRING (SIZE(0..15))
    MAX-ACCESS  read-only
    STATUS      current
    DESCRIPTION
        "Expected SAPI part of the TCMB trace (15 character). NULL TRACE-TCM implies that no trace comparison is made." 
    ::=  { changeServiceDeployProvIfDefaultsEntry 63 }

changeServiceDeployProvIfDefaultsTraceTransmitSapiOduTcmB OBJECT-TYPE
    SYNTAX      OCTET STRING (SIZE(0..15))
    MAX-ACCESS  read-only
    STATUS      current
    DESCRIPTION
        "The transmitted SAPI part of the TCMB trace (15 character)" 
    ::=  { changeServiceDeployProvIfDefaultsEntry 64 }

changeServiceDeployProvIfDefaultsTraceTransmitDapiOduTcmB OBJECT-TYPE
    SYNTAX      OCTET STRING (SIZE(0..15))
    MAX-ACCESS  read-only
    STATUS      current
    DESCRIPTION
        "The transmitted DAPI part of the TCMB trace (15 character)" 
    ::=  { changeServiceDeployProvIfDefaultsEntry 65 }

changeServiceDeployProvIfDefaultsTraceTransmitOpspOduTcmB OBJECT-TYPE
    SYNTAX      OCTET STRING (SIZE(0..32))
    MAX-ACCESS  read-only
    STATUS      current
    DESCRIPTION
        "The transmitted Operator Specific part of the TCMB trace (32 character)" 
    ::=  { changeServiceDeployProvIfDefaultsEntry 66 }

changeServiceDeployProvIfDefaultsTimModeOduTcmB OBJECT-TYPE
    SYNTAX      TimMode
    MAX-ACCESS  read-only
    STATUS      current
    DESCRIPTION
        "TCM_B Trace Identifier Mismatch (TIM) detection/action for TIM defect." 
    ::=  { changeServiceDeployProvIfDefaultsEntry 67 }

changeServiceDeployProvIfDefaultsTraceExpectedOduTcmC OBJECT-TYPE
    SYNTAX      OCTET STRING (SIZE(0..15))
    MAX-ACCESS  read-only
    STATUS      current
    DESCRIPTION   "Expected SAPI part of the TCMC trace (15 character).
         NULL TRACE-TCM implies that no trace comparison is made."
    ::=  { changeServiceDeployProvIfDefaultsEntry 68 }

changeServiceDeployProvIfDefaultsTraceTransmitSapiOduTcmC OBJECT-TYPE
    SYNTAX      OCTET STRING (SIZE(0..15))
    MAX-ACCESS  read-only
    STATUS      current
    DESCRIPTION
        "The transmitted SAPI part of the TCMC trace (15 character)" 
    ::=  { changeServiceDeployProvIfDefaultsEntry 69 }

changeServiceDeployProvIfDefaultsTraceTransmitDapiOduTcmC OBJECT-TYPE
    SYNTAX      OCTET STRING (SIZE(0..15))
    MAX-ACCESS  read-only
    STATUS      current
    DESCRIPTION
        "The transmitted DAPI part of the TCMC trace (15 character)" 
    ::=  { changeServiceDeployProvIfDefaultsEntry 70 }

changeServiceDeployProvIfDefaultsTraceTransmitOpspOduTcmC OBJECT-TYPE
    SYNTAX      OCTET STRING (SIZE(0..32))
    MAX-ACCESS  read-only
    STATUS      current
    DESCRIPTION
        "The transmitted Operator Specific part of the TCMC trace (32 character)" 
    ::=  { changeServiceDeployProvIfDefaultsEntry 71 }

changeServiceDeployProvIfDefaultsTimModeOduTcmC OBJECT-TYPE
    SYNTAX      TimMode
    MAX-ACCESS  read-only
    STATUS      current
    DESCRIPTION
        "TCM_C Trace Identifier Mismatch (TIM) detection/action for TIM defect." 
    ::=  { changeServiceDeployProvIfDefaultsEntry 72 }

changeServiceDeployProvIfDefaultsChannelProvisioning OBJECT-TYPE
    SYNTAX      FspR7ChannelIdentifier
    MAX-ACCESS  read-only
    STATUS      current
    DESCRIPTION
        "Channel" 
    ::=  { changeServiceDeployProvIfDefaultsEntry 73 }

changeServiceDeployProvIfDefaultsVariableGain OBJECT-TYPE
    SYNTAX      Unsigned32 (0..350 | 4294967295) 
    UNITS       "0.1 dB"
    MAX-ACCESS  read-only
    STATUS      current
    DESCRIPTION
        "Variable Gain of EDFA" 
    ::=  { changeServiceDeployProvIfDefaultsEntry 74 }

changeServiceDeployProvIfDefaultsBand OBJECT-TYPE
    SYNTAX      FspR7OpticalBand
    MAX-ACCESS  read-only
    STATUS      current
    DESCRIPTION   "The The optical band of the module."
    ::=  { changeServiceDeployProvIfDefaultsEntry 75 }

changeServiceDeployProvIfDefaultsSigDegThreshold OBJECT-TYPE
    SYNTAX      Unsigned32 (1..10000 | 4294967295)
    MAX-ACCESS  read-only
    STATUS      current
    DESCRIPTION
        "Threshold for number of errors (CV or CV+DE) in one second" 
    ::=  { changeServiceDeployProvIfDefaultsEntry 76 }

changeServiceDeployProvIfDefaultsSigDegPeriodIntegration OBJECT-TYPE
    SYNTAX      Unsigned32 (1..10 | 4294967295) 
    UNITS       "s"
    MAX-ACCESS  read-only
    STATUS      current
    DESCRIPTION
        "Integration Period for Signal degrade" 
    ::=  { changeServiceDeployProvIfDefaultsEntry 77 }

changeServiceDeployProvIfDefaultsVoaMode OBJECT-TYPE
    SYNTAX      FspR7VoaMode
    MAX-ACCESS  read-only
    STATUS      current
    DESCRIPTION
        "VOA operating mode" 
    ::=  { changeServiceDeployProvIfDefaultsEntry 78 }

changeServiceDeployProvIfDefaultsOpticalSetPoint OBJECT-TYPE
    SYNTAX      Integer32 (-250..100 | -2147483648) 
    UNITS       "0.1 dBm"
    MAX-ACCESS  read-only
    STATUS      current
    DESCRIPTION
        "Sets the optical power for power equalization in ROADM or for channel power control in OPCM" 
    ::=  { changeServiceDeployProvIfDefaultsEntry 79 }

changeServiceDeployProvIfDefaultsVoaSetpoint OBJECT-TYPE
    SYNTAX      Unsigned32 (0..300 | 4294967295) 
    UNITS       "0.1 dB"
    MAX-ACCESS  read-only
    STATUS      current
    DESCRIPTION
        "Sets the optical attenuation of VOA" 
    ::=  { changeServiceDeployProvIfDefaultsEntry 80 }

changeServiceDeployProvIfDefaultsLanAid OBJECT-TYPE
    SYNTAX      EntityIndex
    MAX-ACCESS  read-only
    STATUS      current
    DESCRIPTION
        "AID of LAN" 
    ::=  { changeServiceDeployProvIfDefaultsEntry 81 }

changeServiceDeployProvIfDefaultsAprHighThreshold OBJECT-TYPE
    SYNTAX      Unsigned32 
    UNITS       "0.1 dBm"
    MAX-ACCESS  read-only
    STATUS      current
    DESCRIPTION
        "Automatic Power Reduction High Threshold" 
    ::=  { changeServiceDeployProvIfDefaultsEntry 82 }

changeServiceDeployProvIfDefaultsPumpPower OBJECT-TYPE
    SYNTAX      Integer32 (115..138 | -2147483648) 
    UNITS       "0.2 dBm"
    MAX-ACCESS  read-only
    STATUS      current
    DESCRIPTION
        "Total raman pump power" 
    ::=  { changeServiceDeployProvIfDefaultsEntry 83 }

changeServiceDeployProvIfDefaultsWdmRxChannel OBJECT-TYPE
    SYNTAX      FspR7ChannelIdentifier
    MAX-ACCESS  read-only
    STATUS      current
    DESCRIPTION
        "Configuration of Rx optical channel" 
    ::=  { changeServiceDeployProvIfDefaultsEntry 84 }

changeServiceDeployProvIfDefaultsSigDegThresSonetSection OBJECT-TYPE
    SYNTAX      FspR7BERThresholdSection
    MAX-ACCESS  read-only
    STATUS      current
    DESCRIPTION
        "Bit-Error-Based Degradation Definition for SONET (standard integration period)" 
    ::=  { changeServiceDeployProvIfDefaultsEntry 85 }

changeServiceDeployProvIfDefaultsSigDegThresSdhSection OBJECT-TYPE
    SYNTAX      Unsigned32 (1..100 | 4294967295) 
    UNITS       "%"
    MAX-ACCESS  read-only
    STATUS      current
    DESCRIPTION
        "Block-Error-Based Degradation Definition for SDH (standard integration period).
         Defined as percentage Background Block Errors (30% default) evaluated
         over a defined period (SDPER-RS)." 
    ::=  { changeServiceDeployProvIfDefaultsEntry 86 }

changeServiceDeployProvIfDefaultsSigDegPeriodSdhSection OBJECT-TYPE
    SYNTAX      Unsigned32 (2..10 | 4294967295) 
    UNITS       "s"
    MAX-ACCESS  read-only
    STATUS      current
    DESCRIPTION
        "Provisionable Signal Degrade Integration Period for SDH" 
    ::=  { changeServiceDeployProvIfDefaultsEntry 87 }

changeServiceDeployProvIfDefaultsDispersionMode OBJECT-TYPE
    SYNTAX      FspR7DispersionModes
    MAX-ACCESS  read-only
    STATUS      current
    DESCRIPTION
        "Chromatic Dispersion Compensation Mode" 
    ::=  { changeServiceDeployProvIfDefaultsEntry 88 }

changeServiceDeployProvIfDefaultsDispersionSetting OBJECT-TYPE
    SYNTAX      Integer32 (-50000..50000 | -2147483648) 
    UNITS       "ps/nm"
    MAX-ACCESS  read-only
    STATUS      current
    DESCRIPTION
        "Chromatic Dispersion Compensation setting on module" 
    ::=  { changeServiceDeployProvIfDefaultsEntry 89 }

changeServiceDeployProvIfDefaultsIpType OBJECT-TYPE
    SYNTAX      FspR7IpType
    MAX-ACCESS  read-only
    STATUS      current
    DESCRIPTION
        "Type of IP configuration" 
    ::=  { changeServiceDeployProvIfDefaultsEntry 90 }

changeServiceDeployProvIfDefaultsOffset OBJECT-TYPE
    SYNTAX      Integer32 (10..30 | -2147483648) 
    UNITS       "0.1 dB"
    MAX-ACCESS  read-only
    STATUS      current
    DESCRIPTION   "Sets the offset for the mean optical power for power equalization in ROADM"
    ::=  { changeServiceDeployProvIfDefaultsEntry 91 }

changeServiceDeployProvIfDefaultsFunction OBJECT-TYPE
    SYNTAX      FspR7InterfaceFunction
    MAX-ACCESS  read-only
    STATUS      current
    DESCRIPTION
        "Interface Function" 
    ::=  { changeServiceDeployProvIfDefaultsEntry 92 }

changeServiceDeployProvIfDefaultsFarEndCommunication OBJECT-TYPE
    SYNTAX      FspR7YesNo
    MAX-ACCESS  read-only
    STATUS      current
    DESCRIPTION
        "Used for Optojack plugs; Communication to Far End Plug is observed" 
    ::=  { changeServiceDeployProvIfDefaultsEntry 93 }

changeServiceDeployProvIfDefaultsEqlzAdmin OBJECT-TYPE
    SYNTAX      FspR7EqlzAdminState
    MAX-ACCESS  read-only
    STATUS      current
    DESCRIPTION   "Scheduled Equalization Administration"
    ::=  { changeServiceDeployProvIfDefaultsEntry 94 }

changeServiceDeployProvIfDefaultsTxOffDelay OBJECT-TYPE
    SYNTAX      FspR7EnableDisable
    MAX-ACCESS  read-only
    STATUS      current
    DESCRIPTION
        "Enable or disable TXOFFHOLD Period for Error Forwarding and LKDO-OFF Consequent Action." 
    ::=  { changeServiceDeployProvIfDefaultsEntry 95 }

changeServiceDeployProvIfDefaultsOpuPayloadType OBJECT-TYPE
    SYNTAX      FspR7OpuPayloadType
    MAX-ACCESS  read-only
    STATUS      current
    DESCRIPTION
        "OPU Payload Type Indicator" 
    ::=  { changeServiceDeployProvIfDefaultsEntry 96 }

changeServiceDeployProvIfDefaultsOscOpticalSetpoint OBJECT-TYPE
    SYNTAX      Integer32 (-250..50 | -2147483648) 
    UNITS       "0.1 dBm"
    MAX-ACCESS  read-only
    STATUS      current
    DESCRIPTION
        "Sets the OSC optical power" 
    ::=  { changeServiceDeployProvIfDefaultsEntry 97 }

changeServiceDeployProvIfDefaultsFiberBrand OBJECT-TYPE
    SYNTAX      FspR7FiberBrand
    MAX-ACCESS  read-only
    STATUS      current
    DESCRIPTION
        "Brand of fiber present in the fiber plant" 
    ::=  { changeServiceDeployProvIfDefaultsEntry 98 }

changeServiceDeployProvIfDefaultsXfpDecisionThres OBJECT-TYPE
    SYNTAX      FspR7XfpDecisionThres
    MAX-ACCESS  read-only
    STATUS      current
    DESCRIPTION
        "XFP Decision threshold setting" 
    ::=  { changeServiceDeployProvIfDefaultsEntry 99 }

changeServiceDeployProvIfDefaultsLaserDelayTimer OBJECT-TYPE
    SYNTAX      FspR7LaserDelayTimer
    MAX-ACCESS  read-only
    STATUS      current
    DESCRIPTION
        "Relevant only when ERRFWD=LSROFF. Enables/disables the
         possibility to delay turning off and on the laser.
         This applies to the case when turning off the laser
         is done as an error forwarding mechanism." 
    ::=  { changeServiceDeployProvIfDefaultsEntry 100 }

changeServiceDeployProvIfDefaultsLaserOffTimer OBJECT-TYPE
    SYNTAX      Unsigned32 (1..1000 | 4294967295) 
    UNITS       "ms"
    MAX-ACCESS  read-only
    STATUS      current
    DESCRIPTION
        "Delay before laser is swiched off" 
    ::=  { changeServiceDeployProvIfDefaultsEntry 101 }

changeServiceDeployProvIfDefaultsLaserOnTimer OBJECT-TYPE
    SYNTAX      Unsigned32 (1..1000 | 4294967295) 
    UNITS       "ms"
    MAX-ACCESS  read-only
    STATUS      current
    DESCRIPTION
        "Delay before laser is switched on" 
    ::=  { changeServiceDeployProvIfDefaultsEntry 102 }

changeServiceDeployProvIfDefaultsLaneChannelSetting OBJECT-TYPE
    SYNTAX      FspR7ChannelIdentifier
    MAX-ACCESS  read-only
    STATUS      current
    DESCRIPTION
        "Lane Channel Setting" 
    ::=  { changeServiceDeployProvIfDefaultsEntry 103 }

changeServiceDeployProvIfDefaultsBip OBJECT-TYPE
    SYNTAX      FspR7Bip
    MAX-ACCESS  read-only
    STATUS      current
    DESCRIPTION
        "Bit Interleaved Parity" 
    ::=  { changeServiceDeployProvIfDefaultsEntry 104 }

changeServiceDeployProvIfDefaultsCodeGain OBJECT-TYPE
    SYNTAX      FspR7CodeGain
    MAX-ACCESS  read-only
    STATUS      current
    DESCRIPTION
        "Forward Error Correction Coding gain" 
    ::=  { changeServiceDeployProvIfDefaultsEntry 105 }

deployProvOpticalLinkTable OBJECT-TYPE
    SYNTAX      SEQUENCE OF DeployProvOpticalLinkEntry
    MAX-ACCESS  not-accessible
    STATUS      current
    DESCRIPTION   ""
    ::=  { facilityDeployProv 43 }

deployProvOpticalLinkEntry OBJECT-TYPE
    SYNTAX      DeployProvOpticalLinkEntry
    MAX-ACCESS  not-accessible
    STATUS      current
    DESCRIPTION   ""
    INDEX       {
                  entityIndex
                }
    ::=  { deployProvOpticalLinkTable 1 }

DeployProvOpticalLinkEntry ::=  SEQUENCE
  { deployProvOpticalLinkRowStatus RowStatus,
    deployProvOpticalLinkTxLineAttenuation Integer32,
    deployProvOpticalLinkRxLineAttenuation Integer32,
    deployProvOpticalLinkFarEndLocation SnmpAdminString }

deployProvOpticalLinkRowStatus OBJECT-TYPE
    SYNTAX      RowStatus
    MAX-ACCESS  read-write
    STATUS      current
    DESCRIPTION   "RowStatus"
    ::=  { deployProvOpticalLinkEntry 1 }

deployProvOpticalLinkTxLineAttenuation OBJECT-TYPE
    SYNTAX      Integer32 
    UNITS       "0.1 dB"
    MAX-ACCESS  read-write
    STATUS      current
    DESCRIPTION   "The Attenuation (in 0.1 dB) on line connected to
         transmitter of this interface. If there is loss of signal
         then line attenuation is -65535. The value -255 will be
         returned if the value isn't available."
    ::=  { deployProvOpticalLinkEntry 2 }

deployProvOpticalLinkRxLineAttenuation OBJECT-TYPE
    SYNTAX      Integer32 
    UNITS       "0.1 dB"
    MAX-ACCESS  read-write
    STATUS      current
    DESCRIPTION   "The Attenuation (in 0.1 dB) on line connected to receiver
         of this interface. If there is loss of signal then ine
         attenuation is -65535. The value -255 will be returned if
         the value isn't available."
    ::=  { deployProvOpticalLinkEntry 3 }

deployProvOpticalLinkFarEndLocation OBJECT-TYPE
    SYNTAX      SnmpAdminString
    MAX-ACCESS  read-write
    STATUS      current
    DESCRIPTION   ""
    ::=  { deployProvOpticalLinkEntry 4 }

deployProvOpticalLinkCapTable OBJECT-TYPE
    SYNTAX      SEQUENCE OF DeployProvOpticalLinkCapEntry
    MAX-ACCESS  not-accessible
    STATUS      current
    DESCRIPTION   ""
    ::=  { facilityDeployProv 44  }

deployProvOpticalLinkCapEntry OBJECT-TYPE
    SYNTAX      DeployProvOpticalLinkCapEntry
    MAX-ACCESS  not-accessible
    STATUS      current
    DESCRIPTION   ""
    INDEX       { entityIndex }
    ::=  { deployProvOpticalLinkCapTable 1 }

DeployProvOpticalLinkCapEntry ::=  SEQUENCE
  { deployProvOpticalLinkCapRowStatus FspR7RowStatusCaps,
    deployProvOpticalLinkCapTxLineAttenuation FspR7Integer32Caps,
    deployProvOpticalLinkCapRxLineAttenuation FspR7Integer32Caps,
    deployProvOpticalLinkCapFarEndLocation Integer32 }

deployProvOpticalLinkCapRowStatus OBJECT-TYPE
    SYNTAX      FspR7RowStatusCaps
    MAX-ACCESS  read-only
    STATUS      current
    DESCRIPTION   "RowStatus"
    ::=  { deployProvOpticalLinkCapEntry 1 }

deployProvOpticalLinkCapTxLineAttenuation OBJECT-TYPE
    SYNTAX      FspR7Integer32Caps
    UNITS       "0.1 dB"
    MAX-ACCESS  read-only
    STATUS      current
    DESCRIPTION   "The Attenuation (in 0.1 dB) on line connected to
         transmitter of this interface. If there is loss of signal
         then line attenuation is -65535. The value -255 will be
         returned if the value isn't available."
    ::=  { deployProvOpticalLinkCapEntry 2 }

deployProvOpticalLinkCapRxLineAttenuation OBJECT-TYPE
    SYNTAX      FspR7Integer32Caps
    UNITS       "0.1 dB"
    MAX-ACCESS  read-only
    STATUS      current
    DESCRIPTION   "The Attenuation (in 0.1 dB) on line connected to receiver
         of this interface. If there is loss of signal then ine
         attenuation is -65535. The value -255 will be returned if
         the value isn't available."
    ::=  { deployProvOpticalLinkCapEntry 3 }

deployProvOpticalLinkCapFarEndLocation OBJECT-TYPE
    SYNTAX      Integer32
    MAX-ACCESS  read-only
    STATUS      current
    DESCRIPTION   ""
    ::=  { deployProvOpticalLinkCapEntry 4 }

deployProvOpticalLinkDefaultsTable  OBJECT-TYPE
    SYNTAX      SEQUENCE OF DeployProvOpticalLinkDefaultsEntry
    MAX-ACCESS  not-accessible
    STATUS      current
    DESCRIPTION   ""
    ::=  { facilityDeployProv 45  }

deployProvOpticalLinkDefaultsEntry OBJECT-TYPE
    SYNTAX      DeployProvOpticalLinkDefaultsEntry
    MAX-ACCESS  not-accessible
    STATUS      current
    DESCRIPTION   ""
    INDEX       { entityIndex }
    ::=  { deployProvOpticalLinkDefaultsTable 1 }

DeployProvOpticalLinkDefaultsEntry ::=  SEQUENCE
  { deployProvOpticalLinkDefaultsRowStatus RowStatus,
    deployProvOpticalLinkDefaultsTxLineAttenuation Integer32,
    deployProvOpticalLinkDefaultsRxLineAttenuation Integer32,
    deployProvOpticalLinkDefaultsFarEndLocation SnmpAdminString }

deployProvOpticalLinkDefaultsRowStatus OBJECT-TYPE
    SYNTAX      RowStatus
    MAX-ACCESS  read-only
    STATUS      current
    DESCRIPTION   "RowStatus"
    ::=  { deployProvOpticalLinkDefaultsEntry 1 }

deployProvOpticalLinkDefaultsTxLineAttenuation OBJECT-TYPE
    SYNTAX      Integer32 
    UNITS       "0.1 dB"
    MAX-ACCESS  read-only
    STATUS      current
    DESCRIPTION   "The Attenuation (in 0.1 dB) on line connected to
         transmitter of this interface. If there is loss of signal
         then line attenuation is -65535. The value -255 will be
         returned if the value isn't available."
    ::=  { deployProvOpticalLinkDefaultsEntry 2 }

deployProvOpticalLinkDefaultsRxLineAttenuation OBJECT-TYPE
    SYNTAX      Integer32 
    UNITS       "0.1 dB"
    MAX-ACCESS  read-only
    STATUS      current
    DESCRIPTION   "The Attenuation (in 0.1 dB) on line connected to receiver
         of this interface. If there is loss of signal then ine
         attenuation is -65535. The value -255 will be returned if
         the value isn't available."
    ::=  { deployProvOpticalLinkDefaultsEntry 3 }

deployProvOpticalLinkDefaultsFarEndLocation OBJECT-TYPE
    SYNTAX      SnmpAdminString
    MAX-ACCESS  read-only
    STATUS      current
    DESCRIPTION   ""
    ::=  { deployProvOpticalLinkDefaultsEntry 4 }

deployProvVirtualOpticalChannelTable OBJECT-TYPE
    SYNTAX      SEQUENCE OF DeployProvVirtualOpticalChannelEntry
    MAX-ACCESS  not-accessible
    STATUS      current
    DESCRIPTION   ""
    ::=  { facilityDeployProv 46 }

deployProvVirtualOpticalChannelEntry OBJECT-TYPE
    SYNTAX      DeployProvVirtualOpticalChannelEntry
    MAX-ACCESS  not-accessible
    STATUS      current
    DESCRIPTION   ""
    INDEX       {
                  entityIndex
                }
    ::=  { deployProvVirtualOpticalChannelTable 1 }

DeployProvVirtualOpticalChannelEntry ::=  SEQUENCE
  { deployProvVirtualOpticalChannelRowStatus RowStatus,
    deployProvVirtualOpticalChannelAlias SnmpAdminString }

deployProvVirtualOpticalChannelRowStatus OBJECT-TYPE
    SYNTAX      RowStatus
    MAX-ACCESS  read-write
    STATUS      current
    DESCRIPTION   "RowStatus"
    ::=  { deployProvVirtualOpticalChannelEntry 1 }

deployProvVirtualOpticalChannelAlias OBJECT-TYPE
    SYNTAX      SnmpAdminString
    MAX-ACCESS  read-write
    STATUS      current
    DESCRIPTION
        "User Applied Descriptor" 
    ::=  { deployProvVirtualOpticalChannelEntry 2 }

deployProvVirtualOpticalChannelCapTable OBJECT-TYPE
    SYNTAX      SEQUENCE OF DeployProvVirtualOpticalChannelCapEntry
    MAX-ACCESS  not-accessible
    STATUS      current
    DESCRIPTION   ""
    ::=  { facilityDeployProv 47  }

deployProvVirtualOpticalChannelCapEntry OBJECT-TYPE
    SYNTAX      DeployProvVirtualOpticalChannelCapEntry
    MAX-ACCESS  not-accessible
    STATUS      current
    DESCRIPTION   ""
    INDEX       { entityIndex }
    ::=  { deployProvVirtualOpticalChannelCapTable 1 }

DeployProvVirtualOpticalChannelCapEntry ::=  SEQUENCE
  { deployProvVirtualOpticalChannelCapRowStatus FspR7RowStatusCaps,
    deployProvVirtualOpticalChannelCapAlias Integer32 }

deployProvVirtualOpticalChannelCapRowStatus OBJECT-TYPE
    SYNTAX      FspR7RowStatusCaps
    MAX-ACCESS  read-only
    STATUS      current
    DESCRIPTION   "RowStatus"
    ::=  { deployProvVirtualOpticalChannelCapEntry 1 }

deployProvVirtualOpticalChannelCapAlias OBJECT-TYPE
    SYNTAX      Integer32
    MAX-ACCESS  read-only
    STATUS      current
    DESCRIPTION
        "User Applied Descriptor" 
    ::=  { deployProvVirtualOpticalChannelCapEntry 2 }

deployProvVirtualOpticalChannelDefaultsTable  OBJECT-TYPE
    SYNTAX      SEQUENCE OF DeployProvVirtualOpticalChannelDefaultsEntry
    MAX-ACCESS  not-accessible
    STATUS      current
    DESCRIPTION   ""
    ::=  { facilityDeployProv 48  }

deployProvVirtualOpticalChannelDefaultsEntry OBJECT-TYPE
    SYNTAX      DeployProvVirtualOpticalChannelDefaultsEntry
    MAX-ACCESS  not-accessible
    STATUS      current
    DESCRIPTION   ""
    INDEX       { entityIndex }
    ::=  { deployProvVirtualOpticalChannelDefaultsTable 1 }

DeployProvVirtualOpticalChannelDefaultsEntry ::=  SEQUENCE
  { deployProvVirtualOpticalChannelDefaultsRowStatus RowStatus,
    deployProvVirtualOpticalChannelDefaultsAlias SnmpAdminString }

deployProvVirtualOpticalChannelDefaultsRowStatus OBJECT-TYPE
    SYNTAX      RowStatus
    MAX-ACCESS  read-only
    STATUS      current
    DESCRIPTION   "RowStatus"
    ::=  { deployProvVirtualOpticalChannelDefaultsEntry 1 }

deployProvVirtualOpticalChannelDefaultsAlias OBJECT-TYPE
    SYNTAX      SnmpAdminString
    MAX-ACCESS  read-only
    STATUS      current
    DESCRIPTION
        "User Applied Descriptor" 
    ::=  { deployProvVirtualOpticalChannelDefaultsEntry 2 }

deployProvLogicalIfTable OBJECT-TYPE
    SYNTAX      SEQUENCE OF DeployProvLogicalIfEntry
    MAX-ACCESS  not-accessible
    STATUS      current
    DESCRIPTION   ""
    ::=  { facilityDeployProv 49 }

deployProvLogicalIfEntry OBJECT-TYPE
    SYNTAX      DeployProvLogicalIfEntry
    MAX-ACCESS  not-accessible
    STATUS      current
    DESCRIPTION   ""
    INDEX       {
                  entityIndex
                }
    ::=  { deployProvLogicalIfTable 1 }

DeployProvLogicalIfEntry ::=  SEQUENCE
  { deployProvLogicalIfRowStatus RowStatus,
    deployProvLogicalIfFacilityType FspR7InterfaceType,
    deployProvLogicalIfAlias SnmpAdminString,
    deployProvLogicalIfLanLinkAid EntityIndex,
    deployProvLogicalIfAreaId IpAddress,
    deployProvLogicalIfMetric Unsigned32,
    deployProvLogicalIfHelloInterval Unsigned32,
    deployProvLogicalIfDeadInterval Unsigned32,
    deployProvLogicalIfPrio Unsigned32,
    deployProvLogicalIfRetransmitInterval Unsigned32,
    deployProvLogicalIfAuthType FspR7CpAuthType,
    deployProvLogicalIfAuthString SnmpAdminString,
    deployProvLogicalIfIpType FspR7IpType,
    deployProvLogicalIfIpAddr IpAddress,
    deployProvLogicalIfIpAddrMask IpAddress,
    deployProvLogicalIfAdmin FspR7AdminState,
    deployProvLogicalIfDcnAid EntityIndex,
    deployProvLogicalIfOspf FspR7OspfMode,
    deployProvLogicalIfEncapsulation FspR7CpEncapsulation,
    deployProvLogicalIfPushedNendIpHeader IpAddress,
    deployProvLogicalIfPushedFarEndIpHeader IpAddress,
    deployProvLogicalIfTimeToLive Unsigned32,
    deployProvLogicalIfLanLinkAidString SnmpAdminString,
    deployProvLogicalIfDcnAidString SnmpAdminString,
    deployProvLogicalIfIPv6 SnmpAdminString,
    deployProvLogicalIfIPv6PrefixLen Unsigned32,
    deployProvLogicalIfIpMode FspR7IpMode }

deployProvLogicalIfRowStatus OBJECT-TYPE
    SYNTAX      RowStatus
    MAX-ACCESS  read-write
    STATUS      current
    DESCRIPTION
        "RowStatus" 
    ::=  { deployProvLogicalIfEntry 1 }

deployProvLogicalIfFacilityType OBJECT-TYPE
    SYNTAX      FspR7InterfaceType
    MAX-ACCESS  read-write
    STATUS      current
    DESCRIPTION   "Facility Type."
    ::=  { deployProvLogicalIfEntry 2 }

deployProvLogicalIfAlias OBJECT-TYPE
    SYNTAX      SnmpAdminString
    MAX-ACCESS  read-write
    STATUS      current
    DESCRIPTION   "Alias."
    ::=  { deployProvLogicalIfEntry 3 }

deployProvLogicalIfLanLinkAid OBJECT-TYPE
    SYNTAX      EntityIndex
    MAX-ACCESS  read-write
    STATUS      current
    DESCRIPTION   ""
    ::=  { deployProvLogicalIfEntry 4 }

deployProvLogicalIfAreaId OBJECT-TYPE
    SYNTAX      IpAddress
    MAX-ACCESS  read-write
    STATUS      current
    DESCRIPTION
        "OSPF Area ID for IP Interface" 
    ::=  { deployProvLogicalIfEntry 5 }

deployProvLogicalIfMetric OBJECT-TYPE
    SYNTAX      Unsigned32 (0..65535 | 4294967295)
    MAX-ACCESS  read-write
    STATUS      current
    DESCRIPTION
        "Routing Metric" 
    ::=  { deployProvLogicalIfEntry 6 }

deployProvLogicalIfHelloInterval OBJECT-TYPE
    SYNTAX      Unsigned32 (1..65535 | 4294967295) 
    UNITS       "s"
    MAX-ACCESS  read-write
    STATUS      current
    DESCRIPTION
        "Hello Interval" 
    ::=  { deployProvLogicalIfEntry 7 }

deployProvLogicalIfDeadInterval OBJECT-TYPE
    SYNTAX      Unsigned32 (1..65535 | 4294967295) 
    UNITS       "s"
    MAX-ACCESS  read-write
    STATUS      current
    DESCRIPTION
        "Dead Interval" 
    ::=  { deployProvLogicalIfEntry 8 }

deployProvLogicalIfPrio OBJECT-TYPE
    SYNTAX      Unsigned32 (0..255 | 4294967295)
    MAX-ACCESS  read-write
    STATUS      current
    DESCRIPTION
        "Priority" 
    ::=  { deployProvLogicalIfEntry 9 }

deployProvLogicalIfRetransmitInterval OBJECT-TYPE
    SYNTAX      Unsigned32 (0..3600 | 4294967295) 
    UNITS       "s"
    MAX-ACCESS  read-write
    STATUS      current
    DESCRIPTION
        "Retransmit Interval" 
    ::=  { deployProvLogicalIfEntry 10 }

deployProvLogicalIfAuthType OBJECT-TYPE
    SYNTAX      FspR7CpAuthType
    MAX-ACCESS  read-write
    STATUS      current
    DESCRIPTION
        "OSPF Authentication Type" 
    ::=  { deployProvLogicalIfEntry 11 }

deployProvLogicalIfAuthString OBJECT-TYPE
    SYNTAX      SnmpAdminString
    MAX-ACCESS  read-write
    STATUS      current
    DESCRIPTION
        "OSPF Authentication Key/String depending on Authentication Type" 
    ::=  { deployProvLogicalIfEntry 12 }

deployProvLogicalIfIpType OBJECT-TYPE
    SYNTAX      FspR7IpType
    MAX-ACCESS  read-write
    STATUS      current
    DESCRIPTION
        "Type of IP configuration" 
    ::=  { deployProvLogicalIfEntry 13 }

deployProvLogicalIfIpAddr OBJECT-TYPE
    SYNTAX      IpAddress
    MAX-ACCESS  read-write
    STATUS      current
    DESCRIPTION
        "IP Address assigned to LAN IP Interface" 
    ::=  { deployProvLogicalIfEntry 14 }

deployProvLogicalIfIpAddrMask OBJECT-TYPE
    SYNTAX      IpAddress
    MAX-ACCESS  read-write
    STATUS      current
    DESCRIPTION
        "IP MASK assigned to LAN IP Interface" 
    ::=  { deployProvLogicalIfEntry 15 }

deployProvLogicalIfAdmin OBJECT-TYPE
    SYNTAX      FspR7AdminState
    MAX-ACCESS  read-write
    STATUS      current
    DESCRIPTION
        "Administrative State is displayed in the GUI and Craft. Transition to Unassigend requires the entity to be deleted." 
    ::=  { deployProvLogicalIfEntry 16 }

deployProvLogicalIfDcnAid OBJECT-TYPE
    SYNTAX      EntityIndex
    MAX-ACCESS  read-write
    STATUS      current
    DESCRIPTION
        "Supporting DCN Facility AID" 
    ::=  { deployProvLogicalIfEntry 17 }

deployProvLogicalIfOspf OBJECT-TYPE
    SYNTAX      FspR7OspfMode
    MAX-ACCESS  read-write
    STATUS      current
    DESCRIPTION
        "OSPF Routing (Dynamic)" 
    ::=  { deployProvLogicalIfEntry 18 }

deployProvLogicalIfEncapsulation OBJECT-TYPE
    SYNTAX      FspR7CpEncapsulation
    MAX-ACCESS  read-write
    STATUS      current
    DESCRIPTION
        "Encapsulation" 
    ::=  { deployProvLogicalIfEntry 19 }

deployProvLogicalIfPushedNendIpHeader OBJECT-TYPE
    SYNTAX      IpAddress
    MAX-ACCESS  read-write
    STATUS      current
    DESCRIPTION
        "Pushed Near End IP address in encapsulating header" 
    ::=  { deployProvLogicalIfEntry 20 }

deployProvLogicalIfPushedFarEndIpHeader OBJECT-TYPE
    SYNTAX      IpAddress
    MAX-ACCESS  read-write
    STATUS      current
    DESCRIPTION
        "Pushed Far End IP address in encapsulating header" 
    ::=  { deployProvLogicalIfEntry 21 }

deployProvLogicalIfTimeToLive OBJECT-TYPE
    SYNTAX      Unsigned32 (1..255 | 4294967295)
    MAX-ACCESS  read-write
    STATUS      current
    DESCRIPTION
        "Time to Live" 
    ::=  { deployProvLogicalIfEntry 22 }

deployProvLogicalIfLanLinkAidString OBJECT-TYPE
    SYNTAX      SnmpAdminString
    MAX-ACCESS  read-write
    STATUS      current
    DESCRIPTION   ""
    ::=  { deployProvLogicalIfEntry 23 }

deployProvLogicalIfDcnAidString OBJECT-TYPE
    SYNTAX      SnmpAdminString
    MAX-ACCESS  read-write
    STATUS      current
    DESCRIPTION
        "Supporting DCN Facility AID" 
    ::=  { deployProvLogicalIfEntry 24 }

deployProvLogicalIfIPv6 OBJECT-TYPE
    SYNTAX      SnmpAdminString
    MAX-ACCESS  read-write
    STATUS      current
    DESCRIPTION
        "IPv6 Address" 
    ::=  { deployProvLogicalIfEntry 25 }

deployProvLogicalIfIPv6PrefixLen OBJECT-TYPE
    SYNTAX      Unsigned32 (0..128 | 4294967295)
    MAX-ACCESS  read-write
    STATUS      current
    DESCRIPTION
        "IPv6 Subnet Prefix Length" 
    ::=  { deployProvLogicalIfEntry 26 }

deployProvLogicalIfIpMode OBJECT-TYPE
    SYNTAX      FspR7IpMode
    MAX-ACCESS  read-write
    STATUS      current
    DESCRIPTION
        "IP Mode of Operation either IPv4 only or IPv4 and IPv6. When operation supports IPv6, it is used for addresses external to the network." 
    ::=  { deployProvLogicalIfEntry 27 }

deployProvLogicalIfCapTable OBJECT-TYPE
    SYNTAX      SEQUENCE OF DeployProvLogicalIfCapEntry
    MAX-ACCESS  not-accessible
    STATUS      current
    DESCRIPTION   ""
    ::=  { facilityDeployProv 50  }

deployProvLogicalIfCapEntry OBJECT-TYPE
    SYNTAX      DeployProvLogicalIfCapEntry
    MAX-ACCESS  not-accessible
    STATUS      current
    DESCRIPTION   ""
    INDEX       { entityIndex }
    ::=  { deployProvLogicalIfCapTable 1 }

DeployProvLogicalIfCapEntry ::=  SEQUENCE
  { deployProvLogicalIfCapRowStatus FspR7RowStatusCaps,
    deployProvLogicalIfCapFacilityType FspR7InterfaceTypeCaps,
    deployProvLogicalIfCapAlias Integer32,
    deployProvLogicalIfCapLanLinkAid Integer32,
    deployProvLogicalIfCapAreaId FspR7YesNo,
    deployProvLogicalIfCapMetric FspR7Unsigned32Caps,
    deployProvLogicalIfCapHelloInterval FspR7Unsigned32Caps,
    deployProvLogicalIfCapDeadInterval FspR7Unsigned32Caps,
    deployProvLogicalIfCapPrio FspR7Unsigned32Caps,
    deployProvLogicalIfCapRetransmitInterval FspR7Unsigned32Caps,
    deployProvLogicalIfCapAuthType FspR7CpAuthTypeCaps,
    deployProvLogicalIfCapAuthString Integer32,
    deployProvLogicalIfCapIpType FspR7IpTypeCaps,
    deployProvLogicalIfCapIpAddr FspR7YesNo,
    deployProvLogicalIfCapIpAddrMask FspR7YesNo,
    deployProvLogicalIfCapAdmin FspR7AdminStateCaps,
    deployProvLogicalIfCapDcnAid Integer32,
    deployProvLogicalIfCapOspf FspR7OspfModeCaps,
    deployProvLogicalIfCapEncapsulation FspR7CpEncapsulationCaps,
    deployProvLogicalIfCapPushedNendIpHeader FspR7YesNo,
    deployProvLogicalIfCapPushedFarEndIpHeader FspR7YesNo,
    deployProvLogicalIfCapTimeToLive FspR7Unsigned32Caps,
    deployProvLogicalIfCapLanLinkAidString Integer32,
    deployProvLogicalIfCapDcnAidString FspR7SnmpLongString,
    deployProvLogicalIfCapIPv6 Integer32,
    deployProvLogicalIfCapIPv6PrefixLen FspR7Unsigned32Caps,
    deployProvLogicalIfCapIpMode FspR7IpModeCaps }

deployProvLogicalIfCapRowStatus OBJECT-TYPE
    SYNTAX      FspR7RowStatusCaps
    MAX-ACCESS  read-only
    STATUS      current
    DESCRIPTION
        "RowStatus" 
    ::=  { deployProvLogicalIfCapEntry 1 }

deployProvLogicalIfCapFacilityType OBJECT-TYPE
    SYNTAX      FspR7InterfaceTypeCaps
    MAX-ACCESS  read-only
    STATUS      current
    DESCRIPTION   "Facility Type."
    ::=  { deployProvLogicalIfCapEntry 2 }

deployProvLogicalIfCapAlias OBJECT-TYPE
    SYNTAX      Integer32
    MAX-ACCESS  read-only
    STATUS      current
    DESCRIPTION   "Alias."
    ::=  { deployProvLogicalIfCapEntry 3 }

deployProvLogicalIfCapLanLinkAid OBJECT-TYPE
    SYNTAX      Integer32
    MAX-ACCESS  read-only
    STATUS      current
    DESCRIPTION   ""
    ::=  { deployProvLogicalIfCapEntry 4 }

deployProvLogicalIfCapAreaId OBJECT-TYPE
    SYNTAX      FspR7YesNo
    MAX-ACCESS  read-only
    STATUS      current
    DESCRIPTION
        "OSPF Area ID for IP Interface" 
    ::=  { deployProvLogicalIfCapEntry 5 }

deployProvLogicalIfCapMetric OBJECT-TYPE
    SYNTAX      FspR7Unsigned32Caps
    MAX-ACCESS  read-only
    STATUS      current
    DESCRIPTION
        "Routing Metric" 
    ::=  { deployProvLogicalIfCapEntry 6 }

deployProvLogicalIfCapHelloInterval OBJECT-TYPE
    SYNTAX      FspR7Unsigned32Caps
    UNITS       "s"
    MAX-ACCESS  read-only
    STATUS      current
    DESCRIPTION
        "Hello Interval" 
    ::=  { deployProvLogicalIfCapEntry 7 }

deployProvLogicalIfCapDeadInterval OBJECT-TYPE
    SYNTAX      FspR7Unsigned32Caps
    UNITS       "s"
    MAX-ACCESS  read-only
    STATUS      current
    DESCRIPTION
        "Dead Interval" 
    ::=  { deployProvLogicalIfCapEntry 8 }

deployProvLogicalIfCapPrio OBJECT-TYPE
    SYNTAX      FspR7Unsigned32Caps
    MAX-ACCESS  read-only
    STATUS      current
    DESCRIPTION
        "Priority" 
    ::=  { deployProvLogicalIfCapEntry 9 }

deployProvLogicalIfCapRetransmitInterval OBJECT-TYPE
    SYNTAX      FspR7Unsigned32Caps
    UNITS       "s"
    MAX-ACCESS  read-only
    STATUS      current
    DESCRIPTION
        "Retransmit Interval" 
    ::=  { deployProvLogicalIfCapEntry 10 }

deployProvLogicalIfCapAuthType OBJECT-TYPE
    SYNTAX      FspR7CpAuthTypeCaps
    MAX-ACCESS  read-only
    STATUS      current
    DESCRIPTION
        "OSPF Authentication Type" 
    ::=  { deployProvLogicalIfCapEntry 11 }

deployProvLogicalIfCapAuthString OBJECT-TYPE
    SYNTAX      Integer32
    MAX-ACCESS  read-only
    STATUS      current
    DESCRIPTION
        "OSPF Authentication Key/String depending on Authentication Type" 
    ::=  { deployProvLogicalIfCapEntry 12 }

deployProvLogicalIfCapIpType OBJECT-TYPE
    SYNTAX      FspR7IpTypeCaps
    MAX-ACCESS  read-only
    STATUS      current
    DESCRIPTION
        "Type of IP configuration" 
    ::=  { deployProvLogicalIfCapEntry 13 }

deployProvLogicalIfCapIpAddr OBJECT-TYPE
    SYNTAX      FspR7YesNo
    MAX-ACCESS  read-only
    STATUS      current
    DESCRIPTION
        "IP Address assigned to LAN IP Interface" 
    ::=  { deployProvLogicalIfCapEntry 14 }

deployProvLogicalIfCapIpAddrMask OBJECT-TYPE
    SYNTAX      FspR7YesNo
    MAX-ACCESS  read-only
    STATUS      current
    DESCRIPTION
        "IP MASK assigned to LAN IP Interface" 
    ::=  { deployProvLogicalIfCapEntry 15 }

deployProvLogicalIfCapAdmin OBJECT-TYPE
    SYNTAX      FspR7AdminStateCaps
    MAX-ACCESS  read-only
    STATUS      current
    DESCRIPTION
        "Administrative State is displayed in the GUI and Craft. Transition to Unassigend requires the entity to be deleted." 
    ::=  { deployProvLogicalIfCapEntry 16 }

deployProvLogicalIfCapDcnAid OBJECT-TYPE
    SYNTAX      Integer32
    MAX-ACCESS  read-only
    STATUS      current
    DESCRIPTION
        "Supporting DCN Facility AID" 
    ::=  { deployProvLogicalIfCapEntry 17 }

deployProvLogicalIfCapOspf OBJECT-TYPE
    SYNTAX      FspR7OspfModeCaps
    MAX-ACCESS  read-only
    STATUS      current
    DESCRIPTION
        "OSPF Routing (Dynamic)" 
    ::=  { deployProvLogicalIfCapEntry 18 }

deployProvLogicalIfCapEncapsulation OBJECT-TYPE
    SYNTAX      FspR7CpEncapsulationCaps
    MAX-ACCESS  read-only
    STATUS      current
    DESCRIPTION
        "Encapsulation" 
    ::=  { deployProvLogicalIfCapEntry 19 }

deployProvLogicalIfCapPushedNendIpHeader OBJECT-TYPE
    SYNTAX      FspR7YesNo
    MAX-ACCESS  read-only
    STATUS      current
    DESCRIPTION
        "Pushed Near End IP address in encapsulating header" 
    ::=  { deployProvLogicalIfCapEntry 20 }

deployProvLogicalIfCapPushedFarEndIpHeader OBJECT-TYPE
    SYNTAX      FspR7YesNo
    MAX-ACCESS  read-only
    STATUS      current
    DESCRIPTION
        "Pushed Far End IP address in encapsulating header" 
    ::=  { deployProvLogicalIfCapEntry 21 }

deployProvLogicalIfCapTimeToLive OBJECT-TYPE
    SYNTAX      FspR7Unsigned32Caps
    MAX-ACCESS  read-only
    STATUS      current
    DESCRIPTION
        "Time to Live" 
    ::=  { deployProvLogicalIfCapEntry 22 }

deployProvLogicalIfCapLanLinkAidString OBJECT-TYPE
    SYNTAX      Integer32
    MAX-ACCESS  read-only
    STATUS      current
    DESCRIPTION   ""
    ::=  { deployProvLogicalIfCapEntry 23 }

deployProvLogicalIfCapDcnAidString OBJECT-TYPE
    SYNTAX      FspR7SnmpLongString
    MAX-ACCESS  read-only
    STATUS      current
    DESCRIPTION
        "Supporting DCN Facility AID" 
    ::=  { deployProvLogicalIfCapEntry 24 }

deployProvLogicalIfCapIPv6 OBJECT-TYPE
    SYNTAX      Integer32
    MAX-ACCESS  read-only
    STATUS      current
    DESCRIPTION
        "IPv6 Address" 
    ::=  { deployProvLogicalIfCapEntry 25 }

deployProvLogicalIfCapIPv6PrefixLen OBJECT-TYPE
    SYNTAX      FspR7Unsigned32Caps
    MAX-ACCESS  read-only
    STATUS      current
    DESCRIPTION
        "IPv6 Subnet Prefix Length" 
    ::=  { deployProvLogicalIfCapEntry 26 }

deployProvLogicalIfCapIpMode OBJECT-TYPE
    SYNTAX      FspR7IpModeCaps
    MAX-ACCESS  read-only
    STATUS      current
    DESCRIPTION
        "IP Mode of Operation either IPv4 only or IPv4 and IPv6. When operation supports IPv6, it is used for addresses external to the network." 
    ::=  { deployProvLogicalIfCapEntry 27 }

deployProvLogicalIfDefaultsTable  OBJECT-TYPE
    SYNTAX      SEQUENCE OF DeployProvLogicalIfDefaultsEntry
    MAX-ACCESS  not-accessible
    STATUS      current
    DESCRIPTION   ""
    ::=  { facilityDeployProv 51  }

deployProvLogicalIfDefaultsEntry OBJECT-TYPE
    SYNTAX      DeployProvLogicalIfDefaultsEntry
    MAX-ACCESS  not-accessible
    STATUS      current
    DESCRIPTION   ""
    INDEX       { entityIndex }
    ::=  { deployProvLogicalIfDefaultsTable 1 }

DeployProvLogicalIfDefaultsEntry ::=  SEQUENCE
  { deployProvLogicalIfDefaultsRowStatus RowStatus,
    deployProvLogicalIfDefaultsFacilityType FspR7InterfaceType,
    deployProvLogicalIfDefaultsAlias SnmpAdminString,
    deployProvLogicalIfDefaultsLanLinkAid EntityIndex,
    deployProvLogicalIfDefaultsAreaId IpAddress,
    deployProvLogicalIfDefaultsMetric Unsigned32,
    deployProvLogicalIfDefaultsHelloInterval Unsigned32,
    deployProvLogicalIfDefaultsDeadInterval Unsigned32,
    deployProvLogicalIfDefaultsPrio Unsigned32,
    deployProvLogicalIfDefaultsRetransmitInterval Unsigned32,
    deployProvLogicalIfDefaultsAuthType FspR7CpAuthType,
    deployProvLogicalIfDefaultsAuthString SnmpAdminString,
    deployProvLogicalIfDefaultsIpType FspR7IpType,
    deployProvLogicalIfDefaultsIpAddr IpAddress,
    deployProvLogicalIfDefaultsIpAddrMask IpAddress,
    deployProvLogicalIfDefaultsAdmin FspR7AdminState,
    deployProvLogicalIfDefaultsDcnAid EntityIndex,
    deployProvLogicalIfDefaultsOspf FspR7OspfMode,
    deployProvLogicalIfDefaultsEncapsulation FspR7CpEncapsulation,
    deployProvLogicalIfDefaultsPushedNendIpHeader IpAddress,
    deployProvLogicalIfDefaultsPushedFarEndIpHeader IpAddress,
    deployProvLogicalIfDefaultsTimeToLive Unsigned32,
    deployProvLogicalIfDefaultsLanLinkAidString SnmpAdminString,
    deployProvLogicalIfDefaultsDcnAidString SnmpAdminString,
    deployProvLogicalIfDefaultsIPv6 SnmpAdminString,
    deployProvLogicalIfDefaultsIPv6PrefixLen Unsigned32,
    deployProvLogicalIfDefaultsIpMode FspR7IpMode }

deployProvLogicalIfDefaultsRowStatus OBJECT-TYPE
    SYNTAX      RowStatus
    MAX-ACCESS  read-only
    STATUS      current
    DESCRIPTION
        "RowStatus" 
    ::=  { deployProvLogicalIfDefaultsEntry 1 }

deployProvLogicalIfDefaultsFacilityType OBJECT-TYPE
    SYNTAX      FspR7InterfaceType
    MAX-ACCESS  read-only
    STATUS      current
    DESCRIPTION   "Facility Type."
    ::=  { deployProvLogicalIfDefaultsEntry 2 }

deployProvLogicalIfDefaultsAlias OBJECT-TYPE
    SYNTAX      SnmpAdminString
    MAX-ACCESS  read-only
    STATUS      current
    DESCRIPTION   "Alias."
    ::=  { deployProvLogicalIfDefaultsEntry 3 }

deployProvLogicalIfDefaultsLanLinkAid OBJECT-TYPE
    SYNTAX      EntityIndex
    MAX-ACCESS  read-only
    STATUS      current
    DESCRIPTION   ""
    ::=  { deployProvLogicalIfDefaultsEntry 4 }

deployProvLogicalIfDefaultsAreaId OBJECT-TYPE
    SYNTAX      IpAddress
    MAX-ACCESS  read-only
    STATUS      current
    DESCRIPTION
        "OSPF Area ID for IP Interface" 
    ::=  { deployProvLogicalIfDefaultsEntry 5 }

deployProvLogicalIfDefaultsMetric OBJECT-TYPE
    SYNTAX      Unsigned32 (0..65535 | 4294967295)
    MAX-ACCESS  read-only
    STATUS      current
    DESCRIPTION
        "Routing Metric" 
    ::=  { deployProvLogicalIfDefaultsEntry 6 }

deployProvLogicalIfDefaultsHelloInterval OBJECT-TYPE
    SYNTAX      Unsigned32 (1..65535 | 4294967295) 
    UNITS       "s"
    MAX-ACCESS  read-only
    STATUS      current
    DESCRIPTION
        "Hello Interval" 
    ::=  { deployProvLogicalIfDefaultsEntry 7 }

deployProvLogicalIfDefaultsDeadInterval OBJECT-TYPE
    SYNTAX      Unsigned32 (1..65535 | 4294967295) 
    UNITS       "s"
    MAX-ACCESS  read-only
    STATUS      current
    DESCRIPTION
        "Dead Interval" 
    ::=  { deployProvLogicalIfDefaultsEntry 8 }

deployProvLogicalIfDefaultsPrio OBJECT-TYPE
    SYNTAX      Unsigned32 (0..255 | 4294967295)
    MAX-ACCESS  read-only
    STATUS      current
    DESCRIPTION
        "Priority" 
    ::=  { deployProvLogicalIfDefaultsEntry 9 }

deployProvLogicalIfDefaultsRetransmitInterval OBJECT-TYPE
    SYNTAX      Unsigned32 (0..3600 | 4294967295) 
    UNITS       "s"
    MAX-ACCESS  read-only
    STATUS      current
    DESCRIPTION
        "Retransmit Interval" 
    ::=  { deployProvLogicalIfDefaultsEntry 10 }

deployProvLogicalIfDefaultsAuthType OBJECT-TYPE
    SYNTAX      FspR7CpAuthType
    MAX-ACCESS  read-only
    STATUS      current
    DESCRIPTION
        "OSPF Authentication Type" 
    ::=  { deployProvLogicalIfDefaultsEntry 11 }

deployProvLogicalIfDefaultsAuthString OBJECT-TYPE
    SYNTAX      SnmpAdminString
    MAX-ACCESS  read-only
    STATUS      current
    DESCRIPTION
        "OSPF Authentication Key/String depending on Authentication Type" 
    ::=  { deployProvLogicalIfDefaultsEntry 12 }

deployProvLogicalIfDefaultsIpType OBJECT-TYPE
    SYNTAX      FspR7IpType
    MAX-ACCESS  read-only
    STATUS      current
    DESCRIPTION
        "Type of IP configuration" 
    ::=  { deployProvLogicalIfDefaultsEntry 13 }

deployProvLogicalIfDefaultsIpAddr OBJECT-TYPE
    SYNTAX      IpAddress
    MAX-ACCESS  read-only
    STATUS      current
    DESCRIPTION
        "IP Address assigned to LAN IP Interface" 
    ::=  { deployProvLogicalIfDefaultsEntry 14 }

deployProvLogicalIfDefaultsIpAddrMask OBJECT-TYPE
    SYNTAX      IpAddress
    MAX-ACCESS  read-only
    STATUS      current
    DESCRIPTION
        "IP MASK assigned to LAN IP Interface" 
    ::=  { deployProvLogicalIfDefaultsEntry 15 }

deployProvLogicalIfDefaultsAdmin OBJECT-TYPE
    SYNTAX      FspR7AdminState
    MAX-ACCESS  read-only
    STATUS      current
    DESCRIPTION
        "Administrative State is displayed in the GUI and Craft. Transition to Unassigend requires the entity to be deleted." 
    ::=  { deployProvLogicalIfDefaultsEntry 16 }

deployProvLogicalIfDefaultsDcnAid OBJECT-TYPE
    SYNTAX      EntityIndex
    MAX-ACCESS  read-only
    STATUS      current
    DESCRIPTION
        "Supporting DCN Facility AID" 
    ::=  { deployProvLogicalIfDefaultsEntry 17 }

deployProvLogicalIfDefaultsOspf OBJECT-TYPE
    SYNTAX      FspR7OspfMode
    MAX-ACCESS  read-only
    STATUS      current
    DESCRIPTION
        "OSPF Routing (Dynamic)" 
    ::=  { deployProvLogicalIfDefaultsEntry 18 }

deployProvLogicalIfDefaultsEncapsulation OBJECT-TYPE
    SYNTAX      FspR7CpEncapsulation
    MAX-ACCESS  read-only
    STATUS      current
    DESCRIPTION
        "Encapsulation" 
    ::=  { deployProvLogicalIfDefaultsEntry 19 }

deployProvLogicalIfDefaultsPushedNendIpHeader OBJECT-TYPE
    SYNTAX      IpAddress
    MAX-ACCESS  read-only
    STATUS      current
    DESCRIPTION
        "Pushed Near End IP address in encapsulating header" 
    ::=  { deployProvLogicalIfDefaultsEntry 20 }

deployProvLogicalIfDefaultsPushedFarEndIpHeader OBJECT-TYPE
    SYNTAX      IpAddress
    MAX-ACCESS  read-only
    STATUS      current
    DESCRIPTION
        "Pushed Far End IP address in encapsulating header" 
    ::=  { deployProvLogicalIfDefaultsEntry 21 }

deployProvLogicalIfDefaultsTimeToLive OBJECT-TYPE
    SYNTAX      Unsigned32 (1..255 | 4294967295)
    MAX-ACCESS  read-only
    STATUS      current
    DESCRIPTION
        "Time to Live" 
    ::=  { deployProvLogicalIfDefaultsEntry 22 }

deployProvLogicalIfDefaultsLanLinkAidString OBJECT-TYPE
    SYNTAX      SnmpAdminString
    MAX-ACCESS  read-only
    STATUS      current
    DESCRIPTION   ""
    ::=  { deployProvLogicalIfDefaultsEntry 23 }

deployProvLogicalIfDefaultsDcnAidString OBJECT-TYPE
    SYNTAX      SnmpAdminString
    MAX-ACCESS  read-only
    STATUS      current
    DESCRIPTION
        "Supporting DCN Facility AID" 
    ::=  { deployProvLogicalIfDefaultsEntry 24 }

deployProvLogicalIfDefaultsIPv6 OBJECT-TYPE
    SYNTAX      SnmpAdminString
    MAX-ACCESS  read-only
    STATUS      current
    DESCRIPTION
        "IPv6 Address" 
    ::=  { deployProvLogicalIfDefaultsEntry 25 }

deployProvLogicalIfDefaultsIPv6PrefixLen OBJECT-TYPE
    SYNTAX      Unsigned32 (0..128 | 4294967295)
    MAX-ACCESS  read-only
    STATUS      current
    DESCRIPTION
        "IPv6 Subnet Prefix Length" 
    ::=  { deployProvLogicalIfDefaultsEntry 26 }

deployProvLogicalIfDefaultsIpMode OBJECT-TYPE
    SYNTAX      FspR7IpMode
    MAX-ACCESS  read-only
    STATUS      current
    DESCRIPTION
        "IP Mode of Operation either IPv4 only or IPv4 and IPv6. When operation supports IPv6, it is used for addresses external to the network." 
    ::=  { deployProvLogicalIfDefaultsEntry 27 }

deployProvIfLanAidCapsTable OBJECT-TYPE
    SYNTAX      SEQUENCE OF DeployProvIfLanAidCapsEntry
    MAX-ACCESS  not-accessible
    STATUS      current
    DESCRIPTION   ""
    ::=  { facilityDeployProv 52 }

deployProvIfLanAidCapsEntry OBJECT-TYPE
    SYNTAX      DeployProvIfLanAidCapsEntry
    MAX-ACCESS  not-accessible
    STATUS      current
    DESCRIPTION   ""
    INDEX       {
                  entityIndex,
                  deployProvIfLanAidCapsIndex
                }
    ::=  { deployProvIfLanAidCapsTable 1 }

DeployProvIfLanAidCapsEntry ::=  SEQUENCE
  { deployProvIfLanAidCapsIndex EntityIndex }

deployProvIfLanAidCapsIndex OBJECT-TYPE
    SYNTAX      EntityIndex
    MAX-ACCESS  read-only
    STATUS      current
    DESCRIPTION
        "AID of LAN" 
    ::=  { deployProvIfLanAidCapsEntry 1 }

changeServiceDeployProvIfLanAidCapsTable OBJECT-TYPE
    SYNTAX      SEQUENCE OF ChangeServiceDeployProvIfLanAidCapsEntry
    MAX-ACCESS  not-accessible
    STATUS      current
    DESCRIPTION   ""
    ::=  { facilityDeployProv 53 }

changeServiceDeployProvIfLanAidCapsEntry OBJECT-TYPE
    SYNTAX      ChangeServiceDeployProvIfLanAidCapsEntry
    MAX-ACCESS  not-accessible
    STATUS      current
    DESCRIPTION   ""
    INDEX       {
                  entityIndex,
                  changeServiceDeployProvIfLanAidCapsIndex
                }
    ::=  { changeServiceDeployProvIfLanAidCapsTable 1 }

ChangeServiceDeployProvIfLanAidCapsEntry ::=  SEQUENCE
  { changeServiceDeployProvIfLanAidCapsIndex EntityIndex }

changeServiceDeployProvIfLanAidCapsIndex OBJECT-TYPE
    SYNTAX      EntityIndex
    MAX-ACCESS  read-only
    STATUS      current
    DESCRIPTION
        "AID of LAN" 
    ::=  { changeServiceDeployProvIfLanAidCapsEntry 1 }

deployProvIfVethAidCapsTable OBJECT-TYPE
    SYNTAX      SEQUENCE OF DeployProvIfVethAidCapsEntry
    MAX-ACCESS  not-accessible
    STATUS      current
    DESCRIPTION   ""
    ::=  { facilityDeployProv 54 }

deployProvIfVethAidCapsEntry OBJECT-TYPE
    SYNTAX      DeployProvIfVethAidCapsEntry
    MAX-ACCESS  not-accessible
    STATUS      current
    DESCRIPTION   ""
    INDEX       {
                  entityIndex,
                  deployProvIfVethAidCapsIndex
                }
    ::=  { deployProvIfVethAidCapsTable 1 }

DeployProvIfVethAidCapsEntry ::=  SEQUENCE
  { deployProvIfVethAidCapsIndex EntityIndex }

deployProvIfVethAidCapsIndex OBJECT-TYPE
    SYNTAX      EntityIndex
    MAX-ACCESS  read-only
    STATUS      current
    DESCRIPTION
        "Shows if PORT is a member in the LAG with the VETH AID" 
    ::=  { deployProvIfVethAidCapsEntry 1 }

deployProvDcnExternalVidCapsTable OBJECT-TYPE
    SYNTAX      SEQUENCE OF DeployProvDcnExternalVidCapsEntry
    MAX-ACCESS  not-accessible
    STATUS      current
    DESCRIPTION   "This table is used to get capabilities for EXTVID parameter. Regular
         cap tables including EXTVID show the length of output string.
         Value 0 in regular cap tables means 'no capabilities'.
         The second index (n) is used to devide the output string to n string blocks.
         Each block has a maximum of 512 bytes. n = output string / 512."
    ::=  { facilityDeployProv 55 }

deployProvDcnExternalVidCapsEntry OBJECT-TYPE
    SYNTAX      DeployProvDcnExternalVidCapsEntry
    MAX-ACCESS  not-accessible
    STATUS      current
    DESCRIPTION   ""
    INDEX       {
                  entityIndex,
                  deployProvDcnExternalVidCapsIndexCap
                }
    ::=  { deployProvDcnExternalVidCapsTable 1 }

DeployProvDcnExternalVidCapsEntry ::=  SEQUENCE
  { deployProvDcnExternalVidCapsIndexCap EntityIndex,
    deployProvDcnExternalVidCapsStringCap SnmpAdminString }

deployProvDcnExternalVidCapsIndexCap OBJECT-TYPE
    SYNTAX      EntityIndex
    MAX-ACCESS  accessible-for-notify
    STATUS      current
    DESCRIPTION   "Used to display capability value per index. The number of capabilities determines the number of indexes."
    ::=  { deployProvDcnExternalVidCapsEntry 1 }

deployProvDcnExternalVidCapsStringCap OBJECT-TYPE
    SYNTAX      SnmpAdminString
    MAX-ACCESS  read-only
    STATUS      current
    DESCRIPTION
        "" 
    ::=  { deployProvDcnExternalVidCapsEntry 2 }

deployProvDcnLanAidCapsTable OBJECT-TYPE
    SYNTAX      SEQUENCE OF DeployProvDcnLanAidCapsEntry
    MAX-ACCESS  not-accessible
    STATUS      current
    DESCRIPTION   ""
    ::=  { facilityDeployProv 56 }

deployProvDcnLanAidCapsEntry OBJECT-TYPE
    SYNTAX      DeployProvDcnLanAidCapsEntry
    MAX-ACCESS  not-accessible
    STATUS      current
    DESCRIPTION   ""
    INDEX       {
                  entityIndex,
                  deployProvDcnLanAidCapsIndex
                }
    ::=  { deployProvDcnLanAidCapsTable 1 }

DeployProvDcnLanAidCapsEntry ::=  SEQUENCE
  { deployProvDcnLanAidCapsIndex EntityIndex }

deployProvDcnLanAidCapsIndex OBJECT-TYPE
    SYNTAX      EntityIndex
    MAX-ACCESS  read-only
    STATUS      current
    DESCRIPTION
        "AID of LAN" 
    ::=  { deployProvDcnLanAidCapsEntry 1 }

deployProvExChannelTable OBJECT-TYPE
    SYNTAX      SEQUENCE OF DeployProvExChannelEntry
    MAX-ACCESS  not-accessible
    STATUS      current
    DESCRIPTION   "Contains entries for provisioning of external channels."
    ::=  { facilityDeployProv 57 }

deployProvExChannelEntry OBJECT-TYPE
    SYNTAX      DeployProvExChannelEntry
    MAX-ACCESS  not-accessible
    STATUS      current
    DESCRIPTION   ""
    INDEX       {
                  entityIndex
                }
    ::=  { deployProvExChannelTable 1 }

DeployProvExChannelEntry ::=  SEQUENCE
  { deployProvExChannelRowStatus RowStatus,
    deployProvExChannelType FspR7InterfaceType,
    deployProvExChannelTransmitChannel FspR7ChannelIdentifier,
    deployProvExChannelChannelBandwith FspR7ChannelBandwidth,
    deployProvExChannelAlias SnmpAdminString,
    deployProvExChannelFarEndLocation SnmpAdminString,
    deployProvExChannelBitrate Unsigned32,
    deployProvExChannelFecType FspR7FecType,
    deployProvExChannelLineCoding FspR7LineCoding,
    deployProvExChannelFrameFormat FspR7FrameFormat,
    deployProvExChannelOpticalPowerTx Integer32,
    deployProvExChannelOSNRTransmit Unsigned32,
    deployProvExChannelPMDTransmit Unsigned32,
    deployProvExChannelChromaticDispersionTx Integer32,
    deployProvExChannelMinimumOSNRRcv Unsigned32,
    deployProvExChannelMinimumOpticalPowerRcv Integer32,
    deployProvExChannelMaximumOpticalPowerRcv Integer32,
    deployProvExChannelMaximumPMDRcv Unsigned32,
    deployProvExChannelChromaticDispersionRcv Integer32,
    deployProvExChannelMaxBitErrorRate FspR7MaxBitErrorRate,
    deployProvExChannelMinChromaticDispersionRcv Integer32,
    deployProvExChannelMaxChromaticDispersionRcv Integer32,
    deployProvExChannelSourceProfile SnmpAdminString }

deployProvExChannelRowStatus OBJECT-TYPE
    SYNTAX      RowStatus
    MAX-ACCESS  read-write
    STATUS      current
    DESCRIPTION   "RowStatus"
    ::=  { deployProvExChannelEntry 1 }

deployProvExChannelType OBJECT-TYPE
    SYNTAX      FspR7InterfaceType
    MAX-ACCESS  read-write
    STATUS      current
    DESCRIPTION   "The TYPE defines the transport service type as wrapper with wrapper layer
         termination OR else as payload"
    ::=  { deployProvExChannelEntry 2 }

deployProvExChannelTransmitChannel OBJECT-TYPE
    SYNTAX      FspR7ChannelIdentifier
    MAX-ACCESS  read-write
    STATUS      current
    DESCRIPTION
        "Channel" 
    ::=  { deployProvExChannelEntry 3 }

deployProvExChannelChannelBandwith OBJECT-TYPE
    SYNTAX      FspR7ChannelBandwidth
    MAX-ACCESS  read-write
    STATUS      current
    DESCRIPTION
        "Channel Bandwidth" 
    ::=  { deployProvExChannelEntry 4 }

deployProvExChannelAlias OBJECT-TYPE
    SYNTAX      SnmpAdminString
    MAX-ACCESS  read-write
    STATUS      current
    DESCRIPTION
        "User Applied Descriptor" 
    ::=  { deployProvExChannelEntry 5 }

deployProvExChannelFarEndLocation OBJECT-TYPE
    SYNTAX      SnmpAdminString
    MAX-ACCESS  read-write
    STATUS      current
    DESCRIPTION   ""
    ::=  { deployProvExChannelEntry 6 }

deployProvExChannelBitrate OBJECT-TYPE
    SYNTAX      Unsigned32 
    UNITS       "Mbps"
    MAX-ACCESS  read-write
    STATUS      current
    DESCRIPTION   ""
    ::=  { deployProvExChannelEntry 7 }

deployProvExChannelFecType OBJECT-TYPE
    SYNTAX      FspR7FecType
    MAX-ACCESS  read-write
    STATUS      current
    DESCRIPTION   ""
    ::=  { deployProvExChannelEntry 8 }

deployProvExChannelLineCoding OBJECT-TYPE
    SYNTAX      FspR7LineCoding
    MAX-ACCESS  read-write
    STATUS      current
    DESCRIPTION   ""
    ::=  { deployProvExChannelEntry 9 }

deployProvExChannelFrameFormat OBJECT-TYPE
    SYNTAX      FspR7FrameFormat
    MAX-ACCESS  read-write
    STATUS      current
    DESCRIPTION   ""
    ::=  { deployProvExChannelEntry 10 }

deployProvExChannelOpticalPowerTx OBJECT-TYPE
    SYNTAX      Integer32 (-9900..600 | -2147483648) 
    UNITS       "0.1 dBm"
    MAX-ACCESS  read-write
    STATUS      current
    DESCRIPTION
        "Optical Power Transmit" 
    ::=  { deployProvExChannelEntry 11 }

deployProvExChannelOSNRTransmit OBJECT-TYPE
    SYNTAX      Unsigned32 (0..58 | 4294967295) 
    UNITS       "dB"
    MAX-ACCESS  read-write
    STATUS      current
    DESCRIPTION
        "Optical Signal to Noise Ratio Transmit" 
    ::=  { deployProvExChannelEntry 12 }

deployProvExChannelPMDTransmit OBJECT-TYPE
    SYNTAX      Unsigned32 (0..30 | 4294967295) 
    UNITS       "ps"
    MAX-ACCESS  read-write
    STATUS      current
    DESCRIPTION
        "Polarization Mode Dispersion Transmit" 
    ::=  { deployProvExChannelEntry 13 }

deployProvExChannelChromaticDispersionTx OBJECT-TYPE
    SYNTAX      Integer32 (-60000..60000 | -2147483648) 
    UNITS       "ps/nm"
    MAX-ACCESS  read-write
    STATUS      current
    DESCRIPTION
        "Chromatic Dispersion Transmit" 
    ::=  { deployProvExChannelEntry 14 }

deployProvExChannelMinimumOSNRRcv OBJECT-TYPE
    SYNTAX      Unsigned32 (10..58 | 4294967295) 
    UNITS       "dB"
    MAX-ACCESS  read-write
    STATUS      current
    DESCRIPTION
        "Minimum Optical Signal to Noise Ratio, Rcv" 
    ::=  { deployProvExChannelEntry 15 }

deployProvExChannelMinimumOpticalPowerRcv OBJECT-TYPE
    SYNTAX      Integer32 (-2500..1000 | -2147483648) 
    UNITS       "0.1 dBm"
    MAX-ACCESS  read-write
    STATUS      current
    DESCRIPTION
        "Minimum Optical Power Received" 
    ::=  { deployProvExChannelEntry 16 }

deployProvExChannelMaximumOpticalPowerRcv OBJECT-TYPE
    SYNTAX      Integer32 (-2500..1000 | -2147483648) 
    UNITS       "0.1 dBm"
    MAX-ACCESS  read-write
    STATUS      current
    DESCRIPTION
        "Maximum Optical Power Received" 
    ::=  { deployProvExChannelEntry 17 }

deployProvExChannelMaximumPMDRcv OBJECT-TYPE
    SYNTAX      Unsigned32 (0..30 | 4294967295) 
    UNITS       "ps"
    MAX-ACCESS  read-write
    STATUS      current
    DESCRIPTION
        "Maximum Polarization Mode Dispersion Rcv" 
    ::=  { deployProvExChannelEntry 18 }

deployProvExChannelChromaticDispersionRcv OBJECT-TYPE
    SYNTAX      Integer32 (-60000..60000 | -2147483648) 
    UNITS       "ps/nm"
    MAX-ACCESS  read-write
    STATUS      deprecated
    DESCRIPTION
        "Maximum Chromatic Dispersion Rcv" 
    ::=  { deployProvExChannelEntry 19 }

deployProvExChannelMaxBitErrorRate OBJECT-TYPE
    SYNTAX      FspR7MaxBitErrorRate
    MAX-ACCESS  read-write
    STATUS      current
    DESCRIPTION
        "Maximum Bit Error Rate" 
    ::=  { deployProvExChannelEntry 20 }

deployProvExChannelMinChromaticDispersionRcv OBJECT-TYPE
    SYNTAX      Integer32 (-60000..60000 | -2147483648) 
    UNITS       "ps/nm"
    MAX-ACCESS  read-write
    STATUS      current
    DESCRIPTION
        "Minimum Chromatic Dispersion Rcv" 
    ::=  { deployProvExChannelEntry 21 }

deployProvExChannelMaxChromaticDispersionRcv OBJECT-TYPE
    SYNTAX      Integer32 (-60000..60000 | -2147483648) 
    UNITS       "ps/nm"
    MAX-ACCESS  read-write
    STATUS      current
    DESCRIPTION
        "Maximum Chromatic Dispersion Rcv" 
    ::=  { deployProvExChannelEntry 22 }

deployProvExChannelSourceProfile OBJECT-TYPE
    SYNTAX      SnmpAdminString
    MAX-ACCESS  read-write
    STATUS      current
    DESCRIPTION
        "File Name" 
    ::=  { deployProvExChannelEntry 23 }

deployProvExChannelCapTable OBJECT-TYPE
    SYNTAX      SEQUENCE OF DeployProvExChannelCapEntry
    MAX-ACCESS  not-accessible
    STATUS      current
    DESCRIPTION   "Contains entries for provisioning of external channels."
    ::=  { facilityDeployProv 58  }

deployProvExChannelCapEntry OBJECT-TYPE
    SYNTAX      DeployProvExChannelCapEntry
    MAX-ACCESS  not-accessible
    STATUS      current
    DESCRIPTION   ""
    INDEX       { entityIndex }
    ::=  { deployProvExChannelCapTable 1 }

DeployProvExChannelCapEntry ::=  SEQUENCE
  { deployProvExChannelCapRowStatus FspR7RowStatusCaps,
    deployProvExChannelCapType FspR7InterfaceTypeCaps,
    deployProvExChannelCapTransmitChannel FspR7ChannelIdentifierCaps,
    deployProvExChannelCapChannelBandwith FspR7ChannelBandwidthCaps,
    deployProvExChannelCapAlias Integer32,
    deployProvExChannelCapFarEndLocation Integer32,
    deployProvExChannelCapBitrate FspR7Unsigned32Caps,
    deployProvExChannelCapFecType FspR7FecTypeCaps,
    deployProvExChannelCapLineCoding FspR7LineCodingCaps,
    deployProvExChannelCapFrameFormat FspR7FrameFormatCaps,
    deployProvExChannelCapOpticalPowerTx FspR7Integer32Caps,
    deployProvExChannelCapOSNRTransmit FspR7Unsigned32Caps,
    deployProvExChannelCapPMDTransmit FspR7Unsigned32Caps,
    deployProvExChannelCapChromaticDispersionTx FspR7Integer32Caps,
    deployProvExChannelCapMinimumOSNRRcv FspR7Unsigned32Caps,
    deployProvExChannelCapMinimumOpticalPowerRcv FspR7Integer32Caps,
    deployProvExChannelCapMaximumOpticalPowerRcv FspR7Integer32Caps,
    deployProvExChannelCapMaximumPMDRcv FspR7Unsigned32Caps,
    deployProvExChannelCapChromaticDispersionRcv FspR7Integer32Caps,
    deployProvExChannelCapMaxBitErrorRate FspR7MaxBitErrorRateCaps,
    deployProvExChannelCapMinChromaticDispersionRcv FspR7Integer32Caps,
    deployProvExChannelCapMaxChromaticDispersionRcv FspR7Integer32Caps,
    deployProvExChannelCapSourceProfile Integer32 }

deployProvExChannelCapRowStatus OBJECT-TYPE
    SYNTAX      FspR7RowStatusCaps
    MAX-ACCESS  read-only
    STATUS      current
    DESCRIPTION   "RowStatus"
    ::=  { deployProvExChannelCapEntry 1 }

deployProvExChannelCapType OBJECT-TYPE
    SYNTAX      FspR7InterfaceTypeCaps
    MAX-ACCESS  read-only
    STATUS      current
    DESCRIPTION   "The TYPE defines the transport service type as wrapper with wrapper layer
         termination OR else as payload"
    ::=  { deployProvExChannelCapEntry 2 }

deployProvExChannelCapTransmitChannel OBJECT-TYPE
    SYNTAX      FspR7ChannelIdentifierCaps
    MAX-ACCESS  read-only
    STATUS      current
    DESCRIPTION
        "Channel" 
    ::=  { deployProvExChannelCapEntry 3 }

deployProvExChannelCapChannelBandwith OBJECT-TYPE
    SYNTAX      FspR7ChannelBandwidthCaps
    MAX-ACCESS  read-only
    STATUS      current
    DESCRIPTION
        "Channel Bandwidth" 
    ::=  { deployProvExChannelCapEntry 4 }

deployProvExChannelCapAlias OBJECT-TYPE
    SYNTAX      Integer32
    MAX-ACCESS  read-only
    STATUS      current
    DESCRIPTION
        "User Applied Descriptor" 
    ::=  { deployProvExChannelCapEntry 5 }

deployProvExChannelCapFarEndLocation OBJECT-TYPE
    SYNTAX      Integer32
    MAX-ACCESS  read-only
    STATUS      current
    DESCRIPTION   ""
    ::=  { deployProvExChannelCapEntry 6 }

deployProvExChannelCapBitrate OBJECT-TYPE
    SYNTAX      FspR7Unsigned32Caps
    UNITS       "Mbps"
    MAX-ACCESS  read-only
    STATUS      current
    DESCRIPTION   ""
    ::=  { deployProvExChannelCapEntry 7 }

deployProvExChannelCapFecType OBJECT-TYPE
    SYNTAX      FspR7FecTypeCaps
    MAX-ACCESS  read-only
    STATUS      current
    DESCRIPTION   ""
    ::=  { deployProvExChannelCapEntry 8 }

deployProvExChannelCapLineCoding OBJECT-TYPE
    SYNTAX      FspR7LineCodingCaps
    MAX-ACCESS  read-only
    STATUS      current
    DESCRIPTION   ""
    ::=  { deployProvExChannelCapEntry 9 }

deployProvExChannelCapFrameFormat OBJECT-TYPE
    SYNTAX      FspR7FrameFormatCaps
    MAX-ACCESS  read-only
    STATUS      current
    DESCRIPTION   ""
    ::=  { deployProvExChannelCapEntry 10 }

deployProvExChannelCapOpticalPowerTx OBJECT-TYPE
    SYNTAX      FspR7Integer32Caps
    UNITS       "0.1 dBm"
    MAX-ACCESS  read-only
    STATUS      current
    DESCRIPTION
        "Optical Power Transmit" 
    ::=  { deployProvExChannelCapEntry 11 }

deployProvExChannelCapOSNRTransmit OBJECT-TYPE
    SYNTAX      FspR7Unsigned32Caps
    UNITS       "dB"
    MAX-ACCESS  read-only
    STATUS      current
    DESCRIPTION
        "Optical Signal to Noise Ratio Transmit" 
    ::=  { deployProvExChannelCapEntry 12 }

deployProvExChannelCapPMDTransmit OBJECT-TYPE
    SYNTAX      FspR7Unsigned32Caps
    UNITS       "ps"
    MAX-ACCESS  read-only
    STATUS      current
    DESCRIPTION
        "Polarization Mode Dispersion Transmit" 
    ::=  { deployProvExChannelCapEntry 13 }

deployProvExChannelCapChromaticDispersionTx OBJECT-TYPE
    SYNTAX      FspR7Integer32Caps
    UNITS       "ps/nm"
    MAX-ACCESS  read-only
    STATUS      current
    DESCRIPTION
        "Chromatic Dispersion Transmit" 
    ::=  { deployProvExChannelCapEntry 14 }

deployProvExChannelCapMinimumOSNRRcv OBJECT-TYPE
    SYNTAX      FspR7Unsigned32Caps
    UNITS       "dB"
    MAX-ACCESS  read-only
    STATUS      current
    DESCRIPTION
        "Minimum Optical Signal to Noise Ratio, Rcv" 
    ::=  { deployProvExChannelCapEntry 15 }

deployProvExChannelCapMinimumOpticalPowerRcv OBJECT-TYPE
    SYNTAX      FspR7Integer32Caps
    UNITS       "0.1 dBm"
    MAX-ACCESS  read-only
    STATUS      current
    DESCRIPTION
        "Minimum Optical Power Received" 
    ::=  { deployProvExChannelCapEntry 16 }

deployProvExChannelCapMaximumOpticalPowerRcv OBJECT-TYPE
    SYNTAX      FspR7Integer32Caps
    UNITS       "0.1 dBm"
    MAX-ACCESS  read-only
    STATUS      current
    DESCRIPTION
        "Maximum Optical Power Received" 
    ::=  { deployProvExChannelCapEntry 17 }

deployProvExChannelCapMaximumPMDRcv OBJECT-TYPE
    SYNTAX      FspR7Unsigned32Caps
    UNITS       "ps"
    MAX-ACCESS  read-only
    STATUS      current
    DESCRIPTION
        "Maximum Polarization Mode Dispersion Rcv" 
    ::=  { deployProvExChannelCapEntry 18 }

deployProvExChannelCapChromaticDispersionRcv OBJECT-TYPE
    SYNTAX      FspR7Integer32Caps
    UNITS       "ps/nm"
    MAX-ACCESS  read-only
    STATUS      deprecated
    DESCRIPTION
        "Maximum Chromatic Dispersion Rcv" 
    ::=  { deployProvExChannelCapEntry 19 }

deployProvExChannelCapMaxBitErrorRate OBJECT-TYPE
    SYNTAX      FspR7MaxBitErrorRateCaps
    MAX-ACCESS  read-only
    STATUS      current
    DESCRIPTION
        "Maximum Bit Error Rate" 
    ::=  { deployProvExChannelCapEntry 20 }

deployProvExChannelCapMinChromaticDispersionRcv OBJECT-TYPE
    SYNTAX      FspR7Integer32Caps
    UNITS       "ps/nm"
    MAX-ACCESS  read-only
    STATUS      current
    DESCRIPTION
        "Minimum Chromatic Dispersion Rcv" 
    ::=  { deployProvExChannelCapEntry 21 }

deployProvExChannelCapMaxChromaticDispersionRcv OBJECT-TYPE
    SYNTAX      FspR7Integer32Caps
    UNITS       "ps/nm"
    MAX-ACCESS  read-only
    STATUS      current
    DESCRIPTION
        "Maximum Chromatic Dispersion Rcv" 
    ::=  { deployProvExChannelCapEntry 22 }

deployProvExChannelCapSourceProfile OBJECT-TYPE
    SYNTAX      Integer32
    MAX-ACCESS  read-only
    STATUS      current
    DESCRIPTION
        "File Name" 
    ::=  { deployProvExChannelCapEntry 23 }

deployProvExChannelDefaultsTable  OBJECT-TYPE
    SYNTAX      SEQUENCE OF DeployProvExChannelDefaultsEntry
    MAX-ACCESS  not-accessible
    STATUS      current
    DESCRIPTION   "Contains entries for provisioning of external channels."
    ::=  { facilityDeployProv 59  }

deployProvExChannelDefaultsEntry OBJECT-TYPE
    SYNTAX      DeployProvExChannelDefaultsEntry
    MAX-ACCESS  not-accessible
    STATUS      current
    DESCRIPTION   ""
    INDEX       { entityIndex }
    ::=  { deployProvExChannelDefaultsTable 1 }

DeployProvExChannelDefaultsEntry ::=  SEQUENCE
  { deployProvExChannelDefaultsRowStatus RowStatus,
    deployProvExChannelDefaultsType FspR7InterfaceType,
    deployProvExChannelDefaultsTransmitChannel FspR7ChannelIdentifier,
    deployProvExChannelDefaultsChannelBandwith FspR7ChannelBandwidth,
    deployProvExChannelDefaultsAlias SnmpAdminString,
    deployProvExChannelDefaultsFarEndLocation SnmpAdminString,
    deployProvExChannelDefaultsBitrate Unsigned32,
    deployProvExChannelDefaultsFecType FspR7FecType,
    deployProvExChannelDefaultsLineCoding FspR7LineCoding,
    deployProvExChannelDefaultsFrameFormat FspR7FrameFormat,
    deployProvExChannelDefaultsOpticalPowerTx Integer32,
    deployProvExChannelDefaultsOSNRTransmit Unsigned32,
    deployProvExChannelDefaultsPMDTransmit Unsigned32,
    deployProvExChannelDefaultsChromaticDispersionTx Integer32,
    deployProvExChannelDefaultsMinimumOSNRRcv Unsigned32,
    deployProvExChannelDefaultsMinimumOpticalPowerRcv Integer32,
    deployProvExChannelDefaultsMaximumOpticalPowerRcv Integer32,
    deployProvExChannelDefaultsMaximumPMDRcv Unsigned32,
    deployProvExChannelDefaultsChromaticDispersionRcv Integer32,
    deployProvExChannelDefaultsMaxBitErrorRate FspR7MaxBitErrorRate,
    deployProvExChannelDefaultsMinChromaticDispersionRcv Integer32,
    deployProvExChannelDefaultsMaxChromaticDispersionRcv Integer32,
    deployProvExChannelDefaultsSourceProfile SnmpAdminString }

deployProvExChannelDefaultsRowStatus OBJECT-TYPE
    SYNTAX      RowStatus
    MAX-ACCESS  read-only
    STATUS      current
    DESCRIPTION   "RowStatus"
    ::=  { deployProvExChannelDefaultsEntry 1 }

deployProvExChannelDefaultsType OBJECT-TYPE
    SYNTAX      FspR7InterfaceType
    MAX-ACCESS  read-only
    STATUS      current
    DESCRIPTION   "The TYPE defines the transport service type as wrapper with wrapper layer
         termination OR else as payload"
    ::=  { deployProvExChannelDefaultsEntry 2 }

deployProvExChannelDefaultsTransmitChannel OBJECT-TYPE
    SYNTAX      FspR7ChannelIdentifier
    MAX-ACCESS  read-only
    STATUS      current
    DESCRIPTION
        "Channel" 
    ::=  { deployProvExChannelDefaultsEntry 3 }

deployProvExChannelDefaultsChannelBandwith OBJECT-TYPE
    SYNTAX      FspR7ChannelBandwidth
    MAX-ACCESS  read-only
    STATUS      current
    DESCRIPTION
        "Channel Bandwidth" 
    ::=  { deployProvExChannelDefaultsEntry 4 }

deployProvExChannelDefaultsAlias OBJECT-TYPE
    SYNTAX      SnmpAdminString
    MAX-ACCESS  read-only
    STATUS      current
    DESCRIPTION
        "User Applied Descriptor" 
    ::=  { deployProvExChannelDefaultsEntry 5 }

deployProvExChannelDefaultsFarEndLocation OBJECT-TYPE
    SYNTAX      SnmpAdminString
    MAX-ACCESS  read-only
    STATUS      current
    DESCRIPTION   ""
    ::=  { deployProvExChannelDefaultsEntry 6 }

deployProvExChannelDefaultsBitrate OBJECT-TYPE
    SYNTAX      Unsigned32 
    UNITS       "Mbps"
    MAX-ACCESS  read-only
    STATUS      current
    DESCRIPTION   ""
    ::=  { deployProvExChannelDefaultsEntry 7 }

deployProvExChannelDefaultsFecType OBJECT-TYPE
    SYNTAX      FspR7FecType
    MAX-ACCESS  read-only
    STATUS      current
    DESCRIPTION   ""
    ::=  { deployProvExChannelDefaultsEntry 8 }

deployProvExChannelDefaultsLineCoding OBJECT-TYPE
    SYNTAX      FspR7LineCoding
    MAX-ACCESS  read-only
    STATUS      current
    DESCRIPTION   ""
    ::=  { deployProvExChannelDefaultsEntry 9 }

deployProvExChannelDefaultsFrameFormat OBJECT-TYPE
    SYNTAX      FspR7FrameFormat
    MAX-ACCESS  read-only
    STATUS      current
    DESCRIPTION   ""
    ::=  { deployProvExChannelDefaultsEntry 10 }

deployProvExChannelDefaultsOpticalPowerTx OBJECT-TYPE
    SYNTAX      Integer32 (-9900..600 | -2147483648) 
    UNITS       "0.1 dBm"
    MAX-ACCESS  read-only
    STATUS      current
    DESCRIPTION
        "Optical Power Transmit" 
    ::=  { deployProvExChannelDefaultsEntry 11 }

deployProvExChannelDefaultsOSNRTransmit OBJECT-TYPE
    SYNTAX      Unsigned32 (0..58 | 4294967295) 
    UNITS       "dB"
    MAX-ACCESS  read-only
    STATUS      current
    DESCRIPTION
        "Optical Signal to Noise Ratio Transmit" 
    ::=  { deployProvExChannelDefaultsEntry 12 }

deployProvExChannelDefaultsPMDTransmit OBJECT-TYPE
    SYNTAX      Unsigned32 (0..30 | 4294967295) 
    UNITS       "ps"
    MAX-ACCESS  read-only
    STATUS      current
    DESCRIPTION
        "Polarization Mode Dispersion Transmit" 
    ::=  { deployProvExChannelDefaultsEntry 13 }

deployProvExChannelDefaultsChromaticDispersionTx OBJECT-TYPE
    SYNTAX      Integer32 (-60000..60000 | -2147483648) 
    UNITS       "ps/nm"
    MAX-ACCESS  read-only
    STATUS      current
    DESCRIPTION
        "Chromatic Dispersion Transmit" 
    ::=  { deployProvExChannelDefaultsEntry 14 }

deployProvExChannelDefaultsMinimumOSNRRcv OBJECT-TYPE
    SYNTAX      Unsigned32 (10..58 | 4294967295) 
    UNITS       "dB"
    MAX-ACCESS  read-only
    STATUS      current
    DESCRIPTION
        "Minimum Optical Signal to Noise Ratio, Rcv" 
    ::=  { deployProvExChannelDefaultsEntry 15 }

deployProvExChannelDefaultsMinimumOpticalPowerRcv OBJECT-TYPE
    SYNTAX      Integer32 (-2500..1000 | -2147483648) 
    UNITS       "0.1 dBm"
    MAX-ACCESS  read-only
    STATUS      current
    DESCRIPTION
        "Minimum Optical Power Received" 
    ::=  { deployProvExChannelDefaultsEntry 16 }

deployProvExChannelDefaultsMaximumOpticalPowerRcv OBJECT-TYPE
    SYNTAX      Integer32 (-2500..1000 | -2147483648) 
    UNITS       "0.1 dBm"
    MAX-ACCESS  read-only
    STATUS      current
    DESCRIPTION
        "Maximum Optical Power Received" 
    ::=  { deployProvExChannelDefaultsEntry 17 }

deployProvExChannelDefaultsMaximumPMDRcv OBJECT-TYPE
    SYNTAX      Unsigned32 (0..30 | 4294967295) 
    UNITS       "ps"
    MAX-ACCESS  read-only
    STATUS      current
    DESCRIPTION
        "Maximum Polarization Mode Dispersion Rcv" 
    ::=  { deployProvExChannelDefaultsEntry 18 }

deployProvExChannelDefaultsChromaticDispersionRcv OBJECT-TYPE
    SYNTAX      Integer32 (-60000..60000 | -2147483648) 
    UNITS       "ps/nm"
    MAX-ACCESS  read-only
    STATUS      deprecated
    DESCRIPTION
        "Maximum Chromatic Dispersion Rcv" 
    ::=  { deployProvExChannelDefaultsEntry 19 }

deployProvExChannelDefaultsMaxBitErrorRate OBJECT-TYPE
    SYNTAX      FspR7MaxBitErrorRate
    MAX-ACCESS  read-only
    STATUS      current
    DESCRIPTION
        "Maximum Bit Error Rate" 
    ::=  { deployProvExChannelDefaultsEntry 20 }

deployProvExChannelDefaultsMinChromaticDispersionRcv OBJECT-TYPE
    SYNTAX      Integer32 (-60000..60000 | -2147483648) 
    UNITS       "ps/nm"
    MAX-ACCESS  read-only
    STATUS      current
    DESCRIPTION
        "Minimum Chromatic Dispersion Rcv" 
    ::=  { deployProvExChannelDefaultsEntry 21 }

deployProvExChannelDefaultsMaxChromaticDispersionRcv OBJECT-TYPE
    SYNTAX      Integer32 (-60000..60000 | -2147483648) 
    UNITS       "ps/nm"
    MAX-ACCESS  read-only
    STATUS      current
    DESCRIPTION
        "Maximum Chromatic Dispersion Rcv" 
    ::=  { deployProvExChannelDefaultsEntry 22 }

deployProvExChannelDefaultsSourceProfile OBJECT-TYPE
    SYNTAX      SnmpAdminString
    MAX-ACCESS  read-only
    STATUS      current
    DESCRIPTION
        "File Name" 
    ::=  { deployProvExChannelDefaultsEntry 23 }

deployProvSuperChannelTable OBJECT-TYPE
    SYNTAX      SEQUENCE OF DeployProvSuperChannelEntry
    MAX-ACCESS  not-accessible
    STATUS      current
    DESCRIPTION   "Contains entries for provisioning of OTLG."
    ::=  { facilityDeployProv 60 }

deployProvSuperChannelEntry OBJECT-TYPE
    SYNTAX      DeployProvSuperChannelEntry
    MAX-ACCESS  not-accessible
    STATUS      current
    DESCRIPTION   ""
    INDEX       {
                  entityIndex
                }
    ::=  { deployProvSuperChannelTable 1 }

DeployProvSuperChannelEntry ::=  SEQUENCE
  { deployProvSuperChannelRowStatus RowStatus,
    deployProvSuperChannelEqlzAdmin FspR7EqlzAdminState,
    deployProvSuperChannelAlias SnmpAdminString,
    deployProvSuperChannelAdmin FspR7AdminState,
    deployProvSuperChannelType FspR7InterfaceType }

deployProvSuperChannelRowStatus OBJECT-TYPE
    SYNTAX      RowStatus
    MAX-ACCESS  read-write
    STATUS      current
    DESCRIPTION   "RowStatus"
    ::=  { deployProvSuperChannelEntry 1 }

deployProvSuperChannelEqlzAdmin OBJECT-TYPE
    SYNTAX      FspR7EqlzAdminState
    MAX-ACCESS  read-write
    STATUS      current
    DESCRIPTION
        "Scheduled Equalization Administration" 
    ::=  { deployProvSuperChannelEntry 2 }

deployProvSuperChannelAlias OBJECT-TYPE
    SYNTAX      SnmpAdminString
    MAX-ACCESS  read-write
    STATUS      current
    DESCRIPTION
        "User Applied Descriptor" 
    ::=  { deployProvSuperChannelEntry 3 }

deployProvSuperChannelAdmin OBJECT-TYPE
    SYNTAX      FspR7AdminState
    MAX-ACCESS  read-write
    STATUS      current
    DESCRIPTION
        "Administrative State is displayed in the GUI and Craft. Transition to Unassigend requires the entity to be deleted." 
    ::=  { deployProvSuperChannelEntry 4 }

deployProvSuperChannelType OBJECT-TYPE
    SYNTAX      FspR7InterfaceType
    MAX-ACCESS  read-write
    STATUS      current
    DESCRIPTION
        "The TYPE defines the transport service type as wrapper with wrapper layer termination OR else as payload" 
    ::=  { deployProvSuperChannelEntry 5 }

deployProvSuperChannelCapTable OBJECT-TYPE
    SYNTAX      SEQUENCE OF DeployProvSuperChannelCapEntry
    MAX-ACCESS  not-accessible
    STATUS      current
    DESCRIPTION   "Contains entries for provisioning of OTLG."
    ::=  { facilityDeployProv 61  }

deployProvSuperChannelCapEntry OBJECT-TYPE
    SYNTAX      DeployProvSuperChannelCapEntry
    MAX-ACCESS  not-accessible
    STATUS      current
    DESCRIPTION   ""
    INDEX       { entityIndex }
    ::=  { deployProvSuperChannelCapTable 1 }

DeployProvSuperChannelCapEntry ::=  SEQUENCE
  { deployProvSuperChannelCapRowStatus FspR7RowStatusCaps,
    deployProvSuperChannelCapEqlzAdmin FspR7EqlzAdminStateCaps,
    deployProvSuperChannelCapAlias Integer32,
    deployProvSuperChannelCapAdmin FspR7AdminStateCaps,
    deployProvSuperChannelCapType FspR7InterfaceTypeCaps }

deployProvSuperChannelCapRowStatus OBJECT-TYPE
    SYNTAX      FspR7RowStatusCaps
    MAX-ACCESS  read-only
    STATUS      current
    DESCRIPTION   "RowStatus"
    ::=  { deployProvSuperChannelCapEntry 1 }

deployProvSuperChannelCapEqlzAdmin OBJECT-TYPE
    SYNTAX      FspR7EqlzAdminStateCaps
    MAX-ACCESS  read-only
    STATUS      current
    DESCRIPTION
        "Scheduled Equalization Administration" 
    ::=  { deployProvSuperChannelCapEntry 2 }

deployProvSuperChannelCapAlias OBJECT-TYPE
    SYNTAX      Integer32
    MAX-ACCESS  read-only
    STATUS      current
    DESCRIPTION
        "User Applied Descriptor" 
    ::=  { deployProvSuperChannelCapEntry 3 }

deployProvSuperChannelCapAdmin OBJECT-TYPE
    SYNTAX      FspR7AdminStateCaps
    MAX-ACCESS  read-only
    STATUS      current
    DESCRIPTION
        "Administrative State is displayed in the GUI and Craft. Transition to Unassigend requires the entity to be deleted." 
    ::=  { deployProvSuperChannelCapEntry 4 }

deployProvSuperChannelCapType OBJECT-TYPE
    SYNTAX      FspR7InterfaceTypeCaps
    MAX-ACCESS  read-only
    STATUS      current
    DESCRIPTION
        "The TYPE defines the transport service type as wrapper with wrapper layer termination OR else as payload" 
    ::=  { deployProvSuperChannelCapEntry 5 }

deployProvSuperChannelDefaultsTable  OBJECT-TYPE
    SYNTAX      SEQUENCE OF DeployProvSuperChannelDefaultsEntry
    MAX-ACCESS  not-accessible
    STATUS      current
    DESCRIPTION   "Contains entries for provisioning of OTLG."
    ::=  { facilityDeployProv 62  }

deployProvSuperChannelDefaultsEntry OBJECT-TYPE
    SYNTAX      DeployProvSuperChannelDefaultsEntry
    MAX-ACCESS  not-accessible
    STATUS      current
    DESCRIPTION   ""
    INDEX       { entityIndex }
    ::=  { deployProvSuperChannelDefaultsTable 1 }

DeployProvSuperChannelDefaultsEntry ::=  SEQUENCE
  { deployProvSuperChannelDefaultsRowStatus RowStatus,
    deployProvSuperChannelDefaultsEqlzAdmin FspR7EqlzAdminState,
    deployProvSuperChannelDefaultsAlias SnmpAdminString,
    deployProvSuperChannelDefaultsAdmin FspR7AdminState,
    deployProvSuperChannelDefaultsType FspR7InterfaceType }

deployProvSuperChannelDefaultsRowStatus OBJECT-TYPE
    SYNTAX      RowStatus
    MAX-ACCESS  read-only
    STATUS      current
    DESCRIPTION   "RowStatus"
    ::=  { deployProvSuperChannelDefaultsEntry 1 }

deployProvSuperChannelDefaultsEqlzAdmin OBJECT-TYPE
    SYNTAX      FspR7EqlzAdminState
    MAX-ACCESS  read-only
    STATUS      current
    DESCRIPTION
        "Scheduled Equalization Administration" 
    ::=  { deployProvSuperChannelDefaultsEntry 2 }

deployProvSuperChannelDefaultsAlias OBJECT-TYPE
    SYNTAX      SnmpAdminString
    MAX-ACCESS  read-only
    STATUS      current
    DESCRIPTION
        "User Applied Descriptor" 
    ::=  { deployProvSuperChannelDefaultsEntry 3 }

deployProvSuperChannelDefaultsAdmin OBJECT-TYPE
    SYNTAX      FspR7AdminState
    MAX-ACCESS  read-only
    STATUS      current
    DESCRIPTION
        "Administrative State is displayed in the GUI and Craft. Transition to Unassigend requires the entity to be deleted." 
    ::=  { deployProvSuperChannelDefaultsEntry 4 }

deployProvSuperChannelDefaultsType OBJECT-TYPE
    SYNTAX      FspR7InterfaceType
    MAX-ACCESS  read-only
    STATUS      current
    DESCRIPTION
        "The TYPE defines the transport service type as wrapper with wrapper layer termination OR else as payload" 
    ::=  { deployProvSuperChannelDefaultsEntry 5 }

deployProvConnType OBJECT-TYPE
    SYNTAX      FspR7TypeConnection
    MAX-ACCESS  read-write
    STATUS      current
    DESCRIPTION
        "Type of equipment connection"
    ::=  { connectionDeployProv 1 }

deployProvConnEndpointA OBJECT-TYPE
    SYNTAX      EntityIndex
    MAX-ACCESS  read-write
    STATUS      current
    DESCRIPTION   "FROM-end of equipment connection (jumper). FROM direction is significant only
         for 1WAY connections."
    ::=  { connectionDeployProv 2 }

deployProvConnEndpointB OBJECT-TYPE
    SYNTAX      EntityIndex
    MAX-ACCESS  read-write
    STATUS      current
    DESCRIPTION   "TO-end of equipment connection (jumper). TO direction
         is signaificant only for 1WAY"
    ::=  { connectionDeployProv 3 }

deployProvConnCommand OBJECT-TYPE
    SYNTAX      FspR7ConnCommand
    MAX-ACCESS  read-write
    STATUS      current
    DESCRIPTION   "This object is used to create or destroy rows in
         intraNeConnectionsTable. To create a row in
         that table, set this object to create(2) and deployConnType,
         deployConnEndpointA, deployConnEndpointB in one request.
         To remove a row set this object to destroy(3) and
         deployConnEndpointA in one request."
    ::=  { connectionDeployProv 4 }

deployProvConnState OBJECT-TYPE
    SYNTAX      FspR7StateConnection
    MAX-ACCESS  read-only
    STATUS      current
    DESCRIPTION   "State of the physical connection when creation of it ends with failure.
         When value is 0 (undefined) than it is agent internal error."
    ::=  { connectionDeployProv 5 }

deployProvConnCommandCounter OBJECT-TYPE
    SYNTAX      Unsigned32
    MAX-ACCESS  read-only
    STATUS      current
    DESCRIPTION   "Counter incremented when create command ends with failure."
    ::=  { connectionDeployProv 6 }

deployProvConnIndex OBJECT-TYPE
    SYNTAX      EntityIndex
    MAX-ACCESS  read-only
    STATUS      current
    DESCRIPTION   "Parameter cointain CONN index after 'create' command is invoked."
    ::=  { connectionDeployProv 7 }

deployProvConnStdCapFromTable OBJECT-TYPE
    SYNTAX      SEQUENCE OF DeployProvConnStdCapFromEntry
    MAX-ACCESS  not-accessible
    STATUS      current
    DESCRIPTION   "Table containing capabilities of parameters for standard physical
         connection. The first index is endpointA (FROM) and the second index is endpointB
         (TO)."
    ::=  { connectionDeployProv 8 }

deployProvConnStdCapFromEntry OBJECT-TYPE
    SYNTAX      DeployProvConnStdCapFromEntry
    MAX-ACCESS  not-accessible
    STATUS      current
    DESCRIPTION   ""
    INDEX       {
                  deployProvConnStdCapFromEndpointA,
                  deployProvConnStdCapFromEndpointB
                }
    ::=  { deployProvConnStdCapFromTable 1 }

DeployProvConnStdCapFromEntry ::=  SEQUENCE
  { deployProvConnStdCapFromEndpointA EntityIndex,
    deployProvConnStdCapFromEndpointB EntityIndex,
    deployProvConnStdCapFromType FspR7TypeConnectionCaps }

deployProvConnStdCapFromEndpointA OBJECT-TYPE
    SYNTAX      EntityIndex
    MAX-ACCESS  not-accessible
    STATUS      current
    DESCRIPTION   ""
    ::=  { deployProvConnStdCapFromEntry 1 }

deployProvConnStdCapFromEndpointB OBJECT-TYPE
    SYNTAX      EntityIndex
    MAX-ACCESS  not-accessible
    STATUS      current
    DESCRIPTION   ""
    ::=  { deployProvConnStdCapFromEntry 2 }

deployProvConnStdCapFromType OBJECT-TYPE
    SYNTAX      FspR7TypeConnectionCaps
    MAX-ACCESS  read-only
    STATUS      current
    DESCRIPTION   ""
    ::=  { deployProvConnStdCapFromEntry 3 }

deployProvConnStdCapToTable OBJECT-TYPE
    SYNTAX      SEQUENCE OF DeployProvConnStdCapToEntry
    MAX-ACCESS  not-accessible
    STATUS      current
    DESCRIPTION   "Table containing capabilities of parameters for standard physical
         connection. The first index is endpointB (TO) and the second index is endpointA
         (FROM)."
    ::=  { connectionDeployProv 9 }

deployProvConnStdCapToEntry OBJECT-TYPE
    SYNTAX      DeployProvConnStdCapToEntry
    MAX-ACCESS  not-accessible
    STATUS      current
    DESCRIPTION   ""
    INDEX       {
                  deployProvConnStdCapToEndpointB,
                  deployProvConnStdCapToEndpointA
                }
    ::=  { deployProvConnStdCapToTable 1 }

DeployProvConnStdCapToEntry ::=  SEQUENCE
  { deployProvConnStdCapToEndpointB EntityIndex,
    deployProvConnStdCapToEndpointA EntityIndex,
    deployProvConnStdCapToType FspR7TypeConnectionCaps }

deployProvConnStdCapToEndpointB OBJECT-TYPE
    SYNTAX      EntityIndex
    MAX-ACCESS  not-accessible
    STATUS      current
    DESCRIPTION   ""
    ::=  { deployProvConnStdCapToEntry 1 }

deployProvConnStdCapToEndpointA OBJECT-TYPE
    SYNTAX      EntityIndex
    MAX-ACCESS  not-accessible
    STATUS      current
    DESCRIPTION   ""
    ::=  { deployProvConnStdCapToEntry 2 }

deployProvConnStdCapToType OBJECT-TYPE
    SYNTAX      FspR7TypeConnectionCaps
    MAX-ACCESS  read-only
    STATUS      current
    DESCRIPTION   ""
    ::=  { deployProvConnStdCapToEntry 3 }

deployProvConnNonStdCapFromTable OBJECT-TYPE
    SYNTAX      SEQUENCE OF DeployProvConnNonStdCapFromEntry
    MAX-ACCESS  not-accessible
    STATUS      current
    DESCRIPTION   "Table containing capabilities of parameters for non standard physical
         connection. The first index is endpointA (FROM) and the second index is endpointB
         (TO)."
    ::=  { connectionDeployProv 10 }

deployProvConnNonStdCapFromEntry OBJECT-TYPE
    SYNTAX      DeployProvConnNonStdCapFromEntry
    MAX-ACCESS  not-accessible
    STATUS      current
    DESCRIPTION   ""
    INDEX       {
                  deployProvConnNonStdCapFromEndpointA,
                  deployProvConnNonStdCapFromEndpointB
                }
    ::=  { deployProvConnNonStdCapFromTable 1 }

DeployProvConnNonStdCapFromEntry ::=  SEQUENCE
  { deployProvConnNonStdCapFromEndpointA EntityIndex,
    deployProvConnNonStdCapFromEndpointB EntityIndex,
    deployProvConnNonStdCapFromType FspR7TypeConnectionCaps }

deployProvConnNonStdCapFromEndpointA OBJECT-TYPE
    SYNTAX      EntityIndex
    MAX-ACCESS  not-accessible
    STATUS      current
    DESCRIPTION   ""
    ::=  { deployProvConnNonStdCapFromEntry 1 }

deployProvConnNonStdCapFromEndpointB OBJECT-TYPE
    SYNTAX      EntityIndex
    MAX-ACCESS  not-accessible
    STATUS      current
    DESCRIPTION   ""
    ::=  { deployProvConnNonStdCapFromEntry 2 }

deployProvConnNonStdCapFromType OBJECT-TYPE
    SYNTAX      FspR7TypeConnectionCaps
    MAX-ACCESS  read-only
    STATUS      current
    DESCRIPTION   ""
    ::=  { deployProvConnNonStdCapFromEntry 3 }

deployProvConnNonStdCapToTable OBJECT-TYPE
    SYNTAX      SEQUENCE OF DeployProvConnNonStdCapToEntry
    MAX-ACCESS  not-accessible
    STATUS      current
    DESCRIPTION   "Table containing capabilities of parameters for non standard physical
         connection. The first index is endpointB (TO) and the second index is endpointA
         (FROM)."
    ::=  { connectionDeployProv 11 }

deployProvConnNonStdCapToEntry OBJECT-TYPE
    SYNTAX      DeployProvConnNonStdCapToEntry
    MAX-ACCESS  not-accessible
    STATUS      current
    DESCRIPTION   ""
    INDEX       {
                  deployProvConnNonStdCapToEndpointB,
                  deployProvConnNonStdCapToEndpointA
                }
    ::=  { deployProvConnNonStdCapToTable 1 }

DeployProvConnNonStdCapToEntry ::=  SEQUENCE
  { deployProvConnNonStdCapToEndpointB EntityIndex,
    deployProvConnNonStdCapToEndpointA EntityIndex,
    deployProvConnNonStdCapToType FspR7TypeConnectionCaps }

deployProvConnNonStdCapToEndpointB OBJECT-TYPE
    SYNTAX      EntityIndex
    MAX-ACCESS  not-accessible
    STATUS      current
    DESCRIPTION   ""
    ::=  { deployProvConnNonStdCapToEntry 1 }

deployProvConnNonStdCapToEndpointA OBJECT-TYPE
    SYNTAX      EntityIndex
    MAX-ACCESS  not-accessible
    STATUS      current
    DESCRIPTION   ""
    ::=  { deployProvConnNonStdCapToEntry 2 }

deployProvConnNonStdCapToType OBJECT-TYPE
    SYNTAX      FspR7TypeConnectionCaps
    MAX-ACCESS  read-only
    STATUS      current
    DESCRIPTION   ""
    ::=  { deployProvConnNonStdCapToEntry 3 }

crsConnUnusedFromPointsTable OBJECT-TYPE
    SYNTAX      SEQUENCE OF CrsConnUnusedFromPointsEntry
    MAX-ACCESS  not-accessible
    STATUS      current
    DESCRIPTION   "Table containing the unused startpoint which can be cross-connected."
    ::=  { crossConnectionDeployProv 1 }

crsConnUnusedFromPointsEntry OBJECT-TYPE
    SYNTAX      CrsConnUnusedFromPointsEntry
    MAX-ACCESS  not-accessible
    STATUS      current
    DESCRIPTION   ""
    INDEX       {
                  crsConnUnusedFromPointsAidValueFromPoint
                }
    ::=  { crsConnUnusedFromPointsTable 1 }

CrsConnUnusedFromPointsEntry ::=  SEQUENCE
  { crsConnUnusedFromPointsAidValueFromPoint EntityIndex }

crsConnUnusedFromPointsAidValueFromPoint OBJECT-TYPE
    SYNTAX      EntityIndex
    MAX-ACCESS  read-only
    STATUS      current
    DESCRIPTION   "Ports can be cross-connected."
    ::=  { crsConnUnusedFromPointsEntry 1 }

crsConnPossibleToCreateTable OBJECT-TYPE
    SYNTAX      SEQUENCE OF CrsConnPossibleToCreateEntry
    MAX-ACCESS  not-accessible
    STATUS      current
    DESCRIPTION   "Table containing possibly cross-connections."
    ::=  { crossConnectionDeployProv 2 }

crsConnPossibleToCreateEntry OBJECT-TYPE
    SYNTAX      CrsConnPossibleToCreateEntry
    MAX-ACCESS  not-accessible
    STATUS      current
    DESCRIPTION   ""
    INDEX       {
                  crsConnUnusedFromPointsAidValueFromPoint,
                  crsConnPossibleToCreateAidToFromPoint
                }
    ::=  { crsConnPossibleToCreateTable 1 }

CrsConnPossibleToCreateEntry ::=  SEQUENCE
  { crsConnPossibleToCreateAidToFromPoint EntityIndex }

crsConnPossibleToCreateAidToFromPoint OBJECT-TYPE
    SYNTAX      EntityIndex
    MAX-ACCESS  read-only
    STATUS      current
    DESCRIPTION   "Ports can be cross-connected."
    ::=  { crsConnPossibleToCreateEntry 1 }

crsConnDeployProvTable OBJECT-TYPE
    SYNTAX      SEQUENCE OF CrsConnDeployProvEntry
    MAX-ACCESS  not-accessible
    STATUS      current
    DESCRIPTION   "Contains entries for provisioning of cross-connections."
    ::=  { crossConnectionDeployProv 3 }

crsConnDeployProvEntry OBJECT-TYPE
    SYNTAX      CrsConnDeployProvEntry
    MAX-ACCESS  not-accessible
    STATUS      current
    DESCRIPTION   ""
    INDEX       {
                  crsConnDeployProvFrom,
                  crsConnDeployProvTo
                }
    ::=  { crsConnDeployProvTable 1 }

CrsConnDeployProvEntry ::=  SEQUENCE
  { crsConnDeployProvFrom EntityIndex,
    crsConnDeployProvTo EntityIndex,
    crsConnDeployProvRowStatus RowStatus,
    crsConnDeployProvConn FspR7Conn,
    crsConnDeployProvRedLineState FspR7RedLinedState,
    crsConnDeployProvAdmin FspR7AdminState,
    crsConnDeployProvTunnelAid SnmpAdminString,
    crsConnDeployProvAlias SnmpAdminString,
    crsConnDeployProvCrossConnType FspR7TypeCrs,
    crsConnDeployProvPathNode FspR7PathNode,
    crsConnDeployProvType FspR7InterfaceType }

crsConnDeployProvFrom OBJECT-TYPE
    SYNTAX      EntityIndex
    MAX-ACCESS  not-accessible
    STATUS      current
    DESCRIPTION
        "Source point (AID)" 
    ::=  { crsConnDeployProvEntry 1 }

crsConnDeployProvTo OBJECT-TYPE
    SYNTAX      EntityIndex
    MAX-ACCESS  not-accessible
    STATUS      current
    DESCRIPTION
        "Destination point (AID)" 
    ::=  { crsConnDeployProvEntry 2 }

crsConnDeployProvRowStatus OBJECT-TYPE
    SYNTAX      RowStatus
    MAX-ACCESS  read-write
    STATUS      current
    DESCRIPTION   "This object is used to create, or delete a row in this table. To start process of creating
         a new cross-connection, this object is initially set to 'createAndWait'. After this action the state of
         this object becomes 'notReady'. This object stays in this state until all required objects are not set.
         Objects which must be set are indicated by special objects with capabilities. If specjal object exist,
         the indicated object have to be set by one of values specified in special object. If all required objects
         are set, state of this object becomes 'notInService'. To create a new cross-connection, this object have
         to be set to 'active'."
    ::=  { crsConnDeployProvEntry 3 }

crsConnDeployProvConn OBJECT-TYPE
    SYNTAX      FspR7Conn
    MAX-ACCESS  read-write
    STATUS      current
    DESCRIPTION   "Connection Direction"
    ::=  { crsConnDeployProvEntry 4 }

crsConnDeployProvRedLineState OBJECT-TYPE
    SYNTAX      FspR7RedLinedState
    MAX-ACCESS  read-write
    STATUS      current
    DESCRIPTION
        "will be set by higher level software to act as a barrier to deletion" 
    ::=  { crsConnDeployProvEntry 5 }

crsConnDeployProvAdmin OBJECT-TYPE
    SYNTAX      FspR7AdminState
    MAX-ACCESS  read-write
    STATUS      current
    DESCRIPTION
        "Administrative State is displayed in the GUI and Craft. Transition to Unassigend requires the entity to be deleted." 
    ::=  { crsConnDeployProvEntry 6 }

crsConnDeployProvTunnelAid OBJECT-TYPE
    SYNTAX      SnmpAdminString
    MAX-ACCESS  read-write
    STATUS      current
    DESCRIPTION
        "Tunnel AID" 
    ::=  { crsConnDeployProvEntry 7 }

crsConnDeployProvAlias OBJECT-TYPE
    SYNTAX      SnmpAdminString
    MAX-ACCESS  read-write
    STATUS      current
    DESCRIPTION
        "User Applied Descriptor" 
    ::=  { crsConnDeployProvEntry 8 }

crsConnDeployProvCrossConnType OBJECT-TYPE
    SYNTAX      FspR7TypeCrs
    MAX-ACCESS  read-write
    STATUS      current
    DESCRIPTION
        "Type of Cross-Connect" 
    ::=  { crsConnDeployProvEntry 9 }

crsConnDeployProvPathNode OBJECT-TYPE
    SYNTAX      FspR7PathNode
    MAX-ACCESS  read-write
    STATUS      current
    DESCRIPTION   "Node count along a signal path on a unidirectional basis from the client signal
         ingress to egress"
    ::=  { crsConnDeployProvEntry 10 }

crsConnDeployProvType OBJECT-TYPE
    SYNTAX      FspR7InterfaceType
    MAX-ACCESS  read-write
    STATUS      current
    DESCRIPTION   ""
    ::=  { crsConnDeployProvEntry 11 }

crsConnDeployProvCapTable OBJECT-TYPE
    SYNTAX      SEQUENCE OF CrsConnDeployProvCapEntry
    MAX-ACCESS  not-accessible
    STATUS      current
    DESCRIPTION   "Contains entries for provisioning of cross-connections."
    ::=  { crossConnectionDeployProv 4  }

crsConnDeployProvCapEntry OBJECT-TYPE
    SYNTAX      CrsConnDeployProvCapEntry
    MAX-ACCESS  not-accessible
    STATUS      current
    DESCRIPTION   ""
    INDEX       { crsConnDeployProvFrom,
                  crsConnDeployProvTo }
    ::=  { crsConnDeployProvCapTable 1 }

CrsConnDeployProvCapEntry ::=  SEQUENCE
  { crsConnDeployProvCapFrom Integer32,
    crsConnDeployProvCapTo Integer32,
    crsConnDeployProvCapRowStatus FspR7RowStatusCaps,
    crsConnDeployProvCapConn FspR7ConnCaps,
    crsConnDeployProvCapRedLineState FspR7RedLinedStateCaps,
    crsConnDeployProvCapAdmin FspR7AdminStateCaps,
    crsConnDeployProvCapTunnelAid Integer32,
    crsConnDeployProvCapAlias Integer32,
    crsConnDeployProvCapCrossConnType FspR7TypeCrsCaps,
    crsConnDeployProvCapPathNode FspR7PathNodeCaps,
    crsConnDeployProvCapType FspR7InterfaceTypeCaps }

crsConnDeployProvCapFrom OBJECT-TYPE
    SYNTAX      Integer32
    MAX-ACCESS  not-accessible
    STATUS      current
    DESCRIPTION
        "Source point (AID)" 
    ::=  { crsConnDeployProvCapEntry 1 }

crsConnDeployProvCapTo OBJECT-TYPE
    SYNTAX      Integer32
    MAX-ACCESS  not-accessible
    STATUS      current
    DESCRIPTION
        "Destination point (AID)" 
    ::=  { crsConnDeployProvCapEntry 2 }

crsConnDeployProvCapRowStatus OBJECT-TYPE
    SYNTAX      FspR7RowStatusCaps
    MAX-ACCESS  read-only
    STATUS      current
    DESCRIPTION   "This object is used to create, or delete a row in this table. To start process of creating
         a new cross-connection, this object is initially set to 'createAndWait'. After this action the state of
         this object becomes 'notReady'. This object stays in this state until all required objects are not set.
         Objects which must be set are indicated by special objects with capabilities. If specjal object exist,
         the indicated object have to be set by one of values specified in special object. If all required objects
         are set, state of this object becomes 'notInService'. To create a new cross-connection, this object have
         to be set to 'active'."
    ::=  { crsConnDeployProvCapEntry 3 }

crsConnDeployProvCapConn OBJECT-TYPE
    SYNTAX      FspR7ConnCaps
    MAX-ACCESS  read-only
    STATUS      current
    DESCRIPTION   "Connection Direction"
    ::=  { crsConnDeployProvCapEntry 4 }

crsConnDeployProvCapRedLineState OBJECT-TYPE
    SYNTAX      FspR7RedLinedStateCaps
    MAX-ACCESS  read-only
    STATUS      current
    DESCRIPTION
        "will be set by higher level software to act as a barrier to deletion" 
    ::=  { crsConnDeployProvCapEntry 5 }

crsConnDeployProvCapAdmin OBJECT-TYPE
    SYNTAX      FspR7AdminStateCaps
    MAX-ACCESS  read-only
    STATUS      current
    DESCRIPTION
        "Administrative State is displayed in the GUI and Craft. Transition to Unassigend requires the entity to be deleted." 
    ::=  { crsConnDeployProvCapEntry 6 }

crsConnDeployProvCapTunnelAid OBJECT-TYPE
    SYNTAX      Integer32
    MAX-ACCESS  read-only
    STATUS      current
    DESCRIPTION
        "Tunnel AID" 
    ::=  { crsConnDeployProvCapEntry 7 }

crsConnDeployProvCapAlias OBJECT-TYPE
    SYNTAX      Integer32
    MAX-ACCESS  read-only
    STATUS      current
    DESCRIPTION
        "User Applied Descriptor" 
    ::=  { crsConnDeployProvCapEntry 8 }

crsConnDeployProvCapCrossConnType OBJECT-TYPE
    SYNTAX      FspR7TypeCrsCaps
    MAX-ACCESS  read-only
    STATUS      current
    DESCRIPTION
        "Type of Cross-Connect" 
    ::=  { crsConnDeployProvCapEntry 9 }

crsConnDeployProvCapPathNode OBJECT-TYPE
    SYNTAX      FspR7PathNodeCaps
    MAX-ACCESS  read-only
    STATUS      current
    DESCRIPTION   "Node count along a signal path on a unidirectional basis from the client signal
         ingress to egress"
    ::=  { crsConnDeployProvCapEntry 10 }

crsConnDeployProvCapType OBJECT-TYPE
    SYNTAX      FspR7InterfaceTypeCaps
    MAX-ACCESS  read-only
    STATUS      current
    DESCRIPTION   ""
    ::=  { crsConnDeployProvCapEntry 11 }

crsConnDeployProvDefaultsTable  OBJECT-TYPE
    SYNTAX      SEQUENCE OF CrsConnDeployProvDefaultsEntry
    MAX-ACCESS  not-accessible
    STATUS      current
    DESCRIPTION   "Contains entries for provisioning of cross-connections."
    ::=  { crossConnectionDeployProv 5  }

crsConnDeployProvDefaultsEntry OBJECT-TYPE
    SYNTAX      CrsConnDeployProvDefaultsEntry
    MAX-ACCESS  not-accessible
    STATUS      current
    DESCRIPTION   ""
    INDEX       { crsConnDeployProvFrom,
                  crsConnDeployProvTo }
    ::=  { crsConnDeployProvDefaultsTable 1 }

CrsConnDeployProvDefaultsEntry ::=  SEQUENCE
  { crsConnDeployProvDefaultsFrom EntityIndex,
    crsConnDeployProvDefaultsTo EntityIndex,
    crsConnDeployProvDefaultsRowStatus RowStatus,
    crsConnDeployProvDefaultsConn FspR7Conn,
    crsConnDeployProvDefaultsRedLineState FspR7RedLinedState,
    crsConnDeployProvDefaultsAdmin FspR7AdminState,
    crsConnDeployProvDefaultsTunnelAid SnmpAdminString,
    crsConnDeployProvDefaultsAlias SnmpAdminString,
    crsConnDeployProvDefaultsCrossConnType FspR7TypeCrs,
    crsConnDeployProvDefaultsPathNode FspR7PathNode,
    crsConnDeployProvDefaultsType FspR7InterfaceType }

crsConnDeployProvDefaultsFrom OBJECT-TYPE
    SYNTAX      EntityIndex
    MAX-ACCESS  read-only
    STATUS      current
    DESCRIPTION
        "Source point (AID)" 
    ::=  { crsConnDeployProvDefaultsEntry 1 }

crsConnDeployProvDefaultsTo OBJECT-TYPE
    SYNTAX      EntityIndex
    MAX-ACCESS  read-only
    STATUS      current
    DESCRIPTION
        "Destination point (AID)" 
    ::=  { crsConnDeployProvDefaultsEntry 2 }

crsConnDeployProvDefaultsRowStatus OBJECT-TYPE
    SYNTAX      RowStatus
    MAX-ACCESS  read-only
    STATUS      current
    DESCRIPTION   "This object is used to create, or delete a row in this table. To start process of creating
         a new cross-connection, this object is initially set to 'createAndWait'. After this action the state of
         this object becomes 'notReady'. This object stays in this state until all required objects are not set.
         Objects which must be set are indicated by special objects with capabilities. If specjal object exist,
         the indicated object have to be set by one of values specified in special object. If all required objects
         are set, state of this object becomes 'notInService'. To create a new cross-connection, this object have
         to be set to 'active'."
    ::=  { crsConnDeployProvDefaultsEntry 3 }

crsConnDeployProvDefaultsConn OBJECT-TYPE
    SYNTAX      FspR7Conn
    MAX-ACCESS  read-only
    STATUS      current
    DESCRIPTION   "Connection Direction"
    ::=  { crsConnDeployProvDefaultsEntry 4 }

crsConnDeployProvDefaultsRedLineState OBJECT-TYPE
    SYNTAX      FspR7RedLinedState
    MAX-ACCESS  read-only
    STATUS      current
    DESCRIPTION
        "will be set by higher level software to act as a barrier to deletion" 
    ::=  { crsConnDeployProvDefaultsEntry 5 }

crsConnDeployProvDefaultsAdmin OBJECT-TYPE
    SYNTAX      FspR7AdminState
    MAX-ACCESS  read-only
    STATUS      current
    DESCRIPTION
        "Administrative State is displayed in the GUI and Craft. Transition to Unassigend requires the entity to be deleted." 
    ::=  { crsConnDeployProvDefaultsEntry 6 }

crsConnDeployProvDefaultsTunnelAid OBJECT-TYPE
    SYNTAX      SnmpAdminString
    MAX-ACCESS  read-only
    STATUS      current
    DESCRIPTION
        "Tunnel AID" 
    ::=  { crsConnDeployProvDefaultsEntry 7 }

crsConnDeployProvDefaultsAlias OBJECT-TYPE
    SYNTAX      SnmpAdminString
    MAX-ACCESS  read-only
    STATUS      current
    DESCRIPTION
        "User Applied Descriptor" 
    ::=  { crsConnDeployProvDefaultsEntry 8 }

crsConnDeployProvDefaultsCrossConnType OBJECT-TYPE
    SYNTAX      FspR7TypeCrs
    MAX-ACCESS  read-only
    STATUS      current
    DESCRIPTION
        "Type of Cross-Connect" 
    ::=  { crsConnDeployProvDefaultsEntry 9 }

crsConnDeployProvDefaultsPathNode OBJECT-TYPE
    SYNTAX      FspR7PathNode
    MAX-ACCESS  read-only
    STATUS      current
    DESCRIPTION   "Node count along a signal path on a unidirectional basis from the client signal
         ingress to egress"
    ::=  { crsConnDeployProvDefaultsEntry 10 }

crsConnDeployProvDefaultsType OBJECT-TYPE
    SYNTAX      FspR7InterfaceType
    MAX-ACCESS  read-only
    STATUS      current
    DESCRIPTION   ""
    ::=  { crsConnDeployProvDefaultsEntry 11 }

crsConnWdmUnusedFromPointsTable OBJECT-TYPE
    SYNTAX      SEQUENCE OF CrsConnWdmUnusedFromPointsEntry
    MAX-ACCESS  not-accessible
    STATUS      current
    DESCRIPTION   "Table containing the unused startpoint which can be cross-connected."
    ::=  { crossConnectionDeployProv 6 }

crsConnWdmUnusedFromPointsEntry OBJECT-TYPE
    SYNTAX      CrsConnWdmUnusedFromPointsEntry
    MAX-ACCESS  not-accessible
    STATUS      current
    DESCRIPTION   ""
    INDEX       {
                  crsConnWdmUnusedFromPointsAidValueFromPoint
                }
    ::=  { crsConnWdmUnusedFromPointsTable 1 }

CrsConnWdmUnusedFromPointsEntry ::=  SEQUENCE
  { crsConnWdmUnusedFromPointsAidValueFromPoint EntityIndex }

crsConnWdmUnusedFromPointsAidValueFromPoint OBJECT-TYPE
    SYNTAX      EntityIndex
    MAX-ACCESS  read-only
    STATUS      current
    DESCRIPTION   "Ports can be cross-connected."
    ::=  { crsConnWdmUnusedFromPointsEntry 1 }

cloningTable OBJECT-TYPE
    SYNTAX      SEQUENCE OF CloningEntry
    MAX-ACCESS  not-accessible
    STATUS      current
    DESCRIPTION   "Table containing all free entities"
    ::=  { cloningEntitiesDeployProv 1 }

cloningEntry OBJECT-TYPE
    SYNTAX      CloningEntry
    MAX-ACCESS  not-accessible
    STATUS      current
    DESCRIPTION   ""
    INDEX       {
                  entityIndex
                }
    ::=  { cloningTable 1 }

CloningEntry ::=  SEQUENCE
  { cloningSource EntityIndex }

cloningSource OBJECT-TYPE
    SYNTAX      EntityIndex
    MAX-ACCESS  read-write
    STATUS      current
    DESCRIPTION   ""
    ::=  { cloningEntry 1 }

entitiesToCloningTable OBJECT-TYPE
    SYNTAX      SEQUENCE OF EntitiesToCloningEntry
    MAX-ACCESS  not-accessible
    STATUS      current
    DESCRIPTION   "Table containing entities which should be cloned from source entity"
    ::=  { cloningEntitiesDeployProv 2 }

entitiesToCloningEntry OBJECT-TYPE
    SYNTAX      EntitiesToCloningEntry
    MAX-ACCESS  not-accessible
    STATUS      current
    DESCRIPTION   ""
    INDEX       {
                  entityIndex,
                  entitiesToCloningEntity
                }
    ::=  { entitiesToCloningTable 1 }

EntitiesToCloningEntry ::=  SEQUENCE
  { entitiesToCloningEntity EntityIndex }

entitiesToCloningEntity OBJECT-TYPE
    SYNTAX      EntityIndex
    MAX-ACCESS  read-only
    STATUS      current
    DESCRIPTION   ""
    ::=  { entitiesToCloningEntry 1 }

forceDeployProvApsTable OBJECT-TYPE
    SYNTAX      SEQUENCE OF ForceDeployProvApsEntry
    MAX-ACCESS  not-accessible
    STATUS      current
    DESCRIPTION   ""
    ::=  { cloningEntitiesDeployProv 3 }

forceDeployProvApsEntry OBJECT-TYPE
    SYNTAX      ForceDeployProvApsEntry
    MAX-ACCESS  not-accessible
    STATUS      current
    DESCRIPTION   ""
    INDEX       {
                  entityIndex
                }
    ::=  { forceDeployProvApsTable 1 }

ForceDeployProvApsEntry ::=  SEQUENCE
  { forceDeployProvApsRowStatus RowStatus,
    forceDeployProvApsForceDestroy FspR7ForcedStatus,
    forceDeployProvApsSDswitching EnableState,
    forceDeployProvApsHoldOffTime ApsHoldoffTime,
    forceDeployProvApsProtectionMech ProtectionMech,
    forceDeployProvApsWorkingAid EntityIndex,
    forceDeployProvApsProtectionAid EntityIndex,
    forceDeployProvApsSignalDegradeSwitching EnableState,
    forceDeployProvApsSignalFailureSwitching EnableState,
    forceDeployProvApsFarEndIp IpAddress,
    forceDeployProvApsPeerAid EntityIndex,
    forceDeployProvApsApsType ApsType,
    forceDeployProvApsRevertMode ApsRevertMode,
    forceDeployProvApsWaitToRestore Unsigned32,
    forceDeployProvApsDirection ApsDirection }

forceDeployProvApsRowStatus OBJECT-TYPE
    SYNTAX      RowStatus
    MAX-ACCESS  read-write
    STATUS      current
    DESCRIPTION   "RowStatus"
    ::=  { forceDeployProvApsEntry 1 }

forceDeployProvApsForceDestroy OBJECT-TYPE
    SYNTAX      FspR7ForcedStatus
    MAX-ACCESS  read-write
    STATUS      current
    DESCRIPTION
        "Forced Destroy" 
    ::=  { forceDeployProvApsEntry 2 }

forceDeployProvApsSDswitching OBJECT-TYPE
    SYNTAX      EnableState
    MAX-ACCESS  read-write
    STATUS      current
    DESCRIPTION   "This state controls whether the switch criteria for the APS group will
         include the Signal Degrade alarm."
    ::=  { forceDeployProvApsEntry 3 }

forceDeployProvApsHoldOffTime OBJECT-TYPE
    SYNTAX      ApsHoldoffTime
    MAX-ACCESS  read-write
    STATUS      current
    DESCRIPTION   "This value controls the switch delay (0 to 10 seconds in
         100ms steps) for the protection group. Changing the hold-off
         time when the timer is active will not affect the active
         timer. The change will take effect the next time the timer
         is active."
    ::=  { forceDeployProvApsEntry 4 }

forceDeployProvApsProtectionMech OBJECT-TYPE
    SYNTAX      ProtectionMech
    MAX-ACCESS  read-write
    STATUS      current
    DESCRIPTION   "The protection type of this protection group."
    ::=  { forceDeployProvApsEntry 5 }

forceDeployProvApsWorkingAid OBJECT-TYPE
    SYNTAX      EntityIndex
    MAX-ACCESS  read-write
    STATUS      current
    DESCRIPTION
        "AID of working port involved in the protection group." 
    ::=  { forceDeployProvApsEntry 6 }

forceDeployProvApsProtectionAid OBJECT-TYPE
    SYNTAX      EntityIndex
    MAX-ACCESS  read-write
    STATUS      current
    DESCRIPTION
        "(Protection AID) AID of protection entity involved in the protection group." 
    ::=  { forceDeployProvApsEntry 7 }

forceDeployProvApsSignalDegradeSwitching OBJECT-TYPE
    SYNTAX      EnableState
    MAX-ACCESS  read-write
    STATUS      current
    DESCRIPTION
        "Switch Trigger Additionally on Signal Degrade Link Detection" 
    ::=  { forceDeployProvApsEntry 8 }

forceDeployProvApsSignalFailureSwitching OBJECT-TYPE
    SYNTAX      EnableState
    MAX-ACCESS  read-write
    STATUS      current
    DESCRIPTION
        "Switch Trigger on Signal Failure Link Detection" 
    ::=  { forceDeployProvApsEntry 9 }

forceDeployProvApsFarEndIp OBJECT-TYPE
    SYNTAX      IpAddress
    MAX-ACCESS  read-write
    STATUS      current
    DESCRIPTION   "IP Address assigned to PPP Termination Point on Far-End NE. Default
         is set by NE System on LINK establishment if FENDIPACPT = Y"
    ::=  { forceDeployProvApsEntry 10 }

forceDeployProvApsPeerAid OBJECT-TYPE
    SYNTAX      EntityIndex
    MAX-ACCESS  read-write
    STATUS      current
    DESCRIPTION
        "AID of Protection Partner involved in the protection group." 
    ::=  { forceDeployProvApsEntry 11 }

forceDeployProvApsApsType OBJECT-TYPE
    SYNTAX      ApsType
    MAX-ACCESS  read-write
    STATUS      current
    DESCRIPTION   "The type of APS implemented in this protection group."
    ::=  { forceDeployProvApsEntry 12 }

forceDeployProvApsRevertMode OBJECT-TYPE
    SYNTAX      ApsRevertMode
    MAX-ACCESS  read-write
    STATUS      current
    DESCRIPTION
        "Revertive Protection Switching" 
    ::=  { forceDeployProvApsEntry 13 }

forceDeployProvApsWaitToRestore OBJECT-TYPE
    SYNTAX      Unsigned32 (5..12 | 4294967295) 
    UNITS       "min"
    MAX-ACCESS  read-write
    STATUS      current
    DESCRIPTION
        "Wait to Restore Timer value" 
    ::=  { forceDeployProvApsEntry 14 }

forceDeployProvApsDirection OBJECT-TYPE
    SYNTAX      ApsDirection
    MAX-ACCESS  read-write
    STATUS      current
    DESCRIPTION   "Indicates whether the APS function is 'unidirectional' (single-ended)
         or 'bidirectional' (dual-ended)."
    ::=  { forceDeployProvApsEntry 15 }

forceDeployProvApsCapTable OBJECT-TYPE
    SYNTAX      SEQUENCE OF ForceDeployProvApsCapEntry
    MAX-ACCESS  not-accessible
    STATUS      current
    DESCRIPTION   ""
    ::=  { cloningEntitiesDeployProv 4  }

forceDeployProvApsCapEntry OBJECT-TYPE
    SYNTAX      ForceDeployProvApsCapEntry
    MAX-ACCESS  not-accessible
    STATUS      current
    DESCRIPTION   ""
    INDEX       { entityIndex }
    ::=  { forceDeployProvApsCapTable 1 }

ForceDeployProvApsCapEntry ::=  SEQUENCE
  { forceDeployProvApsCapRowStatus FspR7RowStatusCaps,
    forceDeployProvApsCapForceDestroy FspR7ForcedStatusCaps,
    forceDeployProvApsCapSDswitching EnableStateCaps,
    forceDeployProvApsCapHoldOffTime ApsHoldoffTimeCaps,
    forceDeployProvApsCapProtectionMech ProtectionMechCaps,
    forceDeployProvApsCapWorkingAid Integer32,
    forceDeployProvApsCapProtectionAid Integer32,
    forceDeployProvApsCapSignalDegradeSwitching EnableStateCaps,
    forceDeployProvApsCapSignalFailureSwitching EnableStateCaps,
    forceDeployProvApsCapFarEndIp FspR7YesNo,
    forceDeployProvApsCapPeerAid Integer32,
    forceDeployProvApsCapApsType ApsTypeCaps,
    forceDeployProvApsCapRevertMode ApsRevertModeCaps,
    forceDeployProvApsCapWaitToRestore FspR7Unsigned32Caps,
    forceDeployProvApsCapDirection ApsDirectionCaps }

forceDeployProvApsCapRowStatus OBJECT-TYPE
    SYNTAX      FspR7RowStatusCaps
    MAX-ACCESS  read-only
    STATUS      current
    DESCRIPTION   "RowStatus"
    ::=  { forceDeployProvApsCapEntry 1 }

forceDeployProvApsCapForceDestroy OBJECT-TYPE
    SYNTAX      FspR7ForcedStatusCaps
    MAX-ACCESS  read-only
    STATUS      current
    DESCRIPTION
        "Forced Destroy" 
    ::=  { forceDeployProvApsCapEntry 2 }

forceDeployProvApsCapSDswitching OBJECT-TYPE
    SYNTAX      EnableStateCaps
    MAX-ACCESS  read-only
    STATUS      current
    DESCRIPTION   "This state controls whether the switch criteria for the APS group will
         include the Signal Degrade alarm."
    ::=  { forceDeployProvApsCapEntry 3 }

forceDeployProvApsCapHoldOffTime OBJECT-TYPE
    SYNTAX      ApsHoldoffTimeCaps
    MAX-ACCESS  read-only
    STATUS      current
    DESCRIPTION   "This value controls the switch delay (0 to 10 seconds in
         100ms steps) for the protection group. Changing the hold-off
         time when the timer is active will not affect the active
         timer. The change will take effect the next time the timer
         is active."
    ::=  { forceDeployProvApsCapEntry 4 }

forceDeployProvApsCapProtectionMech OBJECT-TYPE
    SYNTAX      ProtectionMechCaps
    MAX-ACCESS  read-only
    STATUS      current
    DESCRIPTION   "The protection type of this protection group."
    ::=  { forceDeployProvApsCapEntry 5 }

forceDeployProvApsCapWorkingAid OBJECT-TYPE
    SYNTAX      Integer32
    MAX-ACCESS  read-only
    STATUS      current
    DESCRIPTION
        "AID of working port involved in the protection group." 
    ::=  { forceDeployProvApsCapEntry 6 }

forceDeployProvApsCapProtectionAid OBJECT-TYPE
    SYNTAX      Integer32
    MAX-ACCESS  read-only
    STATUS      current
    DESCRIPTION
        "(Protection AID) AID of protection entity involved in the protection group." 
    ::=  { forceDeployProvApsCapEntry 7 }

forceDeployProvApsCapSignalDegradeSwitching OBJECT-TYPE
    SYNTAX      EnableStateCaps
    MAX-ACCESS  read-only
    STATUS      current
    DESCRIPTION
        "Switch Trigger Additionally on Signal Degrade Link Detection" 
    ::=  { forceDeployProvApsCapEntry 8 }

forceDeployProvApsCapSignalFailureSwitching OBJECT-TYPE
    SYNTAX      EnableStateCaps
    MAX-ACCESS  read-only
    STATUS      current
    DESCRIPTION
        "Switch Trigger on Signal Failure Link Detection" 
    ::=  { forceDeployProvApsCapEntry 9 }

forceDeployProvApsCapFarEndIp OBJECT-TYPE
    SYNTAX      FspR7YesNo
    MAX-ACCESS  read-only
    STATUS      current
    DESCRIPTION   "IP Address assigned to PPP Termination Point on Far-End NE. Default
         is set by NE System on LINK establishment if FENDIPACPT = Y"
    ::=  { forceDeployProvApsCapEntry 10 }

forceDeployProvApsCapPeerAid OBJECT-TYPE
    SYNTAX      Integer32
    MAX-ACCESS  read-only
    STATUS      current
    DESCRIPTION
        "AID of Protection Partner involved in the protection group." 
    ::=  { forceDeployProvApsCapEntry 11 }

forceDeployProvApsCapApsType OBJECT-TYPE
    SYNTAX      ApsTypeCaps
    MAX-ACCESS  read-only
    STATUS      current
    DESCRIPTION   "The type of APS implemented in this protection group."
    ::=  { forceDeployProvApsCapEntry 12 }

forceDeployProvApsCapRevertMode OBJECT-TYPE
    SYNTAX      ApsRevertModeCaps
    MAX-ACCESS  read-only
    STATUS      current
    DESCRIPTION
        "Revertive Protection Switching" 
    ::=  { forceDeployProvApsCapEntry 13 }

forceDeployProvApsCapWaitToRestore OBJECT-TYPE
    SYNTAX      FspR7Unsigned32Caps
    UNITS       "min"
    MAX-ACCESS  read-only
    STATUS      current
    DESCRIPTION
        "Wait to Restore Timer value" 
    ::=  { forceDeployProvApsCapEntry 14 }

forceDeployProvApsCapDirection OBJECT-TYPE
    SYNTAX      ApsDirectionCaps
    MAX-ACCESS  read-only
    STATUS      current
    DESCRIPTION   "Indicates whether the APS function is 'unidirectional' (single-ended)
         or 'bidirectional' (dual-ended)."
    ::=  { forceDeployProvApsCapEntry 15 }

forceDeployProvApsDefaultsTable  OBJECT-TYPE
    SYNTAX      SEQUENCE OF ForceDeployProvApsDefaultsEntry
    MAX-ACCESS  not-accessible
    STATUS      current
    DESCRIPTION   ""
    ::=  { cloningEntitiesDeployProv 5  }

forceDeployProvApsDefaultsEntry OBJECT-TYPE
    SYNTAX      ForceDeployProvApsDefaultsEntry
    MAX-ACCESS  not-accessible
    STATUS      current
    DESCRIPTION   ""
    INDEX       { entityIndex }
    ::=  { forceDeployProvApsDefaultsTable 1 }

ForceDeployProvApsDefaultsEntry ::=  SEQUENCE
  { forceDeployProvApsDefaultsRowStatus RowStatus,
    forceDeployProvApsDefaultsForceDestroy FspR7ForcedStatus,
    forceDeployProvApsDefaultsSDswitching EnableState,
    forceDeployProvApsDefaultsHoldOffTime ApsHoldoffTime,
    forceDeployProvApsDefaultsProtectionMech ProtectionMech,
    forceDeployProvApsDefaultsWorkingAid EntityIndex,
    forceDeployProvApsDefaultsProtectionAid EntityIndex,
    forceDeployProvApsDefaultsSignalDegradeSwitching EnableState,
    forceDeployProvApsDefaultsSignalFailureSwitching EnableState,
    forceDeployProvApsDefaultsFarEndIp IpAddress,
    forceDeployProvApsDefaultsPeerAid EntityIndex,
    forceDeployProvApsDefaultsApsType ApsType,
    forceDeployProvApsDefaultsRevertMode ApsRevertMode,
    forceDeployProvApsDefaultsWaitToRestore Unsigned32,
    forceDeployProvApsDefaultsDirection ApsDirection }

forceDeployProvApsDefaultsRowStatus OBJECT-TYPE
    SYNTAX      RowStatus
    MAX-ACCESS  read-only
    STATUS      current
    DESCRIPTION   "RowStatus"
    ::=  { forceDeployProvApsDefaultsEntry 1 }

forceDeployProvApsDefaultsForceDestroy OBJECT-TYPE
    SYNTAX      FspR7ForcedStatus
    MAX-ACCESS  read-only
    STATUS      current
    DESCRIPTION
        "Forced Destroy" 
    ::=  { forceDeployProvApsDefaultsEntry 2 }

forceDeployProvApsDefaultsSDswitching OBJECT-TYPE
    SYNTAX      EnableState
    MAX-ACCESS  read-only
    STATUS      current
    DESCRIPTION   "This state controls whether the switch criteria for the APS group will
         include the Signal Degrade alarm."
    ::=  { forceDeployProvApsDefaultsEntry 3 }

forceDeployProvApsDefaultsHoldOffTime OBJECT-TYPE
    SYNTAX      ApsHoldoffTime
    MAX-ACCESS  read-only
    STATUS      current
    DESCRIPTION   "This value controls the switch delay (0 to 10 seconds in
         100ms steps) for the protection group. Changing the hold-off
         time when the timer is active will not affect the active
         timer. The change will take effect the next time the timer
         is active."
    ::=  { forceDeployProvApsDefaultsEntry 4 }

forceDeployProvApsDefaultsProtectionMech OBJECT-TYPE
    SYNTAX      ProtectionMech
    MAX-ACCESS  read-only
    STATUS      current
    DESCRIPTION   "The protection type of this protection group."
    ::=  { forceDeployProvApsDefaultsEntry 5 }

forceDeployProvApsDefaultsWorkingAid OBJECT-TYPE
    SYNTAX      EntityIndex
    MAX-ACCESS  read-only
    STATUS      current
    DESCRIPTION
        "AID of working port involved in the protection group." 
    ::=  { forceDeployProvApsDefaultsEntry 6 }

forceDeployProvApsDefaultsProtectionAid OBJECT-TYPE
    SYNTAX      EntityIndex
    MAX-ACCESS  read-only
    STATUS      current
    DESCRIPTION
        "(Protection AID) AID of protection entity involved in the protection group." 
    ::=  { forceDeployProvApsDefaultsEntry 7 }

forceDeployProvApsDefaultsSignalDegradeSwitching OBJECT-TYPE
    SYNTAX      EnableState
    MAX-ACCESS  read-only
    STATUS      current
    DESCRIPTION
        "Switch Trigger Additionally on Signal Degrade Link Detection" 
    ::=  { forceDeployProvApsDefaultsEntry 8 }

forceDeployProvApsDefaultsSignalFailureSwitching OBJECT-TYPE
    SYNTAX      EnableState
    MAX-ACCESS  read-only
    STATUS      current
    DESCRIPTION
        "Switch Trigger on Signal Failure Link Detection" 
    ::=  { forceDeployProvApsDefaultsEntry 9 }

forceDeployProvApsDefaultsFarEndIp OBJECT-TYPE
    SYNTAX      IpAddress
    MAX-ACCESS  read-only
    STATUS      current
    DESCRIPTION   "IP Address assigned to PPP Termination Point on Far-End NE. Default
         is set by NE System on LINK establishment if FENDIPACPT = Y"
    ::=  { forceDeployProvApsDefaultsEntry 10 }

forceDeployProvApsDefaultsPeerAid OBJECT-TYPE
    SYNTAX      EntityIndex
    MAX-ACCESS  read-only
    STATUS      current
    DESCRIPTION
        "AID of Protection Partner involved in the protection group." 
    ::=  { forceDeployProvApsDefaultsEntry 11 }

forceDeployProvApsDefaultsApsType OBJECT-TYPE
    SYNTAX      ApsType
    MAX-ACCESS  read-only
    STATUS      current
    DESCRIPTION   "The type of APS implemented in this protection group."
    ::=  { forceDeployProvApsDefaultsEntry 12 }

forceDeployProvApsDefaultsRevertMode OBJECT-TYPE
    SYNTAX      ApsRevertMode
    MAX-ACCESS  read-only
    STATUS      current
    DESCRIPTION
        "Revertive Protection Switching" 
    ::=  { forceDeployProvApsDefaultsEntry 13 }

forceDeployProvApsDefaultsWaitToRestore OBJECT-TYPE
    SYNTAX      Unsigned32 (5..12 | 4294967295) 
    UNITS       "min"
    MAX-ACCESS  read-only
    STATUS      current
    DESCRIPTION
        "Wait to Restore Timer value" 
    ::=  { forceDeployProvApsDefaultsEntry 14 }

forceDeployProvApsDefaultsDirection OBJECT-TYPE
    SYNTAX      ApsDirection
    MAX-ACCESS  read-only
    STATUS      current
    DESCRIPTION   "Indicates whether the APS function is 'unidirectional' (single-ended)
         or 'bidirectional' (dual-ended)."
    ::=  { forceDeployProvApsDefaultsEntry 15 }

forceDeployProvApsWorkingAidCapsTable OBJECT-TYPE
    SYNTAX      SEQUENCE OF ForceDeployProvApsWorkingAidCapsEntry
    MAX-ACCESS  not-accessible
    STATUS      current
    DESCRIPTION   ""
    ::=  { cloningEntitiesDeployProv 6 }

forceDeployProvApsWorkingAidCapsEntry OBJECT-TYPE
    SYNTAX      ForceDeployProvApsWorkingAidCapsEntry
    MAX-ACCESS  not-accessible
    STATUS      current
    DESCRIPTION   ""
    INDEX       {
                  entityIndex,
                  deployProvApsWorkingAidCapsIndex
                }
    ::=  { forceDeployProvApsWorkingAidCapsTable 1 }

ForceDeployProvApsWorkingAidCapsEntry ::=  SEQUENCE
  { forceDeployProvApsWorkingAidCapsIndex EntityIndex }

forceDeployProvApsWorkingAidCapsIndex OBJECT-TYPE
    SYNTAX      EntityIndex
    MAX-ACCESS  read-only
    STATUS      current
    DESCRIPTION
        "AID of working port involved in the protection group." 
    ::=  { forceDeployProvApsWorkingAidCapsEntry 1 }

forceDeployProvApsProtectingAidCapsTable OBJECT-TYPE
    SYNTAX      SEQUENCE OF ForceDeployProvApsProtectingAidCapsEntry
    MAX-ACCESS  not-accessible
    STATUS      current
    DESCRIPTION   ""
    ::=  { cloningEntitiesDeployProv 7 }

forceDeployProvApsProtectingAidCapsEntry OBJECT-TYPE
    SYNTAX      ForceDeployProvApsProtectingAidCapsEntry
    MAX-ACCESS  not-accessible
    STATUS      current
    DESCRIPTION   ""
    INDEX       {
                  entityIndex,
                  deployProvApsProtectingAidCapsIndex
                }
    ::=  { forceDeployProvApsProtectingAidCapsTable 1 }

ForceDeployProvApsProtectingAidCapsEntry ::=  SEQUENCE
  { forceDeployProvApsProtectingAidCapsIndex EntityIndex }

forceDeployProvApsProtectingAidCapsIndex OBJECT-TYPE
    SYNTAX      EntityIndex
    MAX-ACCESS  read-only
    STATUS      current
    DESCRIPTION
        "(Protection AID) AID of protection entity involved in the protection group." 
    ::=  { forceDeployProvApsProtectingAidCapsEntry 1 }

forceDeployProvApsPeerAidCapsTable OBJECT-TYPE
    SYNTAX      SEQUENCE OF ForceDeployProvApsPeerAidCapsEntry
    MAX-ACCESS  not-accessible
    STATUS      current
    DESCRIPTION   ""
    ::=  { cloningEntitiesDeployProv 8 }

forceDeployProvApsPeerAidCapsEntry OBJECT-TYPE
    SYNTAX      ForceDeployProvApsPeerAidCapsEntry
    MAX-ACCESS  not-accessible
    STATUS      current
    DESCRIPTION   ""
    INDEX       {
                  entityIndex,
                  deployProvApsWorkingAidCapsIndex
                }
    ::=  { forceDeployProvApsPeerAidCapsTable 1 }

ForceDeployProvApsPeerAidCapsEntry ::=  SEQUENCE
  { forceDeployProvApsPeerAidCapsIndex EntityIndex }

forceDeployProvApsPeerAidCapsIndex OBJECT-TYPE
    SYNTAX      EntityIndex
    MAX-ACCESS  read-only
    STATUS      current
    DESCRIPTION
        "AID of Protection Partner involved in the protection group." 
    ::=  { forceDeployProvApsPeerAidCapsEntry 1 }

unusedWdmTunnelIndex OBJECT-TYPE
    SYNTAX      Unsigned32
    MAX-ACCESS  read-only
    STATUS      current
    DESCRIPTION   "This object is used to retrieve unused tunnel ID for provisioning purpose."
    ::=  { controlPlaneDeployProv 1 }

unusedWdmPathIndex OBJECT-TYPE
    SYNTAX      Unsigned32
    MAX-ACCESS  read-only
    STATUS      current
    DESCRIPTION   "This object is used to retrieve unused path ID for provisioning purpose."
    ::=  { controlPlaneDeployProv 2 }

unusedOtnTunnelIndex OBJECT-TYPE
    SYNTAX      Unsigned32
    MAX-ACCESS  read-only
    STATUS      current
    DESCRIPTION   "This object is used to retrieve unused tunnel ID for provisioning purpose."
    ::=  { controlPlaneDeployProv 95 }

unusedOtnPathIndex OBJECT-TYPE
    SYNTAX      Unsigned32
    MAX-ACCESS  read-only
    STATUS      current
    DESCRIPTION   "This object is used to retrieve unused path ID for provisioning purpose."
    ::=  { controlPlaneDeployProv 96 }

unusedLifCpIndex OBJECT-TYPE
    SYNTAX      Unsigned32
    MAX-ACCESS  read-only
    STATUS      current
    DESCRIPTION
        "This parameter is used to retrieve unused Lif CP index, needed
         to provision new entity. If 0 returned no free slots available for provisioning.
        "
    ::=  { controlPlaneDeployProv 97 }

deployProvControlPlaneWdmTable OBJECT-TYPE
    SYNTAX      SEQUENCE OF DeployProvControlPlaneWdmEntry
    MAX-ACCESS  not-accessible
    STATUS      current
    DESCRIPTION   ""
    ::=  { controlPlaneDeployProv 11 }

deployProvControlPlaneWdmEntry OBJECT-TYPE
    SYNTAX      DeployProvControlPlaneWdmEntry
    MAX-ACCESS  not-accessible
    STATUS      current
    DESCRIPTION   ""
    INDEX       {
                  controlPlaneWdmEntityIndex
                }
    ::=  { deployProvControlPlaneWdmTable 1 }

DeployProvControlPlaneWdmEntry ::=  SEQUENCE
  { deployProvControlPlaneWdmRowStatus RowStatus,
    deployProvControlPlaneWdmCtmConfigFlag Unsigned32,
    deployProvControlPlaneWdmCtmTraceDetail Unsigned32,
    deployProvControlPlaneWdmCtmSetupTimeout Unsigned32,
    deployProvControlPlaneWdmCtmShutdownTimeout Unsigned32,
    deployProvControlPlaneWdmCtmRetryWait Unsigned32,
    deployProvControlPlaneWdmCtmRetryWaitMultiplier Unsigned32,
    deployProvControlPlaneWdmCtmMaximumRetryWait Unsigned32,
    deployProvControlPlaneWdmCtmMaximumRetryNumber Unsigned32,
    deployProvControlPlaneWdmRaConfigFlag Unsigned32,
    deployProvControlPlaneWdmRaTraceDetail Unsigned32,
    deployProvControlPlaneWdmRaAlarmActivationTime Unsigned32,
    deployProvControlPlaneWdmCmConfigFlag Unsigned32,
    deployProvControlPlaneWdmCmTraceDetail Unsigned32,
    deployProvControlPlaneWdmCmAlarmActivationTime Unsigned32,
    deployProvControlPlaneWdmCmFisFrsTimeout Unsigned32,
    deployProvControlPlaneWdmCmCrankBackTimeout Unsigned32,
    deployProvControlPlaneWdmCdbConfigFlag Unsigned32,
    deployProvControlPlaneWdmCdbDetail Unsigned32,
    deployProvControlPlaneWdmCdbMaxSize Unsigned32,
    deployProvControlPlaneWdmRsvpMaxExpRestartTime Counter64String,
    deployProvControlPlaneWdmRsvpMaxExpRecoveryTime Unsigned32,
    deployProvControlPlaneWdmRsvpConfigFlag Unsigned32,
    deployProvControlPlaneWdmTedbConfigFlag Unsigned32,
    deployProvControlPlaneWdmTedbTraceDetail Unsigned32,
    deployProvControlPlaneWdmTedbMaxSize Unsigned32,
    deployProvControlPlaneWdmTedbRouterId IpAddress,
    deployProvControlPlaneWdmTedbMinAdvertWait Unsigned32,
    deployProvControlPlaneWdmNaasConfigFlag Unsigned32,
    deployProvControlPlaneWdmNaasTraceDetail Unsigned32,
    deployProvControlPlaneWdmNaasMaxSize Unsigned32,
    deployProvControlPlaneWdmNaasAdvertWait Unsigned32,
    deployProvControlPlaneWdmPcConfigFlag Unsigned32,
    deployProvControlPlaneWdmPcTraceDetail Unsigned32,
    deployProvControlPlaneWdmCdConfigFlag Unsigned32,
    deployProvControlPlaneWdmCdTraceDetail Unsigned32,
    deployProvControlPlaneWdmCdResyncTimeout Unsigned32,
    deployProvControlPlaneWdmRmConfigFlag Unsigned32,
    deployProvControlPlaneWdmRmTraceDetail Unsigned32,
    deployProvControlPlaneWdmRmTraceTarget Unsigned32,
    deployProvControlPlaneWdmNodeNameSyntax FspR7NodeId,
    deployProvControlPlaneWdmWaitToRestore Unsigned32 }

deployProvControlPlaneWdmRowStatus OBJECT-TYPE
    SYNTAX      RowStatus
    MAX-ACCESS  read-write
    STATUS      current
    DESCRIPTION   ""
    ::=  { deployProvControlPlaneWdmEntry 1 }

deployProvControlPlaneWdmCtmConfigFlag OBJECT-TYPE
    SYNTAX      Unsigned32
    MAX-ACCESS  read-write
    STATUS      current
    DESCRIPTION   "Label Switched Path Edge Component' Configuration Bitfield"
    ::=  { deployProvControlPlaneWdmEntry 2 }

deployProvControlPlaneWdmCtmTraceDetail OBJECT-TYPE
    SYNTAX      Unsigned32
    MAX-ACCESS  read-write
    STATUS      current
    DESCRIPTION   "Label Switched Path Edge Component' Trace Detail"
    ::=  { deployProvControlPlaneWdmEntry 3 }

deployProvControlPlaneWdmCtmSetupTimeout OBJECT-TYPE
    SYNTAX      Unsigned32 
    UNITS       "s"
    MAX-ACCESS  read-write
    STATUS      current
    DESCRIPTION   "Label Switched Path Edge Component' Set-Up Timeout"
    ::=  { deployProvControlPlaneWdmEntry 4 }

deployProvControlPlaneWdmCtmShutdownTimeout OBJECT-TYPE
    SYNTAX      Unsigned32 
    UNITS       "s"
    MAX-ACCESS  read-write
    STATUS      current
    DESCRIPTION   "Label Switched Path Edge Component' Shut-Down Timeout"
    ::=  { deployProvControlPlaneWdmEntry 5 }

deployProvControlPlaneWdmCtmRetryWait OBJECT-TYPE
    SYNTAX      Unsigned32 
    UNITS       "s"
    MAX-ACCESS  read-write
    STATUS      current
    DESCRIPTION   "Label Switched Path Edge Component' Initialization Retry Wait"
    ::=  { deployProvControlPlaneWdmEntry 6 }

deployProvControlPlaneWdmCtmRetryWaitMultiplier OBJECT-TYPE
    SYNTAX      Unsigned32
    MAX-ACCESS  read-write
    STATUS      current
    DESCRIPTION   "Label Switched Path Edge Component' Initialization Retry Wait Multiplier"
    ::=  { deployProvControlPlaneWdmEntry 7 }

deployProvControlPlaneWdmCtmMaximumRetryWait OBJECT-TYPE
    SYNTAX      Unsigned32 
    UNITS       "s"
    MAX-ACCESS  read-write
    STATUS      current
    DESCRIPTION   "Label Switched Path Edge Component' Initialization Maximum Retry Wait"
    ::=  { deployProvControlPlaneWdmEntry 8 }

deployProvControlPlaneWdmCtmMaximumRetryNumber OBJECT-TYPE
    SYNTAX      Unsigned32
    MAX-ACCESS  read-write
    STATUS      current
    DESCRIPTION   "Label Switched Path Edge Component' Initialization Maximum Retry Number"
    ::=  { deployProvControlPlaneWdmEntry 9 }

deployProvControlPlaneWdmRaConfigFlag OBJECT-TYPE
    SYNTAX      Unsigned32
    MAX-ACCESS  read-write
    STATUS      current
    DESCRIPTION   "Resource Allocator Component' Configuration Bitfield"
    ::=  { deployProvControlPlaneWdmEntry 10 }

deployProvControlPlaneWdmRaTraceDetail OBJECT-TYPE
    SYNTAX      Unsigned32
    MAX-ACCESS  read-write
    STATUS      current
    DESCRIPTION   "Resource Allocator Component' Trace Detail"
    ::=  { deployProvControlPlaneWdmEntry 11 }

deployProvControlPlaneWdmRaAlarmActivationTime OBJECT-TYPE
    SYNTAX      Unsigned32 
    UNITS       "s"
    MAX-ACCESS  read-write
    STATUS      current
    DESCRIPTION   "Resource Allocator Component' Alarm Activation Time"
    ::=  { deployProvControlPlaneWdmEntry 12 }

deployProvControlPlaneWdmCmConfigFlag OBJECT-TYPE
    SYNTAX      Unsigned32
    MAX-ACCESS  read-write
    STATUS      current
    DESCRIPTION   "GMPLS Tunnel Manager Component' Configuration Bitfield"
    ::=  { deployProvControlPlaneWdmEntry 13 }

deployProvControlPlaneWdmCmTraceDetail OBJECT-TYPE
    SYNTAX      Unsigned32
    MAX-ACCESS  read-write
    STATUS      current
    DESCRIPTION   "GMPLS Tunnel Manager Component' Trace Detail"
    ::=  { deployProvControlPlaneWdmEntry 14 }

deployProvControlPlaneWdmCmAlarmActivationTime OBJECT-TYPE
    SYNTAX      Unsigned32 
    UNITS       "s"
    MAX-ACCESS  read-write
    STATUS      current
    DESCRIPTION   "GMPLS Tunnel Manager Component' Alarm Activation Time"
    ::=  { deployProvControlPlaneWdmEntry 15 }

deployProvControlPlaneWdmCmFisFrsTimeout OBJECT-TYPE
    SYNTAX      Unsigned32 
    UNITS       "s"
    MAX-ACCESS  read-write
    STATUS      current
    DESCRIPTION   "GMPLS Tunnel Manager Component' FIS-FRS Timeout"
    ::=  { deployProvControlPlaneWdmEntry 16 }

deployProvControlPlaneWdmCmCrankBackTimeout OBJECT-TYPE
    SYNTAX      Unsigned32 
    UNITS       "s"
    MAX-ACCESS  read-write
    STATUS      current
    DESCRIPTION   "GMPLS Tunnel Manager Component' Crank-Back Timeout"
    ::=  { deployProvControlPlaneWdmEntry 17 }

deployProvControlPlaneWdmCdbConfigFlag OBJECT-TYPE
    SYNTAX      Unsigned32
    MAX-ACCESS  read-write
    STATUS      current
    DESCRIPTION   "Label Swithed Path Database Component Configuration Bitfield"
    ::=  { deployProvControlPlaneWdmEntry 18 }

deployProvControlPlaneWdmCdbDetail OBJECT-TYPE
    SYNTAX      Unsigned32
    MAX-ACCESS  read-write
    STATUS      current
    DESCRIPTION   "Label Swithed Path Database Component Trace Detail"
    ::=  { deployProvControlPlaneWdmEntry 19 }

deployProvControlPlaneWdmCdbMaxSize OBJECT-TYPE
    SYNTAX      Unsigned32
    MAX-ACCESS  read-write
    STATUS      current
    DESCRIPTION   "Label Swithed Path Database Component Maximum Size; 0 implies no limit"
    ::=  { deployProvControlPlaneWdmEntry 20 }

deployProvControlPlaneWdmRsvpMaxExpRestartTime OBJECT-TYPE
    SYNTAX      Counter64String 
    UNITS       "ms"
    MAX-ACCESS  read-write
    STATUS      current
    DESCRIPTION   "Maximum Expected Resource Reservation Protocol Component' Restart Time"
    ::=  { deployProvControlPlaneWdmEntry 21 }

deployProvControlPlaneWdmRsvpMaxExpRecoveryTime OBJECT-TYPE
    SYNTAX      Unsigned32 
    UNITS       "ms"
    MAX-ACCESS  read-write
    STATUS      current
    DESCRIPTION   "Maximum Expected Resource Reservation Protocol Component' Recovery Time"
    ::=  { deployProvControlPlaneWdmEntry 22 }

deployProvControlPlaneWdmRsvpConfigFlag OBJECT-TYPE
    SYNTAX      Unsigned32
    MAX-ACCESS  read-write
    STATUS      current
    DESCRIPTION   "Resource Reservation Protocol Component' Configuration Bitfield"
    ::=  { deployProvControlPlaneWdmEntry 23 }

deployProvControlPlaneWdmTedbConfigFlag OBJECT-TYPE
    SYNTAX      Unsigned32
    MAX-ACCESS  read-write
    STATUS      current
    DESCRIPTION   "Traffic Engineering Component' Configuration Bitfield"
    ::=  { deployProvControlPlaneWdmEntry 24 }

deployProvControlPlaneWdmTedbTraceDetail OBJECT-TYPE
    SYNTAX      Unsigned32
    MAX-ACCESS  read-write
    STATUS      current
    DESCRIPTION   "Traffic Engineering Component' Trace Detail"
    ::=  { deployProvControlPlaneWdmEntry 25 }

deployProvControlPlaneWdmTedbMaxSize OBJECT-TYPE
    SYNTAX      Unsigned32
    MAX-ACCESS  read-write
    STATUS      current
    DESCRIPTION   "Traffic Engineering Component' Maximum Size"
    ::=  { deployProvControlPlaneWdmEntry 26 }

deployProvControlPlaneWdmTedbRouterId OBJECT-TYPE
    SYNTAX      IpAddress
    MAX-ACCESS  read-write
    STATUS      current
    DESCRIPTION   "Traffic Engineering Component' Router ID"
    ::=  { deployProvControlPlaneWdmEntry 27 }

deployProvControlPlaneWdmTedbMinAdvertWait OBJECT-TYPE
    SYNTAX      Unsigned32 
    UNITS       "s"
    MAX-ACCESS  read-write
    STATUS      current
    DESCRIPTION   "Traffic Engineering Component' Minimum Advertisement Wait"
    ::=  { deployProvControlPlaneWdmEntry 28 }

deployProvControlPlaneWdmNaasConfigFlag OBJECT-TYPE
    SYNTAX      Unsigned32
    MAX-ACCESS  read-write
    STATUS      current
    DESCRIPTION   "Node Attribute Advertising Service Database Component' Configuration Bitfield"
    ::=  { deployProvControlPlaneWdmEntry 29 }

deployProvControlPlaneWdmNaasTraceDetail OBJECT-TYPE
    SYNTAX      Unsigned32
    MAX-ACCESS  read-write
    STATUS      current
    DESCRIPTION   "Node Attribute Advertising Service Database Component' Trace Detail"
    ::=  { deployProvControlPlaneWdmEntry 30 }

deployProvControlPlaneWdmNaasMaxSize OBJECT-TYPE
    SYNTAX      Unsigned32
    MAX-ACCESS  read-write
    STATUS      current
    DESCRIPTION   "Node Attribute Advertising Service Database Component' Maximum Size"
    ::=  { deployProvControlPlaneWdmEntry 31 }

deployProvControlPlaneWdmNaasAdvertWait OBJECT-TYPE
    SYNTAX      Unsigned32 
    UNITS       "s"
    MAX-ACCESS  read-write
    STATUS      current
    DESCRIPTION   "Node Attribute Advertising Service Database Component' Advertisement Wait"
    ::=  { deployProvControlPlaneWdmEntry 32 }

deployProvControlPlaneWdmPcConfigFlag OBJECT-TYPE
    SYNTAX      Unsigned32
    MAX-ACCESS  read-write
    STATUS      current
    DESCRIPTION   "Path Computation Component' Configuration Bitfield"
    ::=  { deployProvControlPlaneWdmEntry 33 }

deployProvControlPlaneWdmPcTraceDetail OBJECT-TYPE
    SYNTAX      Unsigned32
    MAX-ACCESS  read-write
    STATUS      current
    DESCRIPTION   "Path Computation Component' Trace Detail"
    ::=  { deployProvControlPlaneWdmEntry 34 }

deployProvControlPlaneWdmCdConfigFlag OBJECT-TYPE
    SYNTAX      Unsigned32
    MAX-ACCESS  read-write
    STATUS      current
    DESCRIPTION   "Configuration Data Component' Configuration Bitfield"
    ::=  { deployProvControlPlaneWdmEntry 35 }

deployProvControlPlaneWdmCdTraceDetail OBJECT-TYPE
    SYNTAX      Unsigned32
    MAX-ACCESS  read-write
    STATUS      current
    DESCRIPTION   "Configuration Data Component' Trace Detail"
    ::=  { deployProvControlPlaneWdmEntry 36 }

deployProvControlPlaneWdmCdResyncTimeout OBJECT-TYPE
    SYNTAX      Unsigned32
    MAX-ACCESS  read-write
    STATUS      current
    DESCRIPTION   "Configuration Data Component' Resync Timeout"
    ::=  { deployProvControlPlaneWdmEntry 37 }

deployProvControlPlaneWdmRmConfigFlag OBJECT-TYPE
    SYNTAX      Unsigned32
    MAX-ACCESS  read-write
    STATUS      current
    DESCRIPTION   "Resource Management Component' Configuration Bitfield"
    ::=  { deployProvControlPlaneWdmEntry 38 }

deployProvControlPlaneWdmRmTraceDetail OBJECT-TYPE
    SYNTAX      Unsigned32
    MAX-ACCESS  read-write
    STATUS      current
    DESCRIPTION   "Resource Management Component' Trace Detail"
    ::=  { deployProvControlPlaneWdmEntry 39 }

deployProvControlPlaneWdmRmTraceTarget OBJECT-TYPE
    SYNTAX      Unsigned32
    MAX-ACCESS  read-write
    STATUS      current
    DESCRIPTION   "Resource Management Component' Trace Target"
    ::=  { deployProvControlPlaneWdmEntry 40 }

deployProvControlPlaneWdmNodeNameSyntax OBJECT-TYPE
    SYNTAX      FspR7NodeId
    MAX-ACCESS  read-write
    STATUS      deprecated
    DESCRIPTION   "Node Name Syntax"
    ::=  { deployProvControlPlaneWdmEntry 41 }

deployProvControlPlaneWdmWaitToRestore OBJECT-TYPE
    SYNTAX      Unsigned32 (5..12 | 4294967295) 
    UNITS       "min"
    MAX-ACCESS  read-write
    STATUS      current
    DESCRIPTION
        "Wait to Restore Timer value" 
    ::=  { deployProvControlPlaneWdmEntry 42 }

deployProvControlPlaneWdmCapTable OBJECT-TYPE
    SYNTAX      SEQUENCE OF DeployProvControlPlaneWdmCapEntry
    MAX-ACCESS  not-accessible
    STATUS      current
    DESCRIPTION   ""
    ::=  { controlPlaneDeployProv 12  }

deployProvControlPlaneWdmCapEntry OBJECT-TYPE
    SYNTAX      DeployProvControlPlaneWdmCapEntry
    MAX-ACCESS  not-accessible
    STATUS      current
    DESCRIPTION   ""
    INDEX       { controlPlaneWdmEntityIndex }
    ::=  { deployProvControlPlaneWdmCapTable 1 }

DeployProvControlPlaneWdmCapEntry ::=  SEQUENCE
  { deployProvControlPlaneWdmCapRowStatus FspR7RowStatusCaps,
    deployProvControlPlaneWdmCapCtmConfigFlag FspR7Unsigned32Caps,
    deployProvControlPlaneWdmCapCtmTraceDetail FspR7Unsigned32Caps,
    deployProvControlPlaneWdmCapCtmSetupTimeout FspR7Unsigned32Caps,
    deployProvControlPlaneWdmCapCtmShutdownTimeout FspR7Unsigned32Caps,
    deployProvControlPlaneWdmCapCtmRetryWait FspR7Unsigned32Caps,
    deployProvControlPlaneWdmCapCtmRetryWaitMultiplier FspR7Unsigned32Caps,
    deployProvControlPlaneWdmCapCtmMaximumRetryWait FspR7Unsigned32Caps,
    deployProvControlPlaneWdmCapCtmMaximumRetryNumber FspR7Unsigned32Caps,
    deployProvControlPlaneWdmCapRaConfigFlag FspR7Unsigned32Caps,
    deployProvControlPlaneWdmCapRaTraceDetail FspR7Unsigned32Caps,
    deployProvControlPlaneWdmCapRaAlarmActivationTime FspR7Unsigned32Caps,
    deployProvControlPlaneWdmCapCmConfigFlag FspR7Unsigned32Caps,
    deployProvControlPlaneWdmCapCmTraceDetail FspR7Unsigned32Caps,
    deployProvControlPlaneWdmCapCmAlarmActivationTime FspR7Unsigned32Caps,
    deployProvControlPlaneWdmCapCmFisFrsTimeout FspR7Unsigned32Caps,
    deployProvControlPlaneWdmCapCmCrankBackTimeout FspR7Unsigned32Caps,
    deployProvControlPlaneWdmCapCdbConfigFlag FspR7Unsigned32Caps,
    deployProvControlPlaneWdmCapCdbDetail FspR7Unsigned32Caps,
    deployProvControlPlaneWdmCapCdbMaxSize FspR7Unsigned32Caps,
    deployProvControlPlaneWdmCapRsvpMaxExpRestartTime Counter64StringCaps,
    deployProvControlPlaneWdmCapRsvpMaxExpRecoveryTime FspR7Unsigned32Caps,
    deployProvControlPlaneWdmCapRsvpConfigFlag FspR7Unsigned32Caps,
    deployProvControlPlaneWdmCapTedbConfigFlag FspR7Unsigned32Caps,
    deployProvControlPlaneWdmCapTedbTraceDetail FspR7Unsigned32Caps,
    deployProvControlPlaneWdmCapTedbMaxSize FspR7Unsigned32Caps,
    deployProvControlPlaneWdmCapTedbRouterId FspR7YesNo,
    deployProvControlPlaneWdmCapTedbMinAdvertWait FspR7Unsigned32Caps,
    deployProvControlPlaneWdmCapNaasConfigFlag FspR7Unsigned32Caps,
    deployProvControlPlaneWdmCapNaasTraceDetail FspR7Unsigned32Caps,
    deployProvControlPlaneWdmCapNaasMaxSize FspR7Unsigned32Caps,
    deployProvControlPlaneWdmCapNaasAdvertWait FspR7Unsigned32Caps,
    deployProvControlPlaneWdmCapPcConfigFlag FspR7Unsigned32Caps,
    deployProvControlPlaneWdmCapPcTraceDetail FspR7Unsigned32Caps,
    deployProvControlPlaneWdmCapCdConfigFlag FspR7Unsigned32Caps,
    deployProvControlPlaneWdmCapCdTraceDetail FspR7Unsigned32Caps,
    deployProvControlPlaneWdmCapCdResyncTimeout FspR7Unsigned32Caps,
    deployProvControlPlaneWdmCapRmConfigFlag FspR7Unsigned32Caps,
    deployProvControlPlaneWdmCapRmTraceDetail FspR7Unsigned32Caps,
    deployProvControlPlaneWdmCapRmTraceTarget FspR7Unsigned32Caps,
    deployProvControlPlaneWdmCapNodeNameSyntax FspR7NodeIdCaps,
    deployProvControlPlaneWdmCapWaitToRestore FspR7Unsigned32Caps }

deployProvControlPlaneWdmCapRowStatus OBJECT-TYPE
    SYNTAX      FspR7RowStatusCaps
    MAX-ACCESS  read-only
    STATUS      current
    DESCRIPTION   ""
    ::=  { deployProvControlPlaneWdmCapEntry 1 }

deployProvControlPlaneWdmCapCtmConfigFlag OBJECT-TYPE
    SYNTAX      FspR7Unsigned32Caps
    MAX-ACCESS  read-only
    STATUS      current
    DESCRIPTION   "Label Switched Path Edge Component' Configuration Bitfield"
    ::=  { deployProvControlPlaneWdmCapEntry 2 }

deployProvControlPlaneWdmCapCtmTraceDetail OBJECT-TYPE
    SYNTAX      FspR7Unsigned32Caps
    MAX-ACCESS  read-only
    STATUS      current
    DESCRIPTION   "Label Switched Path Edge Component' Trace Detail"
    ::=  { deployProvControlPlaneWdmCapEntry 3 }

deployProvControlPlaneWdmCapCtmSetupTimeout OBJECT-TYPE
    SYNTAX      FspR7Unsigned32Caps
    UNITS       "s"
    MAX-ACCESS  read-only
    STATUS      current
    DESCRIPTION   "Label Switched Path Edge Component' Set-Up Timeout"
    ::=  { deployProvControlPlaneWdmCapEntry 4 }

deployProvControlPlaneWdmCapCtmShutdownTimeout OBJECT-TYPE
    SYNTAX      FspR7Unsigned32Caps
    UNITS       "s"
    MAX-ACCESS  read-only
    STATUS      current
    DESCRIPTION   "Label Switched Path Edge Component' Shut-Down Timeout"
    ::=  { deployProvControlPlaneWdmCapEntry 5 }

deployProvControlPlaneWdmCapCtmRetryWait OBJECT-TYPE
    SYNTAX      FspR7Unsigned32Caps
    UNITS       "s"
    MAX-ACCESS  read-only
    STATUS      current
    DESCRIPTION   "Label Switched Path Edge Component' Initialization Retry Wait"
    ::=  { deployProvControlPlaneWdmCapEntry 6 }

deployProvControlPlaneWdmCapCtmRetryWaitMultiplier OBJECT-TYPE
    SYNTAX      FspR7Unsigned32Caps
    MAX-ACCESS  read-only
    STATUS      current
    DESCRIPTION   "Label Switched Path Edge Component' Initialization Retry Wait Multiplier"
    ::=  { deployProvControlPlaneWdmCapEntry 7 }

deployProvControlPlaneWdmCapCtmMaximumRetryWait OBJECT-TYPE
    SYNTAX      FspR7Unsigned32Caps
    UNITS       "s"
    MAX-ACCESS  read-only
    STATUS      current
    DESCRIPTION   "Label Switched Path Edge Component' Initialization Maximum Retry Wait"
    ::=  { deployProvControlPlaneWdmCapEntry 8 }

deployProvControlPlaneWdmCapCtmMaximumRetryNumber OBJECT-TYPE
    SYNTAX      FspR7Unsigned32Caps
    MAX-ACCESS  read-only
    STATUS      current
    DESCRIPTION   "Label Switched Path Edge Component' Initialization Maximum Retry Number"
    ::=  { deployProvControlPlaneWdmCapEntry 9 }

deployProvControlPlaneWdmCapRaConfigFlag OBJECT-TYPE
    SYNTAX      FspR7Unsigned32Caps
    MAX-ACCESS  read-only
    STATUS      current
    DESCRIPTION   "Resource Allocator Component' Configuration Bitfield"
    ::=  { deployProvControlPlaneWdmCapEntry 10 }

deployProvControlPlaneWdmCapRaTraceDetail OBJECT-TYPE
    SYNTAX      FspR7Unsigned32Caps
    MAX-ACCESS  read-only
    STATUS      current
    DESCRIPTION   "Resource Allocator Component' Trace Detail"
    ::=  { deployProvControlPlaneWdmCapEntry 11 }

deployProvControlPlaneWdmCapRaAlarmActivationTime OBJECT-TYPE
    SYNTAX      FspR7Unsigned32Caps
    UNITS       "s"
    MAX-ACCESS  read-only
    STATUS      current
    DESCRIPTION   "Resource Allocator Component' Alarm Activation Time"
    ::=  { deployProvControlPlaneWdmCapEntry 12 }

deployProvControlPlaneWdmCapCmConfigFlag OBJECT-TYPE
    SYNTAX      FspR7Unsigned32Caps
    MAX-ACCESS  read-only
    STATUS      current
    DESCRIPTION   "GMPLS Tunnel Manager Component' Configuration Bitfield"
    ::=  { deployProvControlPlaneWdmCapEntry 13 }

deployProvControlPlaneWdmCapCmTraceDetail OBJECT-TYPE
    SYNTAX      FspR7Unsigned32Caps
    MAX-ACCESS  read-only
    STATUS      current
    DESCRIPTION   "GMPLS Tunnel Manager Component' Trace Detail"
    ::=  { deployProvControlPlaneWdmCapEntry 14 }

deployProvControlPlaneWdmCapCmAlarmActivationTime OBJECT-TYPE
    SYNTAX      FspR7Unsigned32Caps
    UNITS       "s"
    MAX-ACCESS  read-only
    STATUS      current
    DESCRIPTION   "GMPLS Tunnel Manager Component' Alarm Activation Time"
    ::=  { deployProvControlPlaneWdmCapEntry 15 }

deployProvControlPlaneWdmCapCmFisFrsTimeout OBJECT-TYPE
    SYNTAX      FspR7Unsigned32Caps
    UNITS       "s"
    MAX-ACCESS  read-only
    STATUS      current
    DESCRIPTION   "GMPLS Tunnel Manager Component' FIS-FRS Timeout"
    ::=  { deployProvControlPlaneWdmCapEntry 16 }

deployProvControlPlaneWdmCapCmCrankBackTimeout OBJECT-TYPE
    SYNTAX      FspR7Unsigned32Caps
    UNITS       "s"
    MAX-ACCESS  read-only
    STATUS      current
    DESCRIPTION   "GMPLS Tunnel Manager Component' Crank-Back Timeout"
    ::=  { deployProvControlPlaneWdmCapEntry 17 }

deployProvControlPlaneWdmCapCdbConfigFlag OBJECT-TYPE
    SYNTAX      FspR7Unsigned32Caps
    MAX-ACCESS  read-only
    STATUS      current
    DESCRIPTION   "Label Swithed Path Database Component Configuration Bitfield"
    ::=  { deployProvControlPlaneWdmCapEntry 18 }

deployProvControlPlaneWdmCapCdbDetail OBJECT-TYPE
    SYNTAX      FspR7Unsigned32Caps
    MAX-ACCESS  read-only
    STATUS      current
    DESCRIPTION   "Label Swithed Path Database Component Trace Detail"
    ::=  { deployProvControlPlaneWdmCapEntry 19 }

deployProvControlPlaneWdmCapCdbMaxSize OBJECT-TYPE
    SYNTAX      FspR7Unsigned32Caps
    MAX-ACCESS  read-only
    STATUS      current
    DESCRIPTION   "Label Swithed Path Database Component Maximum Size; 0 implies no limit"
    ::=  { deployProvControlPlaneWdmCapEntry 20 }

deployProvControlPlaneWdmCapRsvpMaxExpRestartTime OBJECT-TYPE
    SYNTAX      Counter64StringCaps
    UNITS       "ms"
    MAX-ACCESS  read-only
    STATUS      current
    DESCRIPTION   "Maximum Expected Resource Reservation Protocol Component' Restart Time"
    ::=  { deployProvControlPlaneWdmCapEntry 21 }

deployProvControlPlaneWdmCapRsvpMaxExpRecoveryTime OBJECT-TYPE
    SYNTAX      FspR7Unsigned32Caps
    UNITS       "ms"
    MAX-ACCESS  read-only
    STATUS      current
    DESCRIPTION   "Maximum Expected Resource Reservation Protocol Component' Recovery Time"
    ::=  { deployProvControlPlaneWdmCapEntry 22 }

deployProvControlPlaneWdmCapRsvpConfigFlag OBJECT-TYPE
    SYNTAX      FspR7Unsigned32Caps
    MAX-ACCESS  read-only
    STATUS      current
    DESCRIPTION   "Resource Reservation Protocol Component' Configuration Bitfield"
    ::=  { deployProvControlPlaneWdmCapEntry 23 }

deployProvControlPlaneWdmCapTedbConfigFlag OBJECT-TYPE
    SYNTAX      FspR7Unsigned32Caps
    MAX-ACCESS  read-only
    STATUS      current
    DESCRIPTION   "Traffic Engineering Component' Configuration Bitfield"
    ::=  { deployProvControlPlaneWdmCapEntry 24 }

deployProvControlPlaneWdmCapTedbTraceDetail OBJECT-TYPE
    SYNTAX      FspR7Unsigned32Caps
    MAX-ACCESS  read-only
    STATUS      current
    DESCRIPTION   "Traffic Engineering Component' Trace Detail"
    ::=  { deployProvControlPlaneWdmCapEntry 25 }

deployProvControlPlaneWdmCapTedbMaxSize OBJECT-TYPE
    SYNTAX      FspR7Unsigned32Caps
    MAX-ACCESS  read-only
    STATUS      current
    DESCRIPTION   "Traffic Engineering Component' Maximum Size"
    ::=  { deployProvControlPlaneWdmCapEntry 26 }

deployProvControlPlaneWdmCapTedbRouterId OBJECT-TYPE
    SYNTAX      FspR7YesNo
    MAX-ACCESS  read-only
    STATUS      current
    DESCRIPTION   "Traffic Engineering Component' Router ID"
    ::=  { deployProvControlPlaneWdmCapEntry 27 }

deployProvControlPlaneWdmCapTedbMinAdvertWait OBJECT-TYPE
    SYNTAX      FspR7Unsigned32Caps
    UNITS       "s"
    MAX-ACCESS  read-only
    STATUS      current
    DESCRIPTION   "Traffic Engineering Component' Minimum Advertisement Wait"
    ::=  { deployProvControlPlaneWdmCapEntry 28 }

deployProvControlPlaneWdmCapNaasConfigFlag OBJECT-TYPE
    SYNTAX      FspR7Unsigned32Caps
    MAX-ACCESS  read-only
    STATUS      current
    DESCRIPTION   "Node Attribute Advertising Service Database Component' Configuration Bitfield"
    ::=  { deployProvControlPlaneWdmCapEntry 29 }

deployProvControlPlaneWdmCapNaasTraceDetail OBJECT-TYPE
    SYNTAX      FspR7Unsigned32Caps
    MAX-ACCESS  read-only
    STATUS      current
    DESCRIPTION   "Node Attribute Advertising Service Database Component' Trace Detail"
    ::=  { deployProvControlPlaneWdmCapEntry 30 }

deployProvControlPlaneWdmCapNaasMaxSize OBJECT-TYPE
    SYNTAX      FspR7Unsigned32Caps
    MAX-ACCESS  read-only
    STATUS      current
    DESCRIPTION   "Node Attribute Advertising Service Database Component' Maximum Size"
    ::=  { deployProvControlPlaneWdmCapEntry 31 }

deployProvControlPlaneWdmCapNaasAdvertWait OBJECT-TYPE
    SYNTAX      FspR7Unsigned32Caps
    UNITS       "s"
    MAX-ACCESS  read-only
    STATUS      current
    DESCRIPTION   "Node Attribute Advertising Service Database Component' Advertisement Wait"
    ::=  { deployProvControlPlaneWdmCapEntry 32 }

deployProvControlPlaneWdmCapPcConfigFlag OBJECT-TYPE
    SYNTAX      FspR7Unsigned32Caps
    MAX-ACCESS  read-only
    STATUS      current
    DESCRIPTION   "Path Computation Component' Configuration Bitfield"
    ::=  { deployProvControlPlaneWdmCapEntry 33 }

deployProvControlPlaneWdmCapPcTraceDetail OBJECT-TYPE
    SYNTAX      FspR7Unsigned32Caps
    MAX-ACCESS  read-only
    STATUS      current
    DESCRIPTION   "Path Computation Component' Trace Detail"
    ::=  { deployProvControlPlaneWdmCapEntry 34 }

deployProvControlPlaneWdmCapCdConfigFlag OBJECT-TYPE
    SYNTAX      FspR7Unsigned32Caps
    MAX-ACCESS  read-only
    STATUS      current
    DESCRIPTION   "Configuration Data Component' Configuration Bitfield"
    ::=  { deployProvControlPlaneWdmCapEntry 35 }

deployProvControlPlaneWdmCapCdTraceDetail OBJECT-TYPE
    SYNTAX      FspR7Unsigned32Caps
    MAX-ACCESS  read-only
    STATUS      current
    DESCRIPTION   "Configuration Data Component' Trace Detail"
    ::=  { deployProvControlPlaneWdmCapEntry 36 }

deployProvControlPlaneWdmCapCdResyncTimeout OBJECT-TYPE
    SYNTAX      FspR7Unsigned32Caps
    MAX-ACCESS  read-only
    STATUS      current
    DESCRIPTION   "Configuration Data Component' Resync Timeout"
    ::=  { deployProvControlPlaneWdmCapEntry 37 }

deployProvControlPlaneWdmCapRmConfigFlag OBJECT-TYPE
    SYNTAX      FspR7Unsigned32Caps
    MAX-ACCESS  read-only
    STATUS      current
    DESCRIPTION   "Resource Management Component' Configuration Bitfield"
    ::=  { deployProvControlPlaneWdmCapEntry 38 }

deployProvControlPlaneWdmCapRmTraceDetail OBJECT-TYPE
    SYNTAX      FspR7Unsigned32Caps
    MAX-ACCESS  read-only
    STATUS      current
    DESCRIPTION   "Resource Management Component' Trace Detail"
    ::=  { deployProvControlPlaneWdmCapEntry 39 }

deployProvControlPlaneWdmCapRmTraceTarget OBJECT-TYPE
    SYNTAX      FspR7Unsigned32Caps
    MAX-ACCESS  read-only
    STATUS      current
    DESCRIPTION   "Resource Management Component' Trace Target"
    ::=  { deployProvControlPlaneWdmCapEntry 40 }

deployProvControlPlaneWdmCapNodeNameSyntax OBJECT-TYPE
    SYNTAX      FspR7NodeIdCaps
    MAX-ACCESS  read-only
    STATUS      deprecated
    DESCRIPTION   "Node Name Syntax"
    ::=  { deployProvControlPlaneWdmCapEntry 41 }

deployProvControlPlaneWdmCapWaitToRestore OBJECT-TYPE
    SYNTAX      FspR7Unsigned32Caps
    UNITS       "min"
    MAX-ACCESS  read-only
    STATUS      current
    DESCRIPTION
        "Wait to Restore Timer value" 
    ::=  { deployProvControlPlaneWdmCapEntry 42 }

deployProvControlPlaneWdmDefaultsTable  OBJECT-TYPE
    SYNTAX      SEQUENCE OF DeployProvControlPlaneWdmDefaultsEntry
    MAX-ACCESS  not-accessible
    STATUS      current
    DESCRIPTION   ""
    ::=  { controlPlaneDeployProv 13  }

deployProvControlPlaneWdmDefaultsEntry OBJECT-TYPE
    SYNTAX      DeployProvControlPlaneWdmDefaultsEntry
    MAX-ACCESS  not-accessible
    STATUS      current
    DESCRIPTION   ""
    INDEX       { controlPlaneWdmEntityIndex }
    ::=  { deployProvControlPlaneWdmDefaultsTable 1 }

DeployProvControlPlaneWdmDefaultsEntry ::=  SEQUENCE
  { deployProvControlPlaneWdmDefaultsRowStatus RowStatus,
    deployProvControlPlaneWdmDefaultsCtmConfigFlag Unsigned32,
    deployProvControlPlaneWdmDefaultsCtmTraceDetail Unsigned32,
    deployProvControlPlaneWdmDefaultsCtmSetupTimeout Unsigned32,
    deployProvControlPlaneWdmDefaultsCtmShutdownTimeout Unsigned32,
    deployProvControlPlaneWdmDefaultsCtmRetryWait Unsigned32,
    deployProvControlPlaneWdmDefaultsCtmRetryWaitMultiplier Unsigned32,
    deployProvControlPlaneWdmDefaultsCtmMaximumRetryWait Unsigned32,
    deployProvControlPlaneWdmDefaultsCtmMaximumRetryNumber Unsigned32,
    deployProvControlPlaneWdmDefaultsRaConfigFlag Unsigned32,
    deployProvControlPlaneWdmDefaultsRaTraceDetail Unsigned32,
    deployProvControlPlaneWdmDefaultsRaAlarmActivationTime Unsigned32,
    deployProvControlPlaneWdmDefaultsCmConfigFlag Unsigned32,
    deployProvControlPlaneWdmDefaultsCmTraceDetail Unsigned32,
    deployProvControlPlaneWdmDefaultsCmAlarmActivationTime Unsigned32,
    deployProvControlPlaneWdmDefaultsCmFisFrsTimeout Unsigned32,
    deployProvControlPlaneWdmDefaultsCmCrankBackTimeout Unsigned32,
    deployProvControlPlaneWdmDefaultsCdbConfigFlag Unsigned32,
    deployProvControlPlaneWdmDefaultsCdbDetail Unsigned32,
    deployProvControlPlaneWdmDefaultsCdbMaxSize Unsigned32,
    deployProvControlPlaneWdmDefaultsRsvpMaxExpRestartTime Counter64String,
    deployProvControlPlaneWdmDefaultsRsvpMaxExpRecoveryTime Unsigned32,
    deployProvControlPlaneWdmDefaultsRsvpConfigFlag Unsigned32,
    deployProvControlPlaneWdmDefaultsTedbConfigFlag Unsigned32,
    deployProvControlPlaneWdmDefaultsTedbTraceDetail Unsigned32,
    deployProvControlPlaneWdmDefaultsTedbMaxSize Unsigned32,
    deployProvControlPlaneWdmDefaultsTedbRouterId IpAddress,
    deployProvControlPlaneWdmDefaultsTedbMinAdvertWait Unsigned32,
    deployProvControlPlaneWdmDefaultsNaasConfigFlag Unsigned32,
    deployProvControlPlaneWdmDefaultsNaasTraceDetail Unsigned32,
    deployProvControlPlaneWdmDefaultsNaasMaxSize Unsigned32,
    deployProvControlPlaneWdmDefaultsNaasAdvertWait Unsigned32,
    deployProvControlPlaneWdmDefaultsPcConfigFlag Unsigned32,
    deployProvControlPlaneWdmDefaultsPcTraceDetail Unsigned32,
    deployProvControlPlaneWdmDefaultsCdConfigFlag Unsigned32,
    deployProvControlPlaneWdmDefaultsCdTraceDetail Unsigned32,
    deployProvControlPlaneWdmDefaultsCdResyncTimeout Unsigned32,
    deployProvControlPlaneWdmDefaultsRmConfigFlag Unsigned32,
    deployProvControlPlaneWdmDefaultsRmTraceDetail Unsigned32,
    deployProvControlPlaneWdmDefaultsRmTraceTarget Unsigned32,
    deployProvControlPlaneWdmDefaultsNodeNameSyntax FspR7NodeId,
    deployProvControlPlaneWdmDefaultsWaitToRestore Unsigned32 }

deployProvControlPlaneWdmDefaultsRowStatus OBJECT-TYPE
    SYNTAX      RowStatus
    MAX-ACCESS  read-only
    STATUS      current
    DESCRIPTION   ""
    ::=  { deployProvControlPlaneWdmDefaultsEntry 1 }

deployProvControlPlaneWdmDefaultsCtmConfigFlag OBJECT-TYPE
    SYNTAX      Unsigned32
    MAX-ACCESS  read-only
    STATUS      current
    DESCRIPTION   "Label Switched Path Edge Component' Configuration Bitfield"
    ::=  { deployProvControlPlaneWdmDefaultsEntry 2 }

deployProvControlPlaneWdmDefaultsCtmTraceDetail OBJECT-TYPE
    SYNTAX      Unsigned32
    MAX-ACCESS  read-only
    STATUS      current
    DESCRIPTION   "Label Switched Path Edge Component' Trace Detail"
    ::=  { deployProvControlPlaneWdmDefaultsEntry 3 }

deployProvControlPlaneWdmDefaultsCtmSetupTimeout OBJECT-TYPE
    SYNTAX      Unsigned32 
    UNITS       "s"
    MAX-ACCESS  read-only
    STATUS      current
    DESCRIPTION   "Label Switched Path Edge Component' Set-Up Timeout"
    ::=  { deployProvControlPlaneWdmDefaultsEntry 4 }

deployProvControlPlaneWdmDefaultsCtmShutdownTimeout OBJECT-TYPE
    SYNTAX      Unsigned32 
    UNITS       "s"
    MAX-ACCESS  read-only
    STATUS      current
    DESCRIPTION   "Label Switched Path Edge Component' Shut-Down Timeout"
    ::=  { deployProvControlPlaneWdmDefaultsEntry 5 }

deployProvControlPlaneWdmDefaultsCtmRetryWait OBJECT-TYPE
    SYNTAX      Unsigned32 
    UNITS       "s"
    MAX-ACCESS  read-only
    STATUS      current
    DESCRIPTION   "Label Switched Path Edge Component' Initialization Retry Wait"
    ::=  { deployProvControlPlaneWdmDefaultsEntry 6 }

deployProvControlPlaneWdmDefaultsCtmRetryWaitMultiplier OBJECT-TYPE
    SYNTAX      Unsigned32
    MAX-ACCESS  read-only
    STATUS      current
    DESCRIPTION   "Label Switched Path Edge Component' Initialization Retry Wait Multiplier"
    ::=  { deployProvControlPlaneWdmDefaultsEntry 7 }

deployProvControlPlaneWdmDefaultsCtmMaximumRetryWait OBJECT-TYPE
    SYNTAX      Unsigned32 
    UNITS       "s"
    MAX-ACCESS  read-only
    STATUS      current
    DESCRIPTION   "Label Switched Path Edge Component' Initialization Maximum Retry Wait"
    ::=  { deployProvControlPlaneWdmDefaultsEntry 8 }

deployProvControlPlaneWdmDefaultsCtmMaximumRetryNumber OBJECT-TYPE
    SYNTAX      Unsigned32
    MAX-ACCESS  read-only
    STATUS      current
    DESCRIPTION   "Label Switched Path Edge Component' Initialization Maximum Retry Number"
    ::=  { deployProvControlPlaneWdmDefaultsEntry 9 }

deployProvControlPlaneWdmDefaultsRaConfigFlag OBJECT-TYPE
    SYNTAX      Unsigned32
    MAX-ACCESS  read-only
    STATUS      current
    DESCRIPTION   "Resource Allocator Component' Configuration Bitfield"
    ::=  { deployProvControlPlaneWdmDefaultsEntry 10 }

deployProvControlPlaneWdmDefaultsRaTraceDetail OBJECT-TYPE
    SYNTAX      Unsigned32
    MAX-ACCESS  read-only
    STATUS      current
    DESCRIPTION   "Resource Allocator Component' Trace Detail"
    ::=  { deployProvControlPlaneWdmDefaultsEntry 11 }

deployProvControlPlaneWdmDefaultsRaAlarmActivationTime OBJECT-TYPE
    SYNTAX      Unsigned32 
    UNITS       "s"
    MAX-ACCESS  read-only
    STATUS      current
    DESCRIPTION   "Resource Allocator Component' Alarm Activation Time"
    ::=  { deployProvControlPlaneWdmDefaultsEntry 12 }

deployProvControlPlaneWdmDefaultsCmConfigFlag OBJECT-TYPE
    SYNTAX      Unsigned32
    MAX-ACCESS  read-only
    STATUS      current
    DESCRIPTION   "GMPLS Tunnel Manager Component' Configuration Bitfield"
    ::=  { deployProvControlPlaneWdmDefaultsEntry 13 }

deployProvControlPlaneWdmDefaultsCmTraceDetail OBJECT-TYPE
    SYNTAX      Unsigned32
    MAX-ACCESS  read-only
    STATUS      current
    DESCRIPTION   "GMPLS Tunnel Manager Component' Trace Detail"
    ::=  { deployProvControlPlaneWdmDefaultsEntry 14 }

deployProvControlPlaneWdmDefaultsCmAlarmActivationTime OBJECT-TYPE
    SYNTAX      Unsigned32 
    UNITS       "s"
    MAX-ACCESS  read-only
    STATUS      current
    DESCRIPTION   "GMPLS Tunnel Manager Component' Alarm Activation Time"
    ::=  { deployProvControlPlaneWdmDefaultsEntry 15 }

deployProvControlPlaneWdmDefaultsCmFisFrsTimeout OBJECT-TYPE
    SYNTAX      Unsigned32 
    UNITS       "s"
    MAX-ACCESS  read-only
    STATUS      current
    DESCRIPTION   "GMPLS Tunnel Manager Component' FIS-FRS Timeout"
    ::=  { deployProvControlPlaneWdmDefaultsEntry 16 }

deployProvControlPlaneWdmDefaultsCmCrankBackTimeout OBJECT-TYPE
    SYNTAX      Unsigned32 
    UNITS       "s"
    MAX-ACCESS  read-only
    STATUS      current
    DESCRIPTION   "GMPLS Tunnel Manager Component' Crank-Back Timeout"
    ::=  { deployProvControlPlaneWdmDefaultsEntry 17 }

deployProvControlPlaneWdmDefaultsCdbConfigFlag OBJECT-TYPE
    SYNTAX      Unsigned32
    MAX-ACCESS  read-only
    STATUS      current
    DESCRIPTION   "Label Swithed Path Database Component Configuration Bitfield"
    ::=  { deployProvControlPlaneWdmDefaultsEntry 18 }

deployProvControlPlaneWdmDefaultsCdbDetail OBJECT-TYPE
    SYNTAX      Unsigned32
    MAX-ACCESS  read-only
    STATUS      current
    DESCRIPTION   "Label Swithed Path Database Component Trace Detail"
    ::=  { deployProvControlPlaneWdmDefaultsEntry 19 }

deployProvControlPlaneWdmDefaultsCdbMaxSize OBJECT-TYPE
    SYNTAX      Unsigned32
    MAX-ACCESS  read-only
    STATUS      current
    DESCRIPTION   "Label Swithed Path Database Component Maximum Size; 0 implies no limit"
    ::=  { deployProvControlPlaneWdmDefaultsEntry 20 }

deployProvControlPlaneWdmDefaultsRsvpMaxExpRestartTime OBJECT-TYPE
    SYNTAX      Counter64String 
    UNITS       "ms"
    MAX-ACCESS  read-only
    STATUS      current
    DESCRIPTION   "Maximum Expected Resource Reservation Protocol Component' Restart Time"
    ::=  { deployProvControlPlaneWdmDefaultsEntry 21 }

deployProvControlPlaneWdmDefaultsRsvpMaxExpRecoveryTime OBJECT-TYPE
    SYNTAX      Unsigned32 
    UNITS       "ms"
    MAX-ACCESS  read-only
    STATUS      current
    DESCRIPTION   "Maximum Expected Resource Reservation Protocol Component' Recovery Time"
    ::=  { deployProvControlPlaneWdmDefaultsEntry 22 }

deployProvControlPlaneWdmDefaultsRsvpConfigFlag OBJECT-TYPE
    SYNTAX      Unsigned32
    MAX-ACCESS  read-only
    STATUS      current
    DESCRIPTION   "Resource Reservation Protocol Component' Configuration Bitfield"
    ::=  { deployProvControlPlaneWdmDefaultsEntry 23 }

deployProvControlPlaneWdmDefaultsTedbConfigFlag OBJECT-TYPE
    SYNTAX      Unsigned32
    MAX-ACCESS  read-only
    STATUS      current
    DESCRIPTION   "Traffic Engineering Component' Configuration Bitfield"
    ::=  { deployProvControlPlaneWdmDefaultsEntry 24 }

deployProvControlPlaneWdmDefaultsTedbTraceDetail OBJECT-TYPE
    SYNTAX      Unsigned32
    MAX-ACCESS  read-only
    STATUS      current
    DESCRIPTION   "Traffic Engineering Component' Trace Detail"
    ::=  { deployProvControlPlaneWdmDefaultsEntry 25 }

deployProvControlPlaneWdmDefaultsTedbMaxSize OBJECT-TYPE
    SYNTAX      Unsigned32
    MAX-ACCESS  read-only
    STATUS      current
    DESCRIPTION   "Traffic Engineering Component' Maximum Size"
    ::=  { deployProvControlPlaneWdmDefaultsEntry 26 }

deployProvControlPlaneWdmDefaultsTedbRouterId OBJECT-TYPE
    SYNTAX      IpAddress
    MAX-ACCESS  read-only
    STATUS      current
    DESCRIPTION   "Traffic Engineering Component' Router ID"
    ::=  { deployProvControlPlaneWdmDefaultsEntry 27 }

deployProvControlPlaneWdmDefaultsTedbMinAdvertWait OBJECT-TYPE
    SYNTAX      Unsigned32 
    UNITS       "s"
    MAX-ACCESS  read-only
    STATUS      current
    DESCRIPTION   "Traffic Engineering Component' Minimum Advertisement Wait"
    ::=  { deployProvControlPlaneWdmDefaultsEntry 28 }

deployProvControlPlaneWdmDefaultsNaasConfigFlag OBJECT-TYPE
    SYNTAX      Unsigned32
    MAX-ACCESS  read-only
    STATUS      current
    DESCRIPTION   "Node Attribute Advertising Service Database Component' Configuration Bitfield"
    ::=  { deployProvControlPlaneWdmDefaultsEntry 29 }

deployProvControlPlaneWdmDefaultsNaasTraceDetail OBJECT-TYPE
    SYNTAX      Unsigned32
    MAX-ACCESS  read-only
    STATUS      current
    DESCRIPTION   "Node Attribute Advertising Service Database Component' Trace Detail"
    ::=  { deployProvControlPlaneWdmDefaultsEntry 30 }

deployProvControlPlaneWdmDefaultsNaasMaxSize OBJECT-TYPE
    SYNTAX      Unsigned32
    MAX-ACCESS  read-only
    STATUS      current
    DESCRIPTION   "Node Attribute Advertising Service Database Component' Maximum Size"
    ::=  { deployProvControlPlaneWdmDefaultsEntry 31 }

deployProvControlPlaneWdmDefaultsNaasAdvertWait OBJECT-TYPE
    SYNTAX      Unsigned32 
    UNITS       "s"
    MAX-ACCESS  read-only
    STATUS      current
    DESCRIPTION   "Node Attribute Advertising Service Database Component' Advertisement Wait"
    ::=  { deployProvControlPlaneWdmDefaultsEntry 32 }

deployProvControlPlaneWdmDefaultsPcConfigFlag OBJECT-TYPE
    SYNTAX      Unsigned32
    MAX-ACCESS  read-only
    STATUS      current
    DESCRIPTION   "Path Computation Component' Configuration Bitfield"
    ::=  { deployProvControlPlaneWdmDefaultsEntry 33 }

deployProvControlPlaneWdmDefaultsPcTraceDetail OBJECT-TYPE
    SYNTAX      Unsigned32
    MAX-ACCESS  read-only
    STATUS      current
    DESCRIPTION   "Path Computation Component' Trace Detail"
    ::=  { deployProvControlPlaneWdmDefaultsEntry 34 }

deployProvControlPlaneWdmDefaultsCdConfigFlag OBJECT-TYPE
    SYNTAX      Unsigned32
    MAX-ACCESS  read-only
    STATUS      current
    DESCRIPTION   "Configuration Data Component' Configuration Bitfield"
    ::=  { deployProvControlPlaneWdmDefaultsEntry 35 }

deployProvControlPlaneWdmDefaultsCdTraceDetail OBJECT-TYPE
    SYNTAX      Unsigned32
    MAX-ACCESS  read-only
    STATUS      current
    DESCRIPTION   "Configuration Data Component' Trace Detail"
    ::=  { deployProvControlPlaneWdmDefaultsEntry 36 }

deployProvControlPlaneWdmDefaultsCdResyncTimeout OBJECT-TYPE
    SYNTAX      Unsigned32
    MAX-ACCESS  read-only
    STATUS      current
    DESCRIPTION   "Configuration Data Component' Resync Timeout"
    ::=  { deployProvControlPlaneWdmDefaultsEntry 37 }

deployProvControlPlaneWdmDefaultsRmConfigFlag OBJECT-TYPE
    SYNTAX      Unsigned32
    MAX-ACCESS  read-only
    STATUS      current
    DESCRIPTION   "Resource Management Component' Configuration Bitfield"
    ::=  { deployProvControlPlaneWdmDefaultsEntry 38 }

deployProvControlPlaneWdmDefaultsRmTraceDetail OBJECT-TYPE
    SYNTAX      Unsigned32
    MAX-ACCESS  read-only
    STATUS      current
    DESCRIPTION   "Resource Management Component' Trace Detail"
    ::=  { deployProvControlPlaneWdmDefaultsEntry 39 }

deployProvControlPlaneWdmDefaultsRmTraceTarget OBJECT-TYPE
    SYNTAX      Unsigned32
    MAX-ACCESS  read-only
    STATUS      current
    DESCRIPTION   "Resource Management Component' Trace Target"
    ::=  { deployProvControlPlaneWdmDefaultsEntry 40 }

deployProvControlPlaneWdmDefaultsNodeNameSyntax OBJECT-TYPE
    SYNTAX      FspR7NodeId
    MAX-ACCESS  read-only
    STATUS      deprecated
    DESCRIPTION   "Node Name Syntax"
    ::=  { deployProvControlPlaneWdmDefaultsEntry 41 }

deployProvControlPlaneWdmDefaultsWaitToRestore OBJECT-TYPE
    SYNTAX      Unsigned32 (5..12 | 4294967295) 
    UNITS       "min"
    MAX-ACCESS  read-only
    STATUS      current
    DESCRIPTION
        "Wait to Restore Timer value" 
    ::=  { deployProvControlPlaneWdmDefaultsEntry 42 }

deployProvTunnelWdmTable OBJECT-TYPE
    SYNTAX      SEQUENCE OF DeployProvTunnelWdmEntry
    MAX-ACCESS  not-accessible
    STATUS      current
    DESCRIPTION   ""
    ::=  { controlPlaneDeployProv 14 }

deployProvTunnelWdmEntry OBJECT-TYPE
    SYNTAX      DeployProvTunnelWdmEntry
    MAX-ACCESS  not-accessible
    STATUS      current
    DESCRIPTION   ""
    INDEX       {
                  controlPlaneWdmEntityIndex
                }
    ::=  { deployProvTunnelWdmTable 1 }

DeployProvTunnelWdmEntry ::=  SEQUENCE
  { deployProvTunnelWdmRowStatus RowStatus,
    deployProvTunnelWdmTunnelId SnmpAdminString,
    deployProvTunnelWdmTunnelNo Unsigned32,
    deployProvTunnelWdmAlias SnmpAdminString,
    deployProvTunnelWdmTunnelType FspR7CpTunnelType,
    deployProvTunnelWdmToTid SnmpAdminString,
    deployProvTunnelWdmToNodeIp IpAddress,
    deployProvTunnelWdmFromAid EntityIndex,
    deployProvTunnelWdmToAid EntityIndex,
    deployProvTunnelWdmConnectionDirection FspR7Conn,
    deployProvTunnelWdmFacilityType FspR7InterfaceType,
    deployProvTunnelWdmTerminationLevel OhTerminationLevel,
    deployProvTunnelWdmFecType FspR7FecType,
    deployProvTunnelWdmStuff FspR7Stuff,
    deployProvTunnelWdmProvisionedPaths SnmpAdminString,
    deployProvTunnelWdmRecoveryType FspR7CpProtectionType,
    deployProvTunnelWdmPin FspR7CpPinning,
    deployProvTunnelWdmRestorationType FspR7CpRestorationType,
    deployProvTunnelWdmSubLayer FspR7SubLayer,
    deployProvTunnelWdmMonitorEntities FspR7EnableDisable,
    deployProvTunnelWdmSubLayerEncoding FspR7SubLayerEncoding,
    deployProvTunnelWdmPceMode FspR7PceMode,
    deployProvTunnelWdmTunnelScope FspR7CpTunnelScope,
    deployProvTunnelWdmLayer FspR7PacketsLayer,
    deployProvTunnelWdmOifUni FspR7YesNo,
    deployProvTunnelWdmReversionType FspR7CpReversionType,
    deployProvTunnelWdmRestorationMode FspR7CpRestorationMode,
    deployProvTunnelWdmRestPathsNoProv Unsigned32,
    deployProvTunnelWdmRestorationPaths SnmpAdminString,
    deployProvTunnelWdmTunnelTemplate FspR7YesNo,
    deployProvTunnelWdmRestorationPathsComputed SnmpAdminString,
    deployProvTunnelWdmFromAidString SnmpAdminString,
    deployProvTunnelWdmToAidString SnmpAdminString,
    deployProvTunnelWdmExcludedPaths SnmpAdminString,
    deployProvTunnelWdmDvPaths SnmpAdminString,
    deployProvTunnelWdmPreferPcs FspR7YesNo,
    deployProvTunnelWdmEroScope SnmpAdminString,
    deployProvTunnelWdmEroLifeCycle SnmpAdminString,
    deployProvTunnelWdmXroScope SnmpAdminString,
    deployProvTunnelWdmXroLifeCycle SnmpAdminString,
    deployProvTunnelWdmFendTerm OhTerminationLevel,
    deployProvTunnelWdmDistrComputation FspR7YesNo }

deployProvTunnelWdmRowStatus OBJECT-TYPE
    SYNTAX      RowStatus
    MAX-ACCESS  read-write
    STATUS      current
    DESCRIPTION
        "RowStatus" 
    ::=  { deployProvTunnelWdmEntry 1 }

deployProvTunnelWdmTunnelId OBJECT-TYPE
    SYNTAX      SnmpAdminString
    MAX-ACCESS  read-write
    STATUS      current
    DESCRIPTION   ""
    ::=  { deployProvTunnelWdmEntry 2 }

deployProvTunnelWdmTunnelNo OBJECT-TYPE
    SYNTAX      Unsigned32
    MAX-ACCESS  read-write
    STATUS      current
    DESCRIPTION   ""
    ::=  { deployProvTunnelWdmEntry 3 }

deployProvTunnelWdmAlias OBJECT-TYPE
    SYNTAX      SnmpAdminString
    MAX-ACCESS  read-write
    STATUS      current
    DESCRIPTION   ""
    ::=  { deployProvTunnelWdmEntry 4 }

deployProvTunnelWdmTunnelType OBJECT-TYPE
    SYNTAX      FspR7CpTunnelType
    MAX-ACCESS  read-write
    STATUS      current
    DESCRIPTION   ""
    ::=  { deployProvTunnelWdmEntry 5 }

deployProvTunnelWdmToTid OBJECT-TYPE
    SYNTAX      SnmpAdminString
    MAX-ACCESS  read-write
    STATUS      current
    DESCRIPTION   ""
    ::=  { deployProvTunnelWdmEntry 6 }

deployProvTunnelWdmToNodeIp OBJECT-TYPE
    SYNTAX      IpAddress
    MAX-ACCESS  read-write
    STATUS      current
    DESCRIPTION   ""
    ::=  { deployProvTunnelWdmEntry 7 }

deployProvTunnelWdmFromAid OBJECT-TYPE
    SYNTAX      EntityIndex
    MAX-ACCESS  read-write
    STATUS      current
    DESCRIPTION   ""
    ::=  { deployProvTunnelWdmEntry 8 }

deployProvTunnelWdmToAid OBJECT-TYPE
    SYNTAX      EntityIndex
    MAX-ACCESS  read-write
    STATUS      current
    DESCRIPTION   ""
    ::=  { deployProvTunnelWdmEntry 9 }

deployProvTunnelWdmConnectionDirection OBJECT-TYPE
    SYNTAX      FspR7Conn
    MAX-ACCESS  read-write
    STATUS      current
    DESCRIPTION   ""
    ::=  { deployProvTunnelWdmEntry 10 }

deployProvTunnelWdmFacilityType OBJECT-TYPE
    SYNTAX      FspR7InterfaceType
    MAX-ACCESS  read-write
    STATUS      current
    DESCRIPTION   ""
    ::=  { deployProvTunnelWdmEntry 11 }

deployProvTunnelWdmTerminationLevel OBJECT-TYPE
    SYNTAX      OhTerminationLevel
    MAX-ACCESS  read-write
    STATUS      current
    DESCRIPTION   ""
    ::=  { deployProvTunnelWdmEntry 12 }

deployProvTunnelWdmFecType OBJECT-TYPE
    SYNTAX      FspR7FecType
    MAX-ACCESS  read-write
    STATUS      current
    DESCRIPTION   ""
    ::=  { deployProvTunnelWdmEntry 13 }

deployProvTunnelWdmStuff OBJECT-TYPE
    SYNTAX      FspR7Stuff
    MAX-ACCESS  read-write
    STATUS      current
    DESCRIPTION   ""
    ::=  { deployProvTunnelWdmEntry 14 }

deployProvTunnelWdmProvisionedPaths OBJECT-TYPE
    SYNTAX      SnmpAdminString
    MAX-ACCESS  read-write
    STATUS      current
    DESCRIPTION   ""
    ::=  { deployProvTunnelWdmEntry 15 }

deployProvTunnelWdmRecoveryType OBJECT-TYPE
    SYNTAX      FspR7CpProtectionType
    MAX-ACCESS  read-write
    STATUS      current
    DESCRIPTION   ""
    ::=  { deployProvTunnelWdmEntry 16 }

deployProvTunnelWdmPin OBJECT-TYPE
    SYNTAX      FspR7CpPinning
    MAX-ACCESS  read-write
    STATUS      current
    DESCRIPTION   ""
    ::=  { deployProvTunnelWdmEntry 17 }

deployProvTunnelWdmRestorationType OBJECT-TYPE
    SYNTAX      FspR7CpRestorationType
    MAX-ACCESS  read-write
    STATUS      current
    DESCRIPTION   ""
    ::=  { deployProvTunnelWdmEntry 18 }

deployProvTunnelWdmSubLayer OBJECT-TYPE
    SYNTAX      FspR7SubLayer
    MAX-ACCESS  read-write
    STATUS      current
    DESCRIPTION   ""
    ::=  { deployProvTunnelWdmEntry 19 }

deployProvTunnelWdmMonitorEntities OBJECT-TYPE
    SYNTAX      FspR7EnableDisable
    MAX-ACCESS  read-write
    STATUS      current
    DESCRIPTION   ""
    ::=  { deployProvTunnelWdmEntry 20 }

deployProvTunnelWdmSubLayerEncoding OBJECT-TYPE
    SYNTAX      FspR7SubLayerEncoding
    MAX-ACCESS  read-write
    STATUS      current
    DESCRIPTION   ""
    ::=  { deployProvTunnelWdmEntry 21 }

deployProvTunnelWdmPceMode OBJECT-TYPE
    SYNTAX      FspR7PceMode
    MAX-ACCESS  read-write
    STATUS      current
    DESCRIPTION   ""
    ::=  { deployProvTunnelWdmEntry 22 }

deployProvTunnelWdmTunnelScope OBJECT-TYPE
    SYNTAX      FspR7CpTunnelScope
    MAX-ACCESS  read-write
    STATUS      current
    DESCRIPTION
        "Service Scope extending over either Client or Network Ports of Modules or Links (UN or NR) for Connection Segements" 
    ::=  { deployProvTunnelWdmEntry 23 }

deployProvTunnelWdmLayer OBJECT-TYPE
    SYNTAX      FspR7PacketsLayer
    MAX-ACCESS  read-write
    STATUS      current
    DESCRIPTION
        "Notional Layer of Advertisement on Packets on the LIF" 
    ::=  { deployProvTunnelWdmEntry 24 }

deployProvTunnelWdmOifUni OBJECT-TYPE
    SYNTAX      FspR7YesNo
    MAX-ACCESS  read-write
    STATUS      current
    DESCRIPTION
        "OIF UNI Tunnel" 
    ::=  { deployProvTunnelWdmEntry 25 }

deployProvTunnelWdmReversionType OBJECT-TYPE
    SYNTAX      FspR7CpReversionType
    MAX-ACCESS  read-write
    STATUS      current
    DESCRIPTION
        "Manual Reversion, Automatic Reversion, or no reversion at all for tunnels supporting restoration" 
    ::=  { deployProvTunnelWdmEntry 26 }

deployProvTunnelWdmRestorationMode OBJECT-TYPE
    SYNTAX      FspR7CpRestorationMode
    MAX-ACCESS  read-write
    STATUS      current
    DESCRIPTION
        "Restoration Mode (replaces pinning)" 
    ::=  { deployProvTunnelWdmEntry 27 }

deployProvTunnelWdmRestPathsNoProv OBJECT-TYPE
    SYNTAX      Unsigned32
    MAX-ACCESS  read-write
    STATUS      current
    DESCRIPTION
        "Number of provisioned Guaranteed Restoration Paths" 
    ::=  { deployProvTunnelWdmEntry 28 }

deployProvTunnelWdmRestorationPaths OBJECT-TYPE
    SYNTAX      SnmpAdminString
    MAX-ACCESS  read-write
    STATUS      current
    DESCRIPTION
        "" 
    ::=  { deployProvTunnelWdmEntry 29 }

deployProvTunnelWdmTunnelTemplate OBJECT-TYPE
    SYNTAX      FspR7YesNo
    MAX-ACCESS  read-write
    STATUS      current
    DESCRIPTION
        "Tunnel Template, can't be brought into service" 
    ::=  { deployProvTunnelWdmEntry 30 }

deployProvTunnelWdmRestorationPathsComputed OBJECT-TYPE
    SYNTAX      SnmpAdminString
    MAX-ACCESS  read-write
    STATUS      current
    DESCRIPTION
        "" 
    ::=  { deployProvTunnelWdmEntry 31 }

deployProvTunnelWdmFromAidString OBJECT-TYPE
    SYNTAX      SnmpAdminString
    MAX-ACCESS  read-write
    STATUS      current
    DESCRIPTION
        "" 
    ::=  { deployProvTunnelWdmEntry 32 }

deployProvTunnelWdmToAidString OBJECT-TYPE
    SYNTAX      SnmpAdminString
    MAX-ACCESS  read-write
    STATUS      current
    DESCRIPTION
        "" 
    ::=  { deployProvTunnelWdmEntry 33 }

deployProvTunnelWdmExcludedPaths OBJECT-TYPE
    SYNTAX      SnmpAdminString
    MAX-ACCESS  read-write
    STATUS      current
    DESCRIPTION
        "Lists of Path Elements to be excluded" 
    ::=  { deployProvTunnelWdmEntry 34 }

deployProvTunnelWdmDvPaths OBJECT-TYPE
    SYNTAX      SnmpAdminString
    MAX-ACCESS  read-write
    STATUS      current
    DESCRIPTION
        "Control Plane Diversity Reference Identifier (DV)" 
    ::=  { deployProvTunnelWdmEntry 35 }

deployProvTunnelWdmPreferPcs OBJECT-TYPE
    SYNTAX      FspR7YesNo
    MAX-ACCESS  read-write
    STATUS      current
    DESCRIPTION
        "Preferred Path Computation Engine (Server)" 
    ::=  { deployProvTunnelWdmEntry 36 }

deployProvTunnelWdmEroScope OBJECT-TYPE
    SYNTAX      SnmpAdminString
    MAX-ACCESS  read-write
    STATUS      current
    DESCRIPTION
        "Inclusion Route - Scope" 
    ::=  { deployProvTunnelWdmEntry 37 }

deployProvTunnelWdmEroLifeCycle OBJECT-TYPE
    SYNTAX      SnmpAdminString
    MAX-ACCESS  read-write
    STATUS      current
    DESCRIPTION
        "Inclusion Route - Life Cycle" 
    ::=  { deployProvTunnelWdmEntry 38 }

deployProvTunnelWdmXroScope OBJECT-TYPE
    SYNTAX      SnmpAdminString
    MAX-ACCESS  read-write
    STATUS      current
    DESCRIPTION
        "Exclusion Path Elements - Scope" 
    ::=  { deployProvTunnelWdmEntry 39 }

deployProvTunnelWdmXroLifeCycle OBJECT-TYPE
    SYNTAX      SnmpAdminString
    MAX-ACCESS  read-write
    STATUS      current
    DESCRIPTION
        "Exclusion Path Elements - Life Cycle" 
    ::=  { deployProvTunnelWdmEntry 40 }

deployProvTunnelWdmFendTerm OBJECT-TYPE
    SYNTAX      OhTerminationLevel
    MAX-ACCESS  read-write
    STATUS      current
    DESCRIPTION
        "Far End Termination Level" 
    ::=  { deployProvTunnelWdmEntry 41 }

deployProvTunnelWdmDistrComputation OBJECT-TYPE
    SYNTAX      FspR7YesNo
    MAX-ACCESS  read-write
    STATUS      current
    DESCRIPTION
        "Disttributed Path Computation otherwise Compound Path Computation" 
    ::=  { deployProvTunnelWdmEntry 42 }

deployProvTunnelWdmCapTable OBJECT-TYPE
    SYNTAX      SEQUENCE OF DeployProvTunnelWdmCapEntry
    MAX-ACCESS  not-accessible
    STATUS      current
    DESCRIPTION   ""
    ::=  { controlPlaneDeployProv 15  }

deployProvTunnelWdmCapEntry OBJECT-TYPE
    SYNTAX      DeployProvTunnelWdmCapEntry
    MAX-ACCESS  not-accessible
    STATUS      current
    DESCRIPTION   ""
    INDEX       { controlPlaneWdmEntityIndex }
    ::=  { deployProvTunnelWdmCapTable 1 }

DeployProvTunnelWdmCapEntry ::=  SEQUENCE
  { deployProvTunnelWdmCapRowStatus FspR7RowStatusCaps,
    deployProvTunnelWdmCapTunnelId Integer32,
    deployProvTunnelWdmCapTunnelNo FspR7Unsigned32Caps,
    deployProvTunnelWdmCapAlias Integer32,
    deployProvTunnelWdmCapTunnelType FspR7CpTunnelTypeCaps,
    deployProvTunnelWdmCapToTid Integer32,
    deployProvTunnelWdmCapToNodeIp FspR7YesNo,
    deployProvTunnelWdmCapFromAid Integer32,
    deployProvTunnelWdmCapToAid Integer32,
    deployProvTunnelWdmCapConnectionDirection FspR7ConnCaps,
    deployProvTunnelWdmCapFacilityType FspR7InterfaceTypeCaps,
    deployProvTunnelWdmCapTerminationLevel OhTerminationLevelCaps,
    deployProvTunnelWdmCapFecType FspR7FecTypeCaps,
    deployProvTunnelWdmCapStuff FspR7StuffCaps,
    deployProvTunnelWdmCapProvisionedPaths Integer32,
    deployProvTunnelWdmCapRecoveryType FspR7CpProtectionTypeCaps,
    deployProvTunnelWdmCapPin FspR7CpPinningCaps,
    deployProvTunnelWdmCapRestorationType FspR7CpRestorationTypeCaps,
    deployProvTunnelWdmCapSubLayer FspR7SubLayerCaps,
    deployProvTunnelWdmCapMonitorEntities FspR7EnableDisableCaps,
    deployProvTunnelWdmCapSubLayerEncoding FspR7SubLayerEncodingCaps,
    deployProvTunnelWdmCapPceMode FspR7PceModeCaps,
    deployProvTunnelWdmCapTunnelScope FspR7CpTunnelScopeCaps,
    deployProvTunnelWdmCapLayer FspR7PacketsLayerCaps,
    deployProvTunnelWdmCapOifUni FspR7YesNoCaps,
    deployProvTunnelWdmCapReversionType FspR7CpReversionTypeCaps,
    deployProvTunnelWdmCapRestorationMode FspR7CpRestorationModeCaps,
    deployProvTunnelWdmCapRestPathsNoProv FspR7Unsigned32Caps,
    deployProvTunnelWdmCapRestorationPaths Integer32,
    deployProvTunnelWdmCapTunnelTemplate FspR7YesNoCaps,
    deployProvTunnelWdmCapRestorationPathsComputed Integer32,
    deployProvTunnelWdmCapFromAidString Integer32,
    deployProvTunnelWdmCapToAidString Integer32,
    deployProvTunnelWdmCapExcludedPaths SnmpAdminString,
    deployProvTunnelWdmCapDvPaths SnmpAdminString,
    deployProvTunnelWdmCapPreferPcs FspR7YesNoCaps,
    deployProvTunnelWdmCapEroScope SnmpAdminString,
    deployProvTunnelWdmCapEroLifeCycle SnmpAdminString,
    deployProvTunnelWdmCapXroScope SnmpAdminString,
    deployProvTunnelWdmCapXroLifeCycle SnmpAdminString,
    deployProvTunnelWdmCapFendTerm OhTerminationLevelCaps,
    deployProvTunnelWdmCapDistrComputation FspR7YesNoCaps }

deployProvTunnelWdmCapRowStatus OBJECT-TYPE
    SYNTAX      FspR7RowStatusCaps
    MAX-ACCESS  read-only
    STATUS      current
    DESCRIPTION
        "RowStatus" 
    ::=  { deployProvTunnelWdmCapEntry 1 }

deployProvTunnelWdmCapTunnelId OBJECT-TYPE
    SYNTAX      Integer32
    MAX-ACCESS  read-only
    STATUS      current
    DESCRIPTION   ""
    ::=  { deployProvTunnelWdmCapEntry 2 }

deployProvTunnelWdmCapTunnelNo OBJECT-TYPE
    SYNTAX      FspR7Unsigned32Caps
    MAX-ACCESS  read-only
    STATUS      current
    DESCRIPTION   ""
    ::=  { deployProvTunnelWdmCapEntry 3 }

deployProvTunnelWdmCapAlias OBJECT-TYPE
    SYNTAX      Integer32
    MAX-ACCESS  read-only
    STATUS      current
    DESCRIPTION   ""
    ::=  { deployProvTunnelWdmCapEntry 4 }

deployProvTunnelWdmCapTunnelType OBJECT-TYPE
    SYNTAX      FspR7CpTunnelTypeCaps
    MAX-ACCESS  read-only
    STATUS      current
    DESCRIPTION   ""
    ::=  { deployProvTunnelWdmCapEntry 5 }

deployProvTunnelWdmCapToTid OBJECT-TYPE
    SYNTAX      Integer32
    MAX-ACCESS  read-only
    STATUS      current
    DESCRIPTION   ""
    ::=  { deployProvTunnelWdmCapEntry 6 }

deployProvTunnelWdmCapToNodeIp OBJECT-TYPE
    SYNTAX      FspR7YesNo
    MAX-ACCESS  read-only
    STATUS      current
    DESCRIPTION   ""
    ::=  { deployProvTunnelWdmCapEntry 7 }

deployProvTunnelWdmCapFromAid OBJECT-TYPE
    SYNTAX      Integer32
    MAX-ACCESS  read-only
    STATUS      current
    DESCRIPTION   ""
    ::=  { deployProvTunnelWdmCapEntry 8 }

deployProvTunnelWdmCapToAid OBJECT-TYPE
    SYNTAX      Integer32
    MAX-ACCESS  read-only
    STATUS      current
    DESCRIPTION   ""
    ::=  { deployProvTunnelWdmCapEntry 9 }

deployProvTunnelWdmCapConnectionDirection OBJECT-TYPE
    SYNTAX      FspR7ConnCaps
    MAX-ACCESS  read-only
    STATUS      current
    DESCRIPTION   ""
    ::=  { deployProvTunnelWdmCapEntry 10 }

deployProvTunnelWdmCapFacilityType OBJECT-TYPE
    SYNTAX      FspR7InterfaceTypeCaps
    MAX-ACCESS  read-only
    STATUS      current
    DESCRIPTION   ""
    ::=  { deployProvTunnelWdmCapEntry 11 }

deployProvTunnelWdmCapTerminationLevel OBJECT-TYPE
    SYNTAX      OhTerminationLevelCaps
    MAX-ACCESS  read-only
    STATUS      current
    DESCRIPTION   ""
    ::=  { deployProvTunnelWdmCapEntry 12 }

deployProvTunnelWdmCapFecType OBJECT-TYPE
    SYNTAX      FspR7FecTypeCaps
    MAX-ACCESS  read-only
    STATUS      current
    DESCRIPTION   ""
    ::=  { deployProvTunnelWdmCapEntry 13 }

deployProvTunnelWdmCapStuff OBJECT-TYPE
    SYNTAX      FspR7StuffCaps
    MAX-ACCESS  read-only
    STATUS      current
    DESCRIPTION   ""
    ::=  { deployProvTunnelWdmCapEntry 14 }

deployProvTunnelWdmCapProvisionedPaths OBJECT-TYPE
    SYNTAX      Integer32
    MAX-ACCESS  read-only
    STATUS      current
    DESCRIPTION   ""
    ::=  { deployProvTunnelWdmCapEntry 15 }

deployProvTunnelWdmCapRecoveryType OBJECT-TYPE
    SYNTAX      FspR7CpProtectionTypeCaps
    MAX-ACCESS  read-only
    STATUS      current
    DESCRIPTION   ""
    ::=  { deployProvTunnelWdmCapEntry 16 }

deployProvTunnelWdmCapPin OBJECT-TYPE
    SYNTAX      FspR7CpPinningCaps
    MAX-ACCESS  read-only
    STATUS      current
    DESCRIPTION   ""
    ::=  { deployProvTunnelWdmCapEntry 17 }

deployProvTunnelWdmCapRestorationType OBJECT-TYPE
    SYNTAX      FspR7CpRestorationTypeCaps
    MAX-ACCESS  read-only
    STATUS      current
    DESCRIPTION   ""
    ::=  { deployProvTunnelWdmCapEntry 18 }

deployProvTunnelWdmCapSubLayer OBJECT-TYPE
    SYNTAX      FspR7SubLayerCaps
    MAX-ACCESS  read-only
    STATUS      current
    DESCRIPTION   ""
    ::=  { deployProvTunnelWdmCapEntry 19 }

deployProvTunnelWdmCapMonitorEntities OBJECT-TYPE
    SYNTAX      FspR7EnableDisableCaps
    MAX-ACCESS  read-only
    STATUS      current
    DESCRIPTION   ""
    ::=  { deployProvTunnelWdmCapEntry 20 }

deployProvTunnelWdmCapSubLayerEncoding OBJECT-TYPE
    SYNTAX      FspR7SubLayerEncodingCaps
    MAX-ACCESS  read-only
    STATUS      current
    DESCRIPTION   ""
    ::=  { deployProvTunnelWdmCapEntry 21 }

deployProvTunnelWdmCapPceMode OBJECT-TYPE
    SYNTAX      FspR7PceModeCaps
    MAX-ACCESS  read-only
    STATUS      current
    DESCRIPTION   ""
    ::=  { deployProvTunnelWdmCapEntry 22 }

deployProvTunnelWdmCapTunnelScope OBJECT-TYPE
    SYNTAX      FspR7CpTunnelScopeCaps
    MAX-ACCESS  read-only
    STATUS      current
    DESCRIPTION
        "Service Scope extending over either Client or Network Ports of Modules or Links (UN or NR) for Connection Segements" 
    ::=  { deployProvTunnelWdmCapEntry 23 }

deployProvTunnelWdmCapLayer OBJECT-TYPE
    SYNTAX      FspR7PacketsLayerCaps
    MAX-ACCESS  read-only
    STATUS      current
    DESCRIPTION
        "Notional Layer of Advertisement on Packets on the LIF" 
    ::=  { deployProvTunnelWdmCapEntry 24 }

deployProvTunnelWdmCapOifUni OBJECT-TYPE
    SYNTAX      FspR7YesNoCaps
    MAX-ACCESS  read-only
    STATUS      current
    DESCRIPTION
        "OIF UNI Tunnel" 
    ::=  { deployProvTunnelWdmCapEntry 25 }

deployProvTunnelWdmCapReversionType OBJECT-TYPE
    SYNTAX      FspR7CpReversionTypeCaps
    MAX-ACCESS  read-only
    STATUS      current
    DESCRIPTION
        "Manual Reversion, Automatic Reversion, or no reversion at all for tunnels supporting restoration" 
    ::=  { deployProvTunnelWdmCapEntry 26 }

deployProvTunnelWdmCapRestorationMode OBJECT-TYPE
    SYNTAX      FspR7CpRestorationModeCaps
    MAX-ACCESS  read-only
    STATUS      current
    DESCRIPTION
        "Restoration Mode (replaces pinning)" 
    ::=  { deployProvTunnelWdmCapEntry 27 }

deployProvTunnelWdmCapRestPathsNoProv OBJECT-TYPE
    SYNTAX      FspR7Unsigned32Caps
    MAX-ACCESS  read-only
    STATUS      current
    DESCRIPTION
        "Number of provisioned Guaranteed Restoration Paths" 
    ::=  { deployProvTunnelWdmCapEntry 28 }

deployProvTunnelWdmCapRestorationPaths OBJECT-TYPE
    SYNTAX      Integer32
    MAX-ACCESS  read-only
    STATUS      current
    DESCRIPTION
        "" 
    ::=  { deployProvTunnelWdmCapEntry 29 }

deployProvTunnelWdmCapTunnelTemplate OBJECT-TYPE
    SYNTAX      FspR7YesNoCaps
    MAX-ACCESS  read-only
    STATUS      current
    DESCRIPTION
        "Tunnel Template, can't be brought into service" 
    ::=  { deployProvTunnelWdmCapEntry 30 }

deployProvTunnelWdmCapRestorationPathsComputed OBJECT-TYPE
    SYNTAX      Integer32
    MAX-ACCESS  read-only
    STATUS      current
    DESCRIPTION
        "" 
    ::=  { deployProvTunnelWdmCapEntry 31 }

deployProvTunnelWdmCapFromAidString OBJECT-TYPE
    SYNTAX      Integer32
    MAX-ACCESS  read-only
    STATUS      current
    DESCRIPTION
        "" 
    ::=  { deployProvTunnelWdmCapEntry 32 }

deployProvTunnelWdmCapToAidString OBJECT-TYPE
    SYNTAX      Integer32
    MAX-ACCESS  read-only
    STATUS      current
    DESCRIPTION
        "" 
    ::=  { deployProvTunnelWdmCapEntry 33 }

deployProvTunnelWdmCapExcludedPaths OBJECT-TYPE
    SYNTAX      SnmpAdminString
    MAX-ACCESS  read-only
    STATUS      current
    DESCRIPTION
        "Lists of Path Elements to be excluded" 
    ::=  { deployProvTunnelWdmCapEntry 34 }

deployProvTunnelWdmCapDvPaths OBJECT-TYPE
    SYNTAX      SnmpAdminString
    MAX-ACCESS  read-only
    STATUS      current
    DESCRIPTION
        "Control Plane Diversity Reference Identifier (DV)" 
    ::=  { deployProvTunnelWdmCapEntry 35 }

deployProvTunnelWdmCapPreferPcs OBJECT-TYPE
    SYNTAX      FspR7YesNoCaps
    MAX-ACCESS  read-only
    STATUS      current
    DESCRIPTION
        "Preferred Path Computation Engine (Server)" 
    ::=  { deployProvTunnelWdmCapEntry 36 }

deployProvTunnelWdmCapEroScope OBJECT-TYPE
    SYNTAX      SnmpAdminString
    MAX-ACCESS  read-only
    STATUS      current
    DESCRIPTION
        "Inclusion Route - Scope" 
    ::=  { deployProvTunnelWdmCapEntry 37 }

deployProvTunnelWdmCapEroLifeCycle OBJECT-TYPE
    SYNTAX      SnmpAdminString
    MAX-ACCESS  read-only
    STATUS      current
    DESCRIPTION
        "Inclusion Route - Life Cycle" 
    ::=  { deployProvTunnelWdmCapEntry 38 }

deployProvTunnelWdmCapXroScope OBJECT-TYPE
    SYNTAX      SnmpAdminString
    MAX-ACCESS  read-only
    STATUS      current
    DESCRIPTION
        "Exclusion Path Elements - Scope" 
    ::=  { deployProvTunnelWdmCapEntry 39 }

deployProvTunnelWdmCapXroLifeCycle OBJECT-TYPE
    SYNTAX      SnmpAdminString
    MAX-ACCESS  read-only
    STATUS      current
    DESCRIPTION
        "Exclusion Path Elements - Life Cycle" 
    ::=  { deployProvTunnelWdmCapEntry 40 }

deployProvTunnelWdmCapFendTerm OBJECT-TYPE
    SYNTAX      OhTerminationLevelCaps
    MAX-ACCESS  read-only
    STATUS      current
    DESCRIPTION
        "Far End Termination Level" 
    ::=  { deployProvTunnelWdmCapEntry 41 }

deployProvTunnelWdmCapDistrComputation OBJECT-TYPE
    SYNTAX      FspR7YesNoCaps
    MAX-ACCESS  read-only
    STATUS      current
    DESCRIPTION
        "Disttributed Path Computation otherwise Compound Path Computation" 
    ::=  { deployProvTunnelWdmCapEntry 42 }

deployProvTunnelWdmDefaultsTable  OBJECT-TYPE
    SYNTAX      SEQUENCE OF DeployProvTunnelWdmDefaultsEntry
    MAX-ACCESS  not-accessible
    STATUS      current
    DESCRIPTION   ""
    ::=  { controlPlaneDeployProv 16  }

deployProvTunnelWdmDefaultsEntry OBJECT-TYPE
    SYNTAX      DeployProvTunnelWdmDefaultsEntry
    MAX-ACCESS  not-accessible
    STATUS      current
    DESCRIPTION   ""
    INDEX       { controlPlaneWdmEntityIndex }
    ::=  { deployProvTunnelWdmDefaultsTable 1 }

DeployProvTunnelWdmDefaultsEntry ::=  SEQUENCE
  { deployProvTunnelWdmDefaultsRowStatus RowStatus,
    deployProvTunnelWdmDefaultsTunnelId SnmpAdminString,
    deployProvTunnelWdmDefaultsTunnelNo Unsigned32,
    deployProvTunnelWdmDefaultsAlias SnmpAdminString,
    deployProvTunnelWdmDefaultsTunnelType FspR7CpTunnelType,
    deployProvTunnelWdmDefaultsToTid SnmpAdminString,
    deployProvTunnelWdmDefaultsToNodeIp IpAddress,
    deployProvTunnelWdmDefaultsFromAid EntityIndex,
    deployProvTunnelWdmDefaultsToAid EntityIndex,
    deployProvTunnelWdmDefaultsConnectionDirection FspR7Conn,
    deployProvTunnelWdmDefaultsFacilityType FspR7InterfaceType,
    deployProvTunnelWdmDefaultsTerminationLevel OhTerminationLevel,
    deployProvTunnelWdmDefaultsFecType FspR7FecType,
    deployProvTunnelWdmDefaultsStuff FspR7Stuff,
    deployProvTunnelWdmDefaultsProvisionedPaths SnmpAdminString,
    deployProvTunnelWdmDefaultsRecoveryType FspR7CpProtectionType,
    deployProvTunnelWdmDefaultsPin FspR7CpPinning,
    deployProvTunnelWdmDefaultsRestorationType FspR7CpRestorationType,
    deployProvTunnelWdmDefaultsSubLayer FspR7SubLayer,
    deployProvTunnelWdmDefaultsMonitorEntities FspR7EnableDisable,
    deployProvTunnelWdmDefaultsSubLayerEncoding FspR7SubLayerEncoding,
    deployProvTunnelWdmDefaultsPceMode FspR7PceMode,
    deployProvTunnelWdmDefaultsTunnelScope FspR7CpTunnelScope,
    deployProvTunnelWdmDefaultsLayer FspR7PacketsLayer,
    deployProvTunnelWdmDefaultsOifUni FspR7YesNo,
    deployProvTunnelWdmDefaultsReversionType FspR7CpReversionType,
    deployProvTunnelWdmDefaultsRestorationMode FspR7CpRestorationMode,
    deployProvTunnelWdmDefaultsRestPathsNoProv Unsigned32,
    deployProvTunnelWdmDefaultsRestorationPaths SnmpAdminString,
    deployProvTunnelWdmDefaultsTunnelTemplate FspR7YesNo,
    deployProvTunnelWdmDefaultsRestorationPathsComputed SnmpAdminString,
    deployProvTunnelWdmDefaultsFromAidString SnmpAdminString,
    deployProvTunnelWdmDefaultsToAidString SnmpAdminString,
    deployProvTunnelWdmDefaultsExcludedPaths SnmpAdminString,
    deployProvTunnelWdmDefaultsDvPaths SnmpAdminString,
    deployProvTunnelWdmDefaultsPreferPcs FspR7YesNo,
    deployProvTunnelWdmDefaultsEroScope SnmpAdminString,
    deployProvTunnelWdmDefaultsEroLifeCycle SnmpAdminString,
    deployProvTunnelWdmDefaultsXroScope SnmpAdminString,
    deployProvTunnelWdmDefaultsXroLifeCycle SnmpAdminString,
    deployProvTunnelWdmDefaultsFendTerm OhTerminationLevel,
    deployProvTunnelWdmDefaultsDistrComputation FspR7YesNo }

deployProvTunnelWdmDefaultsRowStatus OBJECT-TYPE
    SYNTAX      RowStatus
    MAX-ACCESS  read-only
    STATUS      current
    DESCRIPTION
        "RowStatus" 
    ::=  { deployProvTunnelWdmDefaultsEntry 1 }

deployProvTunnelWdmDefaultsTunnelId OBJECT-TYPE
    SYNTAX      SnmpAdminString
    MAX-ACCESS  read-only
    STATUS      current
    DESCRIPTION   ""
    ::=  { deployProvTunnelWdmDefaultsEntry 2 }

deployProvTunnelWdmDefaultsTunnelNo OBJECT-TYPE
    SYNTAX      Unsigned32
    MAX-ACCESS  read-only
    STATUS      current
    DESCRIPTION   ""
    ::=  { deployProvTunnelWdmDefaultsEntry 3 }

deployProvTunnelWdmDefaultsAlias OBJECT-TYPE
    SYNTAX      SnmpAdminString
    MAX-ACCESS  read-only
    STATUS      current
    DESCRIPTION   ""
    ::=  { deployProvTunnelWdmDefaultsEntry 4 }

deployProvTunnelWdmDefaultsTunnelType OBJECT-TYPE
    SYNTAX      FspR7CpTunnelType
    MAX-ACCESS  read-only
    STATUS      current
    DESCRIPTION   ""
    ::=  { deployProvTunnelWdmDefaultsEntry 5 }

deployProvTunnelWdmDefaultsToTid OBJECT-TYPE
    SYNTAX      SnmpAdminString
    MAX-ACCESS  read-only
    STATUS      current
    DESCRIPTION   ""
    ::=  { deployProvTunnelWdmDefaultsEntry 6 }

deployProvTunnelWdmDefaultsToNodeIp OBJECT-TYPE
    SYNTAX      IpAddress
    MAX-ACCESS  read-only
    STATUS      current
    DESCRIPTION   ""
    ::=  { deployProvTunnelWdmDefaultsEntry 7 }

deployProvTunnelWdmDefaultsFromAid OBJECT-TYPE
    SYNTAX      EntityIndex
    MAX-ACCESS  read-only
    STATUS      current
    DESCRIPTION   ""
    ::=  { deployProvTunnelWdmDefaultsEntry 8 }

deployProvTunnelWdmDefaultsToAid OBJECT-TYPE
    SYNTAX      EntityIndex
    MAX-ACCESS  read-only
    STATUS      current
    DESCRIPTION   ""
    ::=  { deployProvTunnelWdmDefaultsEntry 9 }

deployProvTunnelWdmDefaultsConnectionDirection OBJECT-TYPE
    SYNTAX      FspR7Conn
    MAX-ACCESS  read-only
    STATUS      current
    DESCRIPTION   ""
    ::=  { deployProvTunnelWdmDefaultsEntry 10 }

deployProvTunnelWdmDefaultsFacilityType OBJECT-TYPE
    SYNTAX      FspR7InterfaceType
    MAX-ACCESS  read-only
    STATUS      current
    DESCRIPTION   ""
    ::=  { deployProvTunnelWdmDefaultsEntry 11 }

deployProvTunnelWdmDefaultsTerminationLevel OBJECT-TYPE
    SYNTAX      OhTerminationLevel
    MAX-ACCESS  read-only
    STATUS      current
    DESCRIPTION   ""
    ::=  { deployProvTunnelWdmDefaultsEntry 12 }

deployProvTunnelWdmDefaultsFecType OBJECT-TYPE
    SYNTAX      FspR7FecType
    MAX-ACCESS  read-only
    STATUS      current
    DESCRIPTION   ""
    ::=  { deployProvTunnelWdmDefaultsEntry 13 }

deployProvTunnelWdmDefaultsStuff OBJECT-TYPE
    SYNTAX      FspR7Stuff
    MAX-ACCESS  read-only
    STATUS      current
    DESCRIPTION   ""
    ::=  { deployProvTunnelWdmDefaultsEntry 14 }

deployProvTunnelWdmDefaultsProvisionedPaths OBJECT-TYPE
    SYNTAX      SnmpAdminString
    MAX-ACCESS  read-only
    STATUS      current
    DESCRIPTION   ""
    ::=  { deployProvTunnelWdmDefaultsEntry 15 }

deployProvTunnelWdmDefaultsRecoveryType OBJECT-TYPE
    SYNTAX      FspR7CpProtectionType
    MAX-ACCESS  read-only
    STATUS      current
    DESCRIPTION   ""
    ::=  { deployProvTunnelWdmDefaultsEntry 16 }

deployProvTunnelWdmDefaultsPin OBJECT-TYPE
    SYNTAX      FspR7CpPinning
    MAX-ACCESS  read-only
    STATUS      current
    DESCRIPTION   ""
    ::=  { deployProvTunnelWdmDefaultsEntry 17 }

deployProvTunnelWdmDefaultsRestorationType OBJECT-TYPE
    SYNTAX      FspR7CpRestorationType
    MAX-ACCESS  read-only
    STATUS      current
    DESCRIPTION   ""
    ::=  { deployProvTunnelWdmDefaultsEntry 18 }

deployProvTunnelWdmDefaultsSubLayer OBJECT-TYPE
    SYNTAX      FspR7SubLayer
    MAX-ACCESS  read-only
    STATUS      current
    DESCRIPTION   ""
    ::=  { deployProvTunnelWdmDefaultsEntry 19 }

deployProvTunnelWdmDefaultsMonitorEntities OBJECT-TYPE
    SYNTAX      FspR7EnableDisable
    MAX-ACCESS  read-only
    STATUS      current
    DESCRIPTION   ""
    ::=  { deployProvTunnelWdmDefaultsEntry 20 }

deployProvTunnelWdmDefaultsSubLayerEncoding OBJECT-TYPE
    SYNTAX      FspR7SubLayerEncoding
    MAX-ACCESS  read-only
    STATUS      current
    DESCRIPTION   ""
    ::=  { deployProvTunnelWdmDefaultsEntry 21 }

deployProvTunnelWdmDefaultsPceMode OBJECT-TYPE
    SYNTAX      FspR7PceMode
    MAX-ACCESS  read-only
    STATUS      current
    DESCRIPTION   ""
    ::=  { deployProvTunnelWdmDefaultsEntry 22 }

deployProvTunnelWdmDefaultsTunnelScope OBJECT-TYPE
    SYNTAX      FspR7CpTunnelScope
    MAX-ACCESS  read-only
    STATUS      current
    DESCRIPTION
        "Service Scope extending over either Client or Network Ports of Modules or Links (UN or NR) for Connection Segements" 
    ::=  { deployProvTunnelWdmDefaultsEntry 23 }

deployProvTunnelWdmDefaultsLayer OBJECT-TYPE
    SYNTAX      FspR7PacketsLayer
    MAX-ACCESS  read-only
    STATUS      current
    DESCRIPTION
        "Notional Layer of Advertisement on Packets on the LIF" 
    ::=  { deployProvTunnelWdmDefaultsEntry 24 }

deployProvTunnelWdmDefaultsOifUni OBJECT-TYPE
    SYNTAX      FspR7YesNo
    MAX-ACCESS  read-only
    STATUS      current
    DESCRIPTION
        "OIF UNI Tunnel" 
    ::=  { deployProvTunnelWdmDefaultsEntry 25 }

deployProvTunnelWdmDefaultsReversionType OBJECT-TYPE
    SYNTAX      FspR7CpReversionType
    MAX-ACCESS  read-only
    STATUS      current
    DESCRIPTION
        "Manual Reversion, Automatic Reversion, or no reversion at all for tunnels supporting restoration" 
    ::=  { deployProvTunnelWdmDefaultsEntry 26 }

deployProvTunnelWdmDefaultsRestorationMode OBJECT-TYPE
    SYNTAX      FspR7CpRestorationMode
    MAX-ACCESS  read-only
    STATUS      current
    DESCRIPTION
        "Restoration Mode (replaces pinning)" 
    ::=  { deployProvTunnelWdmDefaultsEntry 27 }

deployProvTunnelWdmDefaultsRestPathsNoProv OBJECT-TYPE
    SYNTAX      Unsigned32
    MAX-ACCESS  read-only
    STATUS      current
    DESCRIPTION
        "Number of provisioned Guaranteed Restoration Paths" 
    ::=  { deployProvTunnelWdmDefaultsEntry 28 }

deployProvTunnelWdmDefaultsRestorationPaths OBJECT-TYPE
    SYNTAX      SnmpAdminString
    MAX-ACCESS  read-only
    STATUS      current
    DESCRIPTION
        "" 
    ::=  { deployProvTunnelWdmDefaultsEntry 29 }

deployProvTunnelWdmDefaultsTunnelTemplate OBJECT-TYPE
    SYNTAX      FspR7YesNo
    MAX-ACCESS  read-only
    STATUS      current
    DESCRIPTION
        "Tunnel Template, can't be brought into service" 
    ::=  { deployProvTunnelWdmDefaultsEntry 30 }

deployProvTunnelWdmDefaultsRestorationPathsComputed OBJECT-TYPE
    SYNTAX      SnmpAdminString
    MAX-ACCESS  read-only
    STATUS      current
    DESCRIPTION
        "" 
    ::=  { deployProvTunnelWdmDefaultsEntry 31 }

deployProvTunnelWdmDefaultsFromAidString OBJECT-TYPE
    SYNTAX      SnmpAdminString
    MAX-ACCESS  read-only
    STATUS      current
    DESCRIPTION
        "" 
    ::=  { deployProvTunnelWdmDefaultsEntry 32 }

deployProvTunnelWdmDefaultsToAidString OBJECT-TYPE
    SYNTAX      SnmpAdminString
    MAX-ACCESS  read-only
    STATUS      current
    DESCRIPTION
        "" 
    ::=  { deployProvTunnelWdmDefaultsEntry 33 }

deployProvTunnelWdmDefaultsExcludedPaths OBJECT-TYPE
    SYNTAX      SnmpAdminString
    MAX-ACCESS  read-only
    STATUS      current
    DESCRIPTION
        "Lists of Path Elements to be excluded" 
    ::=  { deployProvTunnelWdmDefaultsEntry 34 }

deployProvTunnelWdmDefaultsDvPaths OBJECT-TYPE
    SYNTAX      SnmpAdminString
    MAX-ACCESS  read-only
    STATUS      current
    DESCRIPTION
        "Control Plane Diversity Reference Identifier (DV)" 
    ::=  { deployProvTunnelWdmDefaultsEntry 35 }

deployProvTunnelWdmDefaultsPreferPcs OBJECT-TYPE
    SYNTAX      FspR7YesNo
    MAX-ACCESS  read-only
    STATUS      current
    DESCRIPTION
        "Preferred Path Computation Engine (Server)" 
    ::=  { deployProvTunnelWdmDefaultsEntry 36 }

deployProvTunnelWdmDefaultsEroScope OBJECT-TYPE
    SYNTAX      SnmpAdminString
    MAX-ACCESS  read-only
    STATUS      current
    DESCRIPTION
        "Inclusion Route - Scope" 
    ::=  { deployProvTunnelWdmDefaultsEntry 37 }

deployProvTunnelWdmDefaultsEroLifeCycle OBJECT-TYPE
    SYNTAX      SnmpAdminString
    MAX-ACCESS  read-only
    STATUS      current
    DESCRIPTION
        "Inclusion Route - Life Cycle" 
    ::=  { deployProvTunnelWdmDefaultsEntry 38 }

deployProvTunnelWdmDefaultsXroScope OBJECT-TYPE
    SYNTAX      SnmpAdminString
    MAX-ACCESS  read-only
    STATUS      current
    DESCRIPTION
        "Exclusion Path Elements - Scope" 
    ::=  { deployProvTunnelWdmDefaultsEntry 39 }

deployProvTunnelWdmDefaultsXroLifeCycle OBJECT-TYPE
    SYNTAX      SnmpAdminString
    MAX-ACCESS  read-only
    STATUS      current
    DESCRIPTION
        "Exclusion Path Elements - Life Cycle" 
    ::=  { deployProvTunnelWdmDefaultsEntry 40 }

deployProvTunnelWdmDefaultsFendTerm OBJECT-TYPE
    SYNTAX      OhTerminationLevel
    MAX-ACCESS  read-only
    STATUS      current
    DESCRIPTION
        "Far End Termination Level" 
    ::=  { deployProvTunnelWdmDefaultsEntry 41 }

deployProvTunnelWdmDefaultsDistrComputation OBJECT-TYPE
    SYNTAX      FspR7YesNo
    MAX-ACCESS  read-only
    STATUS      current
    DESCRIPTION
        "Disttributed Path Computation otherwise Compound Path Computation" 
    ::=  { deployProvTunnelWdmDefaultsEntry 42 }

deployProvPathWdmTable OBJECT-TYPE
    SYNTAX      SEQUENCE OF DeployProvPathWdmEntry
    MAX-ACCESS  not-accessible
    STATUS      current
    DESCRIPTION   ""
    ::=  { controlPlaneDeployProv 18 }

deployProvPathWdmEntry OBJECT-TYPE
    SYNTAX      DeployProvPathWdmEntry
    MAX-ACCESS  not-accessible
    STATUS      current
    DESCRIPTION   ""
    INDEX       {
                  controlPlaneWdmEntityIndex
                }
    ::=  { deployProvPathWdmTable 1 }

DeployProvPathWdmEntry ::=  SEQUENCE
  { deployProvPathWdmRowStatus RowStatus,
    deployProvPathWdmPathId SnmpAdminString }

deployProvPathWdmRowStatus OBJECT-TYPE
    SYNTAX      RowStatus
    MAX-ACCESS  read-write
    STATUS      current
    DESCRIPTION
        "RowStatus" 
    ::=  { deployProvPathWdmEntry 1 }

deployProvPathWdmPathId OBJECT-TYPE
    SYNTAX      SnmpAdminString
    MAX-ACCESS  read-write
    STATUS      current
    DESCRIPTION   ""
    ::=  { deployProvPathWdmEntry 2 }

deployProvPathWdmCapTable OBJECT-TYPE
    SYNTAX      SEQUENCE OF DeployProvPathWdmCapEntry
    MAX-ACCESS  not-accessible
    STATUS      current
    DESCRIPTION   ""
    ::=  { controlPlaneDeployProv 19  }

deployProvPathWdmCapEntry OBJECT-TYPE
    SYNTAX      DeployProvPathWdmCapEntry
    MAX-ACCESS  not-accessible
    STATUS      current
    DESCRIPTION   ""
    INDEX       { controlPlaneWdmEntityIndex }
    ::=  { deployProvPathWdmCapTable 1 }

DeployProvPathWdmCapEntry ::=  SEQUENCE
  { deployProvPathWdmCapRowStatus FspR7RowStatusCaps,
    deployProvPathWdmCapPathId Integer32 }

deployProvPathWdmCapRowStatus OBJECT-TYPE
    SYNTAX      FspR7RowStatusCaps
    MAX-ACCESS  read-only
    STATUS      current
    DESCRIPTION
        "RowStatus" 
    ::=  { deployProvPathWdmCapEntry 1 }

deployProvPathWdmCapPathId OBJECT-TYPE
    SYNTAX      Integer32
    MAX-ACCESS  read-only
    STATUS      current
    DESCRIPTION   ""
    ::=  { deployProvPathWdmCapEntry 2 }

deployProvPathWdmDefaultsTable  OBJECT-TYPE
    SYNTAX      SEQUENCE OF DeployProvPathWdmDefaultsEntry
    MAX-ACCESS  not-accessible
    STATUS      current
    DESCRIPTION   ""
    ::=  { controlPlaneDeployProv 20  }

deployProvPathWdmDefaultsEntry OBJECT-TYPE
    SYNTAX      DeployProvPathWdmDefaultsEntry
    MAX-ACCESS  not-accessible
    STATUS      current
    DESCRIPTION   ""
    INDEX       { controlPlaneWdmEntityIndex }
    ::=  { deployProvPathWdmDefaultsTable 1 }

DeployProvPathWdmDefaultsEntry ::=  SEQUENCE
  { deployProvPathWdmDefaultsRowStatus RowStatus,
    deployProvPathWdmDefaultsPathId SnmpAdminString }

deployProvPathWdmDefaultsRowStatus OBJECT-TYPE
    SYNTAX      RowStatus
    MAX-ACCESS  read-only
    STATUS      current
    DESCRIPTION
        "RowStatus" 
    ::=  { deployProvPathWdmDefaultsEntry 1 }

deployProvPathWdmDefaultsPathId OBJECT-TYPE
    SYNTAX      SnmpAdminString
    MAX-ACCESS  read-only
    STATUS      current
    DESCRIPTION   ""
    ::=  { deployProvPathWdmDefaultsEntry 2 }

deployProvPathElementWdmTable OBJECT-TYPE
    SYNTAX      SEQUENCE OF DeployProvPathElementWdmEntry
    MAX-ACCESS  not-accessible
    STATUS      current
    DESCRIPTION   ""
    ::=  { controlPlaneDeployProv 21 }

deployProvPathElementWdmEntry OBJECT-TYPE
    SYNTAX      DeployProvPathElementWdmEntry
    MAX-ACCESS  not-accessible
    STATUS      current
    DESCRIPTION   ""
    INDEX       {
                  controlPlaneWdmEntityIndex
                }
    ::=  { deployProvPathElementWdmTable 1 }

DeployProvPathElementWdmEntry ::=  SEQUENCE
  { deployProvPathElementWdmRowStatus RowStatus,
    deployProvPathElementWdmTrafficEngineeringType FspR7CpTEType,
    deployProvPathElementWdmLifIp IpAddress,
    deployProvPathElementWdmNodeIp IpAddress,
    deployProvPathElementWdmTid SnmpAdminString,
    deployProvPathElementWdmLogicalInterfaceId Unsigned32,
    deployProvPathElementWdmTie FspR7CpTie,
    deployProvPathElementWdmChannelUp FspR7ChannelNumber,
    deployProvPathElementWdmChannelDown FspR7ChannelNumber,
    deployProvPathElementWdmUpstreamModuleAid EntityIndex,
    deployProvPathElementWdmDownstreamModuleAid EntityIndex,
    deployProvPathElementWdmUpstreamModuleAidString SnmpAdminString,
    deployProvPathElementWdmDownstreamModuleAidString SnmpAdminString }

deployProvPathElementWdmRowStatus OBJECT-TYPE
    SYNTAX      RowStatus
    MAX-ACCESS  read-write
    STATUS      current
    DESCRIPTION
        "RowStatus" 
    ::=  { deployProvPathElementWdmEntry 1 }

deployProvPathElementWdmTrafficEngineeringType OBJECT-TYPE
    SYNTAX      FspR7CpTEType
    MAX-ACCESS  read-write
    STATUS      current
    DESCRIPTION   ""
    ::=  { deployProvPathElementWdmEntry 2 }

deployProvPathElementWdmLifIp OBJECT-TYPE
    SYNTAX      IpAddress
    MAX-ACCESS  read-write
    STATUS      current
    DESCRIPTION   ""
    ::=  { deployProvPathElementWdmEntry 3 }

deployProvPathElementWdmNodeIp OBJECT-TYPE
    SYNTAX      IpAddress
    MAX-ACCESS  read-write
    STATUS      current
    DESCRIPTION   ""
    ::=  { deployProvPathElementWdmEntry 4 }

deployProvPathElementWdmTid OBJECT-TYPE
    SYNTAX      SnmpAdminString
    MAX-ACCESS  read-write
    STATUS      current
    DESCRIPTION   ""
    ::=  { deployProvPathElementWdmEntry 5 }

deployProvPathElementWdmLogicalInterfaceId OBJECT-TYPE
    SYNTAX      Unsigned32
    MAX-ACCESS  read-write
    STATUS      current
    DESCRIPTION   ""
    ::=  { deployProvPathElementWdmEntry 6 }

deployProvPathElementWdmTie OBJECT-TYPE
    SYNTAX      FspR7CpTie
    MAX-ACCESS  read-write
    STATUS      current
    DESCRIPTION   ""
    ::=  { deployProvPathElementWdmEntry 7 }

deployProvPathElementWdmChannelUp OBJECT-TYPE
    SYNTAX      FspR7ChannelNumber
    MAX-ACCESS  read-write
    STATUS      current
    DESCRIPTION   ""
    ::=  { deployProvPathElementWdmEntry 8 }

deployProvPathElementWdmChannelDown OBJECT-TYPE
    SYNTAX      FspR7ChannelNumber
    MAX-ACCESS  read-write
    STATUS      current
    DESCRIPTION   ""
    ::=  { deployProvPathElementWdmEntry 9 }

deployProvPathElementWdmUpstreamModuleAid OBJECT-TYPE
    SYNTAX      EntityIndex
    MAX-ACCESS  read-write
    STATUS      current
    DESCRIPTION   ""
    ::=  { deployProvPathElementWdmEntry 10 }

deployProvPathElementWdmDownstreamModuleAid OBJECT-TYPE
    SYNTAX      EntityIndex
    MAX-ACCESS  read-write
    STATUS      current
    DESCRIPTION   ""
    ::=  { deployProvPathElementWdmEntry 11 }

deployProvPathElementWdmUpstreamModuleAidString OBJECT-TYPE
    SYNTAX      SnmpAdminString
    MAX-ACCESS  read-write
    STATUS      current
    DESCRIPTION   ""
    ::=  { deployProvPathElementWdmEntry 12 }

deployProvPathElementWdmDownstreamModuleAidString OBJECT-TYPE
    SYNTAX      SnmpAdminString
    MAX-ACCESS  read-write
    STATUS      current
    DESCRIPTION   ""
    ::=  { deployProvPathElementWdmEntry 13 }

deployProvPathElementWdmCapTable OBJECT-TYPE
    SYNTAX      SEQUENCE OF DeployProvPathElementWdmCapEntry
    MAX-ACCESS  not-accessible
    STATUS      current
    DESCRIPTION   ""
    ::=  { controlPlaneDeployProv 22  }

deployProvPathElementWdmCapEntry OBJECT-TYPE
    SYNTAX      DeployProvPathElementWdmCapEntry
    MAX-ACCESS  not-accessible
    STATUS      current
    DESCRIPTION   ""
    INDEX       { controlPlaneWdmEntityIndex }
    ::=  { deployProvPathElementWdmCapTable 1 }

DeployProvPathElementWdmCapEntry ::=  SEQUENCE
  { deployProvPathElementWdmCapRowStatus FspR7RowStatusCaps,
    deployProvPathElementWdmCapTrafficEngineeringType FspR7CpTETypeCaps,
    deployProvPathElementWdmCapLifIp FspR7YesNo,
    deployProvPathElementWdmCapNodeIp FspR7YesNo,
    deployProvPathElementWdmCapTid Integer32,
    deployProvPathElementWdmCapLogicalInterfaceId FspR7Unsigned32Caps,
    deployProvPathElementWdmCapTie FspR7CpTieCaps,
    deployProvPathElementWdmCapChannelUp FspR7ChannelNumberCaps,
    deployProvPathElementWdmCapChannelDown FspR7ChannelNumberCaps,
    deployProvPathElementWdmCapUpstreamModuleAid Integer32,
    deployProvPathElementWdmCapDownstreamModuleAid Integer32,
    deployProvPathElementWdmCapUpstreamModuleAidString Integer32,
    deployProvPathElementWdmCapDownstreamModuleAidString Integer32 }

deployProvPathElementWdmCapRowStatus OBJECT-TYPE
    SYNTAX      FspR7RowStatusCaps
    MAX-ACCESS  read-only
    STATUS      current
    DESCRIPTION
        "RowStatus" 
    ::=  { deployProvPathElementWdmCapEntry 1 }

deployProvPathElementWdmCapTrafficEngineeringType OBJECT-TYPE
    SYNTAX      FspR7CpTETypeCaps
    MAX-ACCESS  read-only
    STATUS      current
    DESCRIPTION   ""
    ::=  { deployProvPathElementWdmCapEntry 2 }

deployProvPathElementWdmCapLifIp OBJECT-TYPE
    SYNTAX      FspR7YesNo
    MAX-ACCESS  read-only
    STATUS      current
    DESCRIPTION   ""
    ::=  { deployProvPathElementWdmCapEntry 3 }

deployProvPathElementWdmCapNodeIp OBJECT-TYPE
    SYNTAX      FspR7YesNo
    MAX-ACCESS  read-only
    STATUS      current
    DESCRIPTION   ""
    ::=  { deployProvPathElementWdmCapEntry 4 }

deployProvPathElementWdmCapTid OBJECT-TYPE
    SYNTAX      Integer32
    MAX-ACCESS  read-only
    STATUS      current
    DESCRIPTION   ""
    ::=  { deployProvPathElementWdmCapEntry 5 }

deployProvPathElementWdmCapLogicalInterfaceId OBJECT-TYPE
    SYNTAX      FspR7Unsigned32Caps
    MAX-ACCESS  read-only
    STATUS      current
    DESCRIPTION   ""
    ::=  { deployProvPathElementWdmCapEntry 6 }

deployProvPathElementWdmCapTie OBJECT-TYPE
    SYNTAX      FspR7CpTieCaps
    MAX-ACCESS  read-only
    STATUS      current
    DESCRIPTION   ""
    ::=  { deployProvPathElementWdmCapEntry 7 }

deployProvPathElementWdmCapChannelUp OBJECT-TYPE
    SYNTAX      FspR7ChannelNumberCaps
    MAX-ACCESS  read-only
    STATUS      current
    DESCRIPTION   ""
    ::=  { deployProvPathElementWdmCapEntry 8 }

deployProvPathElementWdmCapChannelDown OBJECT-TYPE
    SYNTAX      FspR7ChannelNumberCaps
    MAX-ACCESS  read-only
    STATUS      current
    DESCRIPTION   ""
    ::=  { deployProvPathElementWdmCapEntry 9 }

deployProvPathElementWdmCapUpstreamModuleAid OBJECT-TYPE
    SYNTAX      Integer32
    MAX-ACCESS  read-only
    STATUS      current
    DESCRIPTION   ""
    ::=  { deployProvPathElementWdmCapEntry 10 }

deployProvPathElementWdmCapDownstreamModuleAid OBJECT-TYPE
    SYNTAX      Integer32
    MAX-ACCESS  read-only
    STATUS      current
    DESCRIPTION   ""
    ::=  { deployProvPathElementWdmCapEntry 11 }

deployProvPathElementWdmCapUpstreamModuleAidString OBJECT-TYPE
    SYNTAX      Integer32
    MAX-ACCESS  read-only
    STATUS      current
    DESCRIPTION   ""
    ::=  { deployProvPathElementWdmCapEntry 12 }

deployProvPathElementWdmCapDownstreamModuleAidString OBJECT-TYPE
    SYNTAX      Integer32
    MAX-ACCESS  read-only
    STATUS      current
    DESCRIPTION   ""
    ::=  { deployProvPathElementWdmCapEntry 13 }

deployProvPathElementWdmDefaultsTable  OBJECT-TYPE
    SYNTAX      SEQUENCE OF DeployProvPathElementWdmDefaultsEntry
    MAX-ACCESS  not-accessible
    STATUS      current
    DESCRIPTION   ""
    ::=  { controlPlaneDeployProv 23  }

deployProvPathElementWdmDefaultsEntry OBJECT-TYPE
    SYNTAX      DeployProvPathElementWdmDefaultsEntry
    MAX-ACCESS  not-accessible
    STATUS      current
    DESCRIPTION   ""
    INDEX       { controlPlaneWdmEntityIndex }
    ::=  { deployProvPathElementWdmDefaultsTable 1 }

DeployProvPathElementWdmDefaultsEntry ::=  SEQUENCE
  { deployProvPathElementWdmDefaultsRowStatus RowStatus,
    deployProvPathElementWdmDefaultsTrafficEngineeringType FspR7CpTEType,
    deployProvPathElementWdmDefaultsLifIp IpAddress,
    deployProvPathElementWdmDefaultsNodeIp IpAddress,
    deployProvPathElementWdmDefaultsTid SnmpAdminString,
    deployProvPathElementWdmDefaultsLogicalInterfaceId Unsigned32,
    deployProvPathElementWdmDefaultsTie FspR7CpTie,
    deployProvPathElementWdmDefaultsChannelUp FspR7ChannelNumber,
    deployProvPathElementWdmDefaultsChannelDown FspR7ChannelNumber,
    deployProvPathElementWdmDefaultsUpstreamModuleAid EntityIndex,
    deployProvPathElementWdmDefaultsDownstreamModuleAid EntityIndex,
    deployProvPathElementWdmDefaultsUpstreamModuleAidString SnmpAdminString,
    deployProvPathElementWdmDefaultsDownstreamModuleAidString SnmpAdminString }

deployProvPathElementWdmDefaultsRowStatus OBJECT-TYPE
    SYNTAX      RowStatus
    MAX-ACCESS  read-only
    STATUS      current
    DESCRIPTION
        "RowStatus" 
    ::=  { deployProvPathElementWdmDefaultsEntry 1 }

deployProvPathElementWdmDefaultsTrafficEngineeringType OBJECT-TYPE
    SYNTAX      FspR7CpTEType
    MAX-ACCESS  read-only
    STATUS      current
    DESCRIPTION   ""
    ::=  { deployProvPathElementWdmDefaultsEntry 2 }

deployProvPathElementWdmDefaultsLifIp OBJECT-TYPE
    SYNTAX      IpAddress
    MAX-ACCESS  read-only
    STATUS      current
    DESCRIPTION   ""
    ::=  { deployProvPathElementWdmDefaultsEntry 3 }

deployProvPathElementWdmDefaultsNodeIp OBJECT-TYPE
    SYNTAX      IpAddress
    MAX-ACCESS  read-only
    STATUS      current
    DESCRIPTION   ""
    ::=  { deployProvPathElementWdmDefaultsEntry 4 }

deployProvPathElementWdmDefaultsTid OBJECT-TYPE
    SYNTAX      SnmpAdminString
    MAX-ACCESS  read-only
    STATUS      current
    DESCRIPTION   ""
    ::=  { deployProvPathElementWdmDefaultsEntry 5 }

deployProvPathElementWdmDefaultsLogicalInterfaceId OBJECT-TYPE
    SYNTAX      Unsigned32
    MAX-ACCESS  read-only
    STATUS      current
    DESCRIPTION   ""
    ::=  { deployProvPathElementWdmDefaultsEntry 6 }

deployProvPathElementWdmDefaultsTie OBJECT-TYPE
    SYNTAX      FspR7CpTie
    MAX-ACCESS  read-only
    STATUS      current
    DESCRIPTION   ""
    ::=  { deployProvPathElementWdmDefaultsEntry 7 }

deployProvPathElementWdmDefaultsChannelUp OBJECT-TYPE
    SYNTAX      FspR7ChannelNumber
    MAX-ACCESS  read-only
    STATUS      current
    DESCRIPTION   ""
    ::=  { deployProvPathElementWdmDefaultsEntry 8 }

deployProvPathElementWdmDefaultsChannelDown OBJECT-TYPE
    SYNTAX      FspR7ChannelNumber
    MAX-ACCESS  read-only
    STATUS      current
    DESCRIPTION   ""
    ::=  { deployProvPathElementWdmDefaultsEntry 9 }

deployProvPathElementWdmDefaultsUpstreamModuleAid OBJECT-TYPE
    SYNTAX      EntityIndex
    MAX-ACCESS  read-only
    STATUS      current
    DESCRIPTION   ""
    ::=  { deployProvPathElementWdmDefaultsEntry 10 }

deployProvPathElementWdmDefaultsDownstreamModuleAid OBJECT-TYPE
    SYNTAX      EntityIndex
    MAX-ACCESS  read-only
    STATUS      current
    DESCRIPTION   ""
    ::=  { deployProvPathElementWdmDefaultsEntry 11 }

deployProvPathElementWdmDefaultsUpstreamModuleAidString OBJECT-TYPE
    SYNTAX      SnmpAdminString
    MAX-ACCESS  read-only
    STATUS      current
    DESCRIPTION   ""
    ::=  { deployProvPathElementWdmDefaultsEntry 12 }

deployProvPathElementWdmDefaultsDownstreamModuleAidString OBJECT-TYPE
    SYNTAX      SnmpAdminString
    MAX-ACCESS  read-only
    STATUS      current
    DESCRIPTION   ""
    ::=  { deployProvPathElementWdmDefaultsEntry 13 }

deployProvCopyPathWdmTable OBJECT-TYPE
    SYNTAX      SEQUENCE OF DeployProvCopyPathWdmEntry
    MAX-ACCESS  not-accessible
    STATUS      current
    DESCRIPTION   ""
    ::=  { controlPlaneDeployProv 24 }

deployProvCopyPathWdmEntry OBJECT-TYPE
    SYNTAX      DeployProvCopyPathWdmEntry
    MAX-ACCESS  not-accessible
    STATUS      current
    DESCRIPTION   ""
    INDEX       {
                  controlPlaneWdmEntityIndex
                }
    ::=  { deployProvCopyPathWdmTable 1 }

DeployProvCopyPathWdmEntry ::=  SEQUENCE
  { deployProvCopyPathWdmRowStatus RowStatus,
    deployProvCopyPathWdmSourcePathIndex EntityIndex,
    deployProvCopyPathWdmPathId SnmpAdminString }

deployProvCopyPathWdmRowStatus OBJECT-TYPE
    SYNTAX      RowStatus
    MAX-ACCESS  read-write
    STATUS      current
    DESCRIPTION
        "RowStatus" 
    ::=  { deployProvCopyPathWdmEntry 1 }

deployProvCopyPathWdmSourcePathIndex OBJECT-TYPE
    SYNTAX      EntityIndex
    MAX-ACCESS  read-write
    STATUS      current
    DESCRIPTION   ""
    ::=  { deployProvCopyPathWdmEntry 2 }

deployProvCopyPathWdmPathId OBJECT-TYPE
    SYNTAX      SnmpAdminString
    MAX-ACCESS  read-write
    STATUS      current
    DESCRIPTION   ""
    ::=  { deployProvCopyPathWdmEntry 3 }

deployProvCopyPathWdmCapTable OBJECT-TYPE
    SYNTAX      SEQUENCE OF DeployProvCopyPathWdmCapEntry
    MAX-ACCESS  not-accessible
    STATUS      current
    DESCRIPTION   ""
    ::=  { controlPlaneDeployProv 25  }

deployProvCopyPathWdmCapEntry OBJECT-TYPE
    SYNTAX      DeployProvCopyPathWdmCapEntry
    MAX-ACCESS  not-accessible
    STATUS      current
    DESCRIPTION   ""
    INDEX       { controlPlaneWdmEntityIndex }
    ::=  { deployProvCopyPathWdmCapTable 1 }

DeployProvCopyPathWdmCapEntry ::=  SEQUENCE
  { deployProvCopyPathWdmCapRowStatus FspR7RowStatusCaps,
    deployProvCopyPathWdmCapSourcePathIndex Integer32,
    deployProvCopyPathWdmCapPathId Integer32 }

deployProvCopyPathWdmCapRowStatus OBJECT-TYPE
    SYNTAX      FspR7RowStatusCaps
    MAX-ACCESS  read-only
    STATUS      current
    DESCRIPTION
        "RowStatus" 
    ::=  { deployProvCopyPathWdmCapEntry 1 }

deployProvCopyPathWdmCapSourcePathIndex OBJECT-TYPE
    SYNTAX      Integer32
    MAX-ACCESS  read-only
    STATUS      current
    DESCRIPTION   ""
    ::=  { deployProvCopyPathWdmCapEntry 2 }

deployProvCopyPathWdmCapPathId OBJECT-TYPE
    SYNTAX      Integer32
    MAX-ACCESS  read-only
    STATUS      current
    DESCRIPTION   ""
    ::=  { deployProvCopyPathWdmCapEntry 3 }

deployProvCopyPathWdmDefaultsTable  OBJECT-TYPE
    SYNTAX      SEQUENCE OF DeployProvCopyPathWdmDefaultsEntry
    MAX-ACCESS  not-accessible
    STATUS      current
    DESCRIPTION   ""
    ::=  { controlPlaneDeployProv 26  }

deployProvCopyPathWdmDefaultsEntry OBJECT-TYPE
    SYNTAX      DeployProvCopyPathWdmDefaultsEntry
    MAX-ACCESS  not-accessible
    STATUS      current
    DESCRIPTION   ""
    INDEX       { controlPlaneWdmEntityIndex }
    ::=  { deployProvCopyPathWdmDefaultsTable 1 }

DeployProvCopyPathWdmDefaultsEntry ::=  SEQUENCE
  { deployProvCopyPathWdmDefaultsRowStatus RowStatus,
    deployProvCopyPathWdmDefaultsSourcePathIndex EntityIndex,
    deployProvCopyPathWdmDefaultsPathId SnmpAdminString }

deployProvCopyPathWdmDefaultsRowStatus OBJECT-TYPE
    SYNTAX      RowStatus
    MAX-ACCESS  read-only
    STATUS      current
    DESCRIPTION
        "RowStatus" 
    ::=  { deployProvCopyPathWdmDefaultsEntry 1 }

deployProvCopyPathWdmDefaultsSourcePathIndex OBJECT-TYPE
    SYNTAX      EntityIndex
    MAX-ACCESS  read-only
    STATUS      current
    DESCRIPTION   ""
    ::=  { deployProvCopyPathWdmDefaultsEntry 2 }

deployProvCopyPathWdmDefaultsPathId OBJECT-TYPE
    SYNTAX      SnmpAdminString
    MAX-ACCESS  read-only
    STATUS      current
    DESCRIPTION   ""
    ::=  { deployProvCopyPathWdmDefaultsEntry 3 }

deployProvLogicalCpIfTable OBJECT-TYPE
    SYNTAX      SEQUENCE OF DeployProvLogicalCpIfEntry
    MAX-ACCESS  not-accessible
    STATUS      current
    DESCRIPTION   ""
    ::=  { controlPlaneDeployProv 46 }

deployProvLogicalCpIfEntry OBJECT-TYPE
    SYNTAX      DeployProvLogicalCpIfEntry
    MAX-ACCESS  not-accessible
    STATUS      current
    DESCRIPTION   ""
    INDEX       {
                  entityIndex
                }
    ::=  { deployProvLogicalCpIfTable 1 }

DeployProvLogicalCpIfEntry ::=  SEQUENCE
  { deployProvLogicalCpIfRowStatus RowStatus,
    deployProvLogicalCpIfFacilityType FspR7InterfaceType,
    deployProvLogicalCpIfAlias SnmpAdminString,
    deployProvLogicalCpIfDcnAid EntityIndex,
    deployProvLogicalCpIfOspf FspR7OspfMode,
    deployProvLogicalCpIfAreaId IpAddress,
    deployProvLogicalCpIfMetric Unsigned32,
    deployProvLogicalCpIfHelloInterval Unsigned32,
    deployProvLogicalCpIfDeadInterval Unsigned32,
    deployProvLogicalCpIfPrio Unsigned32,
    deployProvLogicalCpIfRetransmitInterval Unsigned32,
    deployProvLogicalCpIfAuthType FspR7CpAuthType,
    deployProvLogicalCpIfAuthString SnmpAdminString,
    deployProvLogicalCpIfTransport SnmpAdminString,
    deployProvLogicalCpIfFarEndLifId EntityIndex,
    deployProvLogicalCpIfFarEndNodeIp IpAddress,
    deployProvLogicalCpIfFarEndTid SnmpAdminString,
    deployProvLogicalCpIfLayer FspR7PacketsLayer,
    deployProvLogicalCpIfCpType FspR7CpType,
    deployProvLogicalCpIfRefreshTimeout Unsigned32,
    deployProvLogicalCpIfRefreshMultiplier Unsigned32,
    deployProvLogicalCpIfTeMetric Unsigned32,
    deployProvLogicalCpIfTeAreaId IpAddress,
    deployProvLogicalCpIfLinkColor Unsigned32,
    deployProvLogicalCpIfIpType FspR7IpType,
    deployProvLogicalCpIfIpAddr IpAddress,
    deployProvLogicalCpIfIpAddrMask IpAddress,
    deployProvLogicalCpIfAdmin FspR7AdminState,
    deployProvLogicalCpIfEncapsulation FspR7CpEncapsulation,
    deployProvLogicalCpIfPushedNendIpHeader IpAddress,
    deployProvLogicalCpIfPushedFarEndIpHeader IpAddress,
    deployProvLogicalCpIfTimeToLive Unsigned32,
    deployProvLogicalCpIfNendTeLinkIdNum IpAddress,
    deployProvLogicalCpIfFendTeLinkIdNum IpAddress,
    deployProvLogicalCpIfFendDataLinkId Unsigned32,
    deployProvLogicalCpIfNendTeLinkIdUnn Unsigned32,
    deployProvLogicalCpIfFendTeLinkIdUnn Unsigned32,
    deployProvLogicalCpIfEncoding FspR7CpEncode,
    deployProvLogicalCpIfTunnelAid EntityIndex,
    deployProvLogicalCpIfExtAdvertised FspR7YesNo,
    deployProvLogicalCpIfVTeType FspR7CpVTeType,
    deployProvLogicalCpIfVNodeIp IpAddress,
    deployProvLogicalCpIfVNodeTltp SnmpAdminString,
    deployProvLogicalCpIfDcnAidString SnmpAdminString,
    deployProvLogicalCpIfFarEndLifIdString SnmpAdminString,
    deployProvLogicalCpIfTunnelAidString SnmpAdminString,
    deployProvLogicalCpIfTransportString SnmpAdminString }

deployProvLogicalCpIfRowStatus OBJECT-TYPE
    SYNTAX      RowStatus
    MAX-ACCESS  read-write
    STATUS      current
    DESCRIPTION
        "RowStatus" 
    ::=  { deployProvLogicalCpIfEntry 1 }

deployProvLogicalCpIfFacilityType OBJECT-TYPE
    SYNTAX      FspR7InterfaceType
    MAX-ACCESS  read-write
    STATUS      current
    DESCRIPTION   "Facility Type."
    ::=  { deployProvLogicalCpIfEntry 2 }

deployProvLogicalCpIfAlias OBJECT-TYPE
    SYNTAX      SnmpAdminString
    MAX-ACCESS  read-write
    STATUS      current
    DESCRIPTION   "Alias."
    ::=  { deployProvLogicalCpIfEntry 3 }

deployProvLogicalCpIfDcnAid OBJECT-TYPE
    SYNTAX      EntityIndex
    MAX-ACCESS  read-write
    STATUS      current
    DESCRIPTION   "Alias."
    ::=  { deployProvLogicalCpIfEntry 4 }

deployProvLogicalCpIfOspf OBJECT-TYPE
    SYNTAX      FspR7OspfMode
    MAX-ACCESS  read-write
    STATUS      current
    DESCRIPTION
        "OSPF Routing (Dynamic)" 
    ::=  { deployProvLogicalCpIfEntry 5 }

deployProvLogicalCpIfAreaId OBJECT-TYPE
    SYNTAX      IpAddress
    MAX-ACCESS  read-write
    STATUS      current
    DESCRIPTION
        "OSPF Area ID for IP Interface" 
    ::=  { deployProvLogicalCpIfEntry 6 }

deployProvLogicalCpIfMetric OBJECT-TYPE
    SYNTAX      Unsigned32 (0..65535 | 4294967295)
    MAX-ACCESS  read-write
    STATUS      current
    DESCRIPTION
        "Routing Metric" 
    ::=  { deployProvLogicalCpIfEntry 7 }

deployProvLogicalCpIfHelloInterval OBJECT-TYPE
    SYNTAX      Unsigned32 (1..65535 | 4294967295) 
    UNITS       "s"
    MAX-ACCESS  read-write
    STATUS      current
    DESCRIPTION
        "Hello Interval" 
    ::=  { deployProvLogicalCpIfEntry 8 }

deployProvLogicalCpIfDeadInterval OBJECT-TYPE
    SYNTAX      Unsigned32 (1..65535 | 4294967295) 
    UNITS       "s"
    MAX-ACCESS  read-write
    STATUS      current
    DESCRIPTION
        "Dead Interval" 
    ::=  { deployProvLogicalCpIfEntry 9 }

deployProvLogicalCpIfPrio OBJECT-TYPE
    SYNTAX      Unsigned32 (0..255 | 4294967295)
    MAX-ACCESS  read-write
    STATUS      current
    DESCRIPTION
        "Priority" 
    ::=  { deployProvLogicalCpIfEntry 10 }

deployProvLogicalCpIfRetransmitInterval OBJECT-TYPE
    SYNTAX      Unsigned32 (0..3600 | 4294967295) 
    UNITS       "s"
    MAX-ACCESS  read-write
    STATUS      current
    DESCRIPTION
        "Retransmit Interval" 
    ::=  { deployProvLogicalCpIfEntry 11 }

deployProvLogicalCpIfAuthType OBJECT-TYPE
    SYNTAX      FspR7CpAuthType
    MAX-ACCESS  read-write
    STATUS      current
    DESCRIPTION
        "OSPF Authentication Type" 
    ::=  { deployProvLogicalCpIfEntry 12 }

deployProvLogicalCpIfAuthString OBJECT-TYPE
    SYNTAX      SnmpAdminString
    MAX-ACCESS  read-write
    STATUS      current
    DESCRIPTION
        "OSPF Authentication Key/String depending on Authentication Type" 
    ::=  { deployProvLogicalCpIfEntry 13 }

deployProvLogicalCpIfTransport OBJECT-TYPE
    SYNTAX      SnmpAdminString
    MAX-ACCESS  read-write
    STATUS      current
    DESCRIPTION   "Transport Layer Termination Point."
    ::=  { deployProvLogicalCpIfEntry 14 }

deployProvLogicalCpIfFarEndLifId OBJECT-TYPE
    SYNTAX      EntityIndex
    MAX-ACCESS  read-write
    STATUS      current
    DESCRIPTION   "Far End Transport Layer Termination Point - index of AID"
    ::=  { deployProvLogicalCpIfEntry 15 }

deployProvLogicalCpIfFarEndNodeIp OBJECT-TYPE
    SYNTAX      IpAddress
    MAX-ACCESS  read-write
    STATUS      current
    DESCRIPTION   "FEND Log. Interf. ID."
    ::=  { deployProvLogicalCpIfEntry 16 }

deployProvLogicalCpIfFarEndTid OBJECT-TYPE
    SYNTAX      SnmpAdminString
    MAX-ACCESS  read-write
    STATUS      current
    DESCRIPTION   "Far End Tid."
    ::=  { deployProvLogicalCpIfEntry 17 }

deployProvLogicalCpIfLayer OBJECT-TYPE
    SYNTAX      FspR7PacketsLayer
    MAX-ACCESS  read-write
    STATUS      current
    DESCRIPTION   "Layer of Packets on LIF."
    ::=  { deployProvLogicalCpIfEntry 18 }

deployProvLogicalCpIfCpType OBJECT-TYPE
    SYNTAX      FspR7CpType
    MAX-ACCESS  read-write
    STATUS      current
    DESCRIPTION
        "Control Plane Type" 
    ::=  { deployProvLogicalCpIfEntry 19 }

deployProvLogicalCpIfRefreshTimeout OBJECT-TYPE
    SYNTAX      Unsigned32 (1..65535 | 4294967295) 
    UNITS       "s"
    MAX-ACCESS  read-write
    STATUS      current
    DESCRIPTION
        "Refresh Timeout" 
    ::=  { deployProvLogicalCpIfEntry 20 }

deployProvLogicalCpIfRefreshMultiplier OBJECT-TYPE
    SYNTAX      Unsigned32 (1..20 | 4294967295)
    MAX-ACCESS  read-write
    STATUS      current
    DESCRIPTION
        "Refresh Multiplier" 
    ::=  { deployProvLogicalCpIfEntry 21 }

deployProvLogicalCpIfTeMetric OBJECT-TYPE
    SYNTAX      Unsigned32 (0..65535 | 4294967295)
    MAX-ACCESS  read-write
    STATUS      current
    DESCRIPTION
        "Traffic Engineering Metric" 
    ::=  { deployProvLogicalCpIfEntry 22 }

deployProvLogicalCpIfTeAreaId OBJECT-TYPE
    SYNTAX      IpAddress
    MAX-ACCESS  read-write
    STATUS      current
    DESCRIPTION
        "OSPF Area ID for Traffic Engineering" 
    ::=  { deployProvLogicalCpIfEntry 23 }

deployProvLogicalCpIfLinkColor OBJECT-TYPE
    SYNTAX      Unsigned32
    MAX-ACCESS  read-write
    STATUS      current
    DESCRIPTION
        "Bitfield to express up to 32 colors" 
    ::=  { deployProvLogicalCpIfEntry 24 }

deployProvLogicalCpIfIpType OBJECT-TYPE
    SYNTAX      FspR7IpType
    MAX-ACCESS  read-write
    STATUS      current
    DESCRIPTION
        "Type of IP configuration" 
    ::=  { deployProvLogicalCpIfEntry 25 }

deployProvLogicalCpIfIpAddr OBJECT-TYPE
    SYNTAX      IpAddress
    MAX-ACCESS  read-write
    STATUS      current
    DESCRIPTION
        "IP Address assigned to LAN IP Interface" 
    ::=  { deployProvLogicalCpIfEntry 26 }

deployProvLogicalCpIfIpAddrMask OBJECT-TYPE
    SYNTAX      IpAddress
    MAX-ACCESS  read-write
    STATUS      current
    DESCRIPTION
        "IP MASK assigned to LAN IP Interface" 
    ::=  { deployProvLogicalCpIfEntry 27 }

deployProvLogicalCpIfAdmin OBJECT-TYPE
    SYNTAX      FspR7AdminState
    MAX-ACCESS  read-write
    STATUS      current
    DESCRIPTION
        "Administrative State is displayed in the GUI and Craft. Transition to Unassigend requires the entity to be deleted." 
    ::=  { deployProvLogicalCpIfEntry 28 }

deployProvLogicalCpIfEncapsulation OBJECT-TYPE
    SYNTAX      FspR7CpEncapsulation
    MAX-ACCESS  read-write
    STATUS      current
    DESCRIPTION
        "Encapsulation" 
    ::=  { deployProvLogicalCpIfEntry 29 }

deployProvLogicalCpIfPushedNendIpHeader OBJECT-TYPE
    SYNTAX      IpAddress
    MAX-ACCESS  read-write
    STATUS      current
    DESCRIPTION
        "Pushed Near End IP address in encapsulating header" 
    ::=  { deployProvLogicalCpIfEntry 30 }

deployProvLogicalCpIfPushedFarEndIpHeader OBJECT-TYPE
    SYNTAX      IpAddress
    MAX-ACCESS  read-write
    STATUS      current
    DESCRIPTION
        "Pushed Far End IP address in encapsulating header" 
    ::=  { deployProvLogicalCpIfEntry 31 }

deployProvLogicalCpIfTimeToLive OBJECT-TYPE
    SYNTAX      Unsigned32 (1..255 | 4294967295)
    MAX-ACCESS  read-write
    STATUS      current
    DESCRIPTION
        "Time to Live" 
    ::=  { deployProvLogicalCpIfEntry 32 }

deployProvLogicalCpIfNendTeLinkIdNum OBJECT-TYPE
    SYNTAX      IpAddress
    MAX-ACCESS  read-write
    STATUS      current
    DESCRIPTION
        "Local Traffic Engineering Link Identifier for Numbered Link" 
    ::=  { deployProvLogicalCpIfEntry 33 }

deployProvLogicalCpIfFendTeLinkIdNum OBJECT-TYPE
    SYNTAX      IpAddress
    MAX-ACCESS  read-write
    STATUS      current
    DESCRIPTION
        "Remote Traffic Engineering Link Identifier for Numbered Link" 
    ::=  { deployProvLogicalCpIfEntry 34 }

deployProvLogicalCpIfFendDataLinkId OBJECT-TYPE
    SYNTAX      Unsigned32
    MAX-ACCESS  read-write
    STATUS      current
    DESCRIPTION
        "Remote physical link identifier" 
    ::=  { deployProvLogicalCpIfEntry 35 }

deployProvLogicalCpIfNendTeLinkIdUnn OBJECT-TYPE
    SYNTAX      Unsigned32
    MAX-ACCESS  read-write
    STATUS      current
    DESCRIPTION
        "Local Traffic Engineering Link Identifier for Unnumbered Link" 
    ::=  { deployProvLogicalCpIfEntry 36 }

deployProvLogicalCpIfFendTeLinkIdUnn OBJECT-TYPE
    SYNTAX      Unsigned32
    MAX-ACCESS  read-write
    STATUS      current
    DESCRIPTION
        "Remote Traffic Engineering Link Identifier for Unnumbered Link" 
    ::=  { deployProvLogicalCpIfEntry 37 }

deployProvLogicalCpIfEncoding OBJECT-TYPE
    SYNTAX      FspR7CpEncode
    MAX-ACCESS  read-write
    STATUS      current
    DESCRIPTION
        "Encoding" 
    ::=  { deployProvLogicalCpIfEntry 38 }

deployProvLogicalCpIfTunnelAid OBJECT-TYPE
    SYNTAX      EntityIndex
    MAX-ACCESS  read-write
    STATUS      current
    DESCRIPTION
        "Supporting Tunnel" 
    ::=  { deployProvLogicalCpIfEntry 39 }

deployProvLogicalCpIfExtAdvertised OBJECT-TYPE
    SYNTAX      FspR7YesNo
    MAX-ACCESS  read-write
    STATUS      current
    DESCRIPTION
        "Externally Advertised TE Link" 
    ::=  { deployProvLogicalCpIfEntry 40 }

deployProvLogicalCpIfVTeType OBJECT-TYPE
    SYNTAX      FspR7CpVTeType
    MAX-ACCESS  read-write
    STATUS      current
    DESCRIPTION
        "Type of Virtual TE configuration" 
    ::=  { deployProvLogicalCpIfEntry 41 }

deployProvLogicalCpIfVNodeIp OBJECT-TYPE
    SYNTAX      IpAddress
    MAX-ACCESS  read-write
    STATUS      current
    DESCRIPTION
        "Virtual Node IP" 
    ::=  { deployProvLogicalCpIfEntry 42 }

deployProvLogicalCpIfVNodeTltp OBJECT-TYPE
    SYNTAX      SnmpAdminString
    MAX-ACCESS  read-write
    STATUS      current
    DESCRIPTION
        "Virtual Node Transport Layer Termination Point" 
    ::=  { deployProvLogicalCpIfEntry 43 }

deployProvLogicalCpIfDcnAidString OBJECT-TYPE
    SYNTAX      SnmpAdminString
    MAX-ACCESS  read-write
    STATUS      current
    DESCRIPTION   "Alias."
    ::=  { deployProvLogicalCpIfEntry 44 }

deployProvLogicalCpIfFarEndLifIdString OBJECT-TYPE
    SYNTAX      SnmpAdminString
    MAX-ACCESS  read-write
    STATUS      current
    DESCRIPTION   "Far End Transport Layer Termination Point - index of AID"
    ::=  { deployProvLogicalCpIfEntry 45 }

deployProvLogicalCpIfTunnelAidString OBJECT-TYPE
    SYNTAX      SnmpAdminString
    MAX-ACCESS  read-write
    STATUS      current
    DESCRIPTION
        "Supporting Tunnel" 
    ::=  { deployProvLogicalCpIfEntry 46 }

deployProvLogicalCpIfTransportString OBJECT-TYPE
    SYNTAX      SnmpAdminString
    MAX-ACCESS  read-write
    STATUS      current
    DESCRIPTION   "Transport Layer Termination Point (Aid String format)"
    ::=  { deployProvLogicalCpIfEntry 47 }

deployProvLogicalCpIfCapTable OBJECT-TYPE
    SYNTAX      SEQUENCE OF DeployProvLogicalCpIfCapEntry
    MAX-ACCESS  not-accessible
    STATUS      current
    DESCRIPTION   ""
    ::=  { controlPlaneDeployProv 47  }

deployProvLogicalCpIfCapEntry OBJECT-TYPE
    SYNTAX      DeployProvLogicalCpIfCapEntry
    MAX-ACCESS  not-accessible
    STATUS      current
    DESCRIPTION   ""
    INDEX       { entityIndex }
    ::=  { deployProvLogicalCpIfCapTable 1 }

DeployProvLogicalCpIfCapEntry ::=  SEQUENCE
  { deployProvLogicalCpIfCapRowStatus FspR7RowStatusCaps,
    deployProvLogicalCpIfCapFacilityType FspR7InterfaceTypeCaps,
    deployProvLogicalCpIfCapAlias Integer32,
    deployProvLogicalCpIfCapDcnAid Integer32,
    deployProvLogicalCpIfCapOspf FspR7OspfModeCaps,
    deployProvLogicalCpIfCapAreaId FspR7YesNo,
    deployProvLogicalCpIfCapMetric FspR7Unsigned32Caps,
    deployProvLogicalCpIfCapHelloInterval FspR7Unsigned32Caps,
    deployProvLogicalCpIfCapDeadInterval FspR7Unsigned32Caps,
    deployProvLogicalCpIfCapPrio FspR7Unsigned32Caps,
    deployProvLogicalCpIfCapRetransmitInterval FspR7Unsigned32Caps,
    deployProvLogicalCpIfCapAuthType FspR7CpAuthTypeCaps,
    deployProvLogicalCpIfCapAuthString Integer32,
    deployProvLogicalCpIfCapTransport Integer32,
    deployProvLogicalCpIfCapFarEndLifId Integer32,
    deployProvLogicalCpIfCapFarEndNodeIp FspR7YesNo,
    deployProvLogicalCpIfCapFarEndTid Integer32,
    deployProvLogicalCpIfCapLayer FspR7PacketsLayerCaps,
    deployProvLogicalCpIfCapCpType FspR7CpTypeCaps,
    deployProvLogicalCpIfCapRefreshTimeout FspR7Unsigned32Caps,
    deployProvLogicalCpIfCapRefreshMultiplier FspR7Unsigned32Caps,
    deployProvLogicalCpIfCapTeMetric FspR7Unsigned32Caps,
    deployProvLogicalCpIfCapTeAreaId FspR7YesNo,
    deployProvLogicalCpIfCapLinkColor FspR7Unsigned32Caps,
    deployProvLogicalCpIfCapIpType FspR7IpTypeCaps,
    deployProvLogicalCpIfCapIpAddr FspR7YesNo,
    deployProvLogicalCpIfCapIpAddrMask FspR7YesNo,
    deployProvLogicalCpIfCapAdmin FspR7AdminStateCaps,
    deployProvLogicalCpIfCapEncapsulation FspR7CpEncapsulationCaps,
    deployProvLogicalCpIfCapPushedNendIpHeader FspR7YesNo,
    deployProvLogicalCpIfCapPushedFarEndIpHeader FspR7YesNo,
    deployProvLogicalCpIfCapTimeToLive FspR7Unsigned32Caps,
    deployProvLogicalCpIfCapNendTeLinkIdNum FspR7YesNo,
    deployProvLogicalCpIfCapFendTeLinkIdNum FspR7YesNo,
    deployProvLogicalCpIfCapFendDataLinkId FspR7Unsigned32Caps,
    deployProvLogicalCpIfCapNendTeLinkIdUnn FspR7Unsigned32Caps,
    deployProvLogicalCpIfCapFendTeLinkIdUnn FspR7Unsigned32Caps,
    deployProvLogicalCpIfCapEncoding FspR7CpEncodeCaps,
    deployProvLogicalCpIfCapTunnelAid Integer32,
    deployProvLogicalCpIfCapExtAdvertised FspR7YesNoCaps,
    deployProvLogicalCpIfCapVTeType FspR7CpVTeTypeCaps,
    deployProvLogicalCpIfCapVNodeIp FspR7YesNo,
    deployProvLogicalCpIfCapVNodeTltp FspR7SnmpLongString,
    deployProvLogicalCpIfCapDcnAidString FspR7SnmpLongString,
    deployProvLogicalCpIfCapFarEndLifIdString Integer32,
    deployProvLogicalCpIfCapTunnelAidString Integer32,
    deployProvLogicalCpIfCapTransportString FspR7SnmpLongString }

deployProvLogicalCpIfCapRowStatus OBJECT-TYPE
    SYNTAX      FspR7RowStatusCaps
    MAX-ACCESS  read-only
    STATUS      current
    DESCRIPTION
        "RowStatus" 
    ::=  { deployProvLogicalCpIfCapEntry 1 }

deployProvLogicalCpIfCapFacilityType OBJECT-TYPE
    SYNTAX      FspR7InterfaceTypeCaps
    MAX-ACCESS  read-only
    STATUS      current
    DESCRIPTION   "Facility Type."
    ::=  { deployProvLogicalCpIfCapEntry 2 }

deployProvLogicalCpIfCapAlias OBJECT-TYPE
    SYNTAX      Integer32
    MAX-ACCESS  read-only
    STATUS      current
    DESCRIPTION   "Alias."
    ::=  { deployProvLogicalCpIfCapEntry 3 }

deployProvLogicalCpIfCapDcnAid OBJECT-TYPE
    SYNTAX      Integer32
    MAX-ACCESS  read-only
    STATUS      current
    DESCRIPTION   "Alias."
    ::=  { deployProvLogicalCpIfCapEntry 4 }

deployProvLogicalCpIfCapOspf OBJECT-TYPE
    SYNTAX      FspR7OspfModeCaps
    MAX-ACCESS  read-only
    STATUS      current
    DESCRIPTION
        "OSPF Routing (Dynamic)" 
    ::=  { deployProvLogicalCpIfCapEntry 5 }

deployProvLogicalCpIfCapAreaId OBJECT-TYPE
    SYNTAX      FspR7YesNo
    MAX-ACCESS  read-only
    STATUS      current
    DESCRIPTION
        "OSPF Area ID for IP Interface" 
    ::=  { deployProvLogicalCpIfCapEntry 6 }

deployProvLogicalCpIfCapMetric OBJECT-TYPE
    SYNTAX      FspR7Unsigned32Caps
    MAX-ACCESS  read-only
    STATUS      current
    DESCRIPTION
        "Routing Metric" 
    ::=  { deployProvLogicalCpIfCapEntry 7 }

deployProvLogicalCpIfCapHelloInterval OBJECT-TYPE
    SYNTAX      FspR7Unsigned32Caps
    UNITS       "s"
    MAX-ACCESS  read-only
    STATUS      current
    DESCRIPTION
        "Hello Interval" 
    ::=  { deployProvLogicalCpIfCapEntry 8 }

deployProvLogicalCpIfCapDeadInterval OBJECT-TYPE
    SYNTAX      FspR7Unsigned32Caps
    UNITS       "s"
    MAX-ACCESS  read-only
    STATUS      current
    DESCRIPTION
        "Dead Interval" 
    ::=  { deployProvLogicalCpIfCapEntry 9 }

deployProvLogicalCpIfCapPrio OBJECT-TYPE
    SYNTAX      FspR7Unsigned32Caps
    MAX-ACCESS  read-only
    STATUS      current
    DESCRIPTION
        "Priority" 
    ::=  { deployProvLogicalCpIfCapEntry 10 }

deployProvLogicalCpIfCapRetransmitInterval OBJECT-TYPE
    SYNTAX      FspR7Unsigned32Caps
    UNITS       "s"
    MAX-ACCESS  read-only
    STATUS      current
    DESCRIPTION
        "Retransmit Interval" 
    ::=  { deployProvLogicalCpIfCapEntry 11 }

deployProvLogicalCpIfCapAuthType OBJECT-TYPE
    SYNTAX      FspR7CpAuthTypeCaps
    MAX-ACCESS  read-only
    STATUS      current
    DESCRIPTION
        "OSPF Authentication Type" 
    ::=  { deployProvLogicalCpIfCapEntry 12 }

deployProvLogicalCpIfCapAuthString OBJECT-TYPE
    SYNTAX      Integer32
    MAX-ACCESS  read-only
    STATUS      current
    DESCRIPTION
        "OSPF Authentication Key/String depending on Authentication Type" 
    ::=  { deployProvLogicalCpIfCapEntry 13 }

deployProvLogicalCpIfCapTransport OBJECT-TYPE
    SYNTAX      Integer32
    MAX-ACCESS  read-only
    STATUS      current
    DESCRIPTION   "Transport Layer Termination Point."
    ::=  { deployProvLogicalCpIfCapEntry 14 }

deployProvLogicalCpIfCapFarEndLifId OBJECT-TYPE
    SYNTAX      Integer32
    MAX-ACCESS  read-only
    STATUS      current
    DESCRIPTION   "Far End Transport Layer Termination Point - index of AID"
    ::=  { deployProvLogicalCpIfCapEntry 15 }

deployProvLogicalCpIfCapFarEndNodeIp OBJECT-TYPE
    SYNTAX      FspR7YesNo
    MAX-ACCESS  read-only
    STATUS      current
    DESCRIPTION   "FEND Log. Interf. ID."
    ::=  { deployProvLogicalCpIfCapEntry 16 }

deployProvLogicalCpIfCapFarEndTid OBJECT-TYPE
    SYNTAX      Integer32
    MAX-ACCESS  read-only
    STATUS      current
    DESCRIPTION   "Far End Tid."
    ::=  { deployProvLogicalCpIfCapEntry 17 }

deployProvLogicalCpIfCapLayer OBJECT-TYPE
    SYNTAX      FspR7PacketsLayerCaps
    MAX-ACCESS  read-only
    STATUS      current
    DESCRIPTION   "Layer of Packets on LIF."
    ::=  { deployProvLogicalCpIfCapEntry 18 }

deployProvLogicalCpIfCapCpType OBJECT-TYPE
    SYNTAX      FspR7CpTypeCaps
    MAX-ACCESS  read-only
    STATUS      current
    DESCRIPTION
        "Control Plane Type" 
    ::=  { deployProvLogicalCpIfCapEntry 19 }

deployProvLogicalCpIfCapRefreshTimeout OBJECT-TYPE
    SYNTAX      FspR7Unsigned32Caps
    UNITS       "s"
    MAX-ACCESS  read-only
    STATUS      current
    DESCRIPTION
        "Refresh Timeout" 
    ::=  { deployProvLogicalCpIfCapEntry 20 }

deployProvLogicalCpIfCapRefreshMultiplier OBJECT-TYPE
    SYNTAX      FspR7Unsigned32Caps
    MAX-ACCESS  read-only
    STATUS      current
    DESCRIPTION
        "Refresh Multiplier" 
    ::=  { deployProvLogicalCpIfCapEntry 21 }

deployProvLogicalCpIfCapTeMetric OBJECT-TYPE
    SYNTAX      FspR7Unsigned32Caps
    MAX-ACCESS  read-only
    STATUS      current
    DESCRIPTION
        "Traffic Engineering Metric" 
    ::=  { deployProvLogicalCpIfCapEntry 22 }

deployProvLogicalCpIfCapTeAreaId OBJECT-TYPE
    SYNTAX      FspR7YesNo
    MAX-ACCESS  read-only
    STATUS      current
    DESCRIPTION
        "OSPF Area ID for Traffic Engineering" 
    ::=  { deployProvLogicalCpIfCapEntry 23 }

deployProvLogicalCpIfCapLinkColor OBJECT-TYPE
    SYNTAX      FspR7Unsigned32Caps
    MAX-ACCESS  read-only
    STATUS      current
    DESCRIPTION
        "Bitfield to express up to 32 colors" 
    ::=  { deployProvLogicalCpIfCapEntry 24 }

deployProvLogicalCpIfCapIpType OBJECT-TYPE
    SYNTAX      FspR7IpTypeCaps
    MAX-ACCESS  read-only
    STATUS      current
    DESCRIPTION
        "Type of IP configuration" 
    ::=  { deployProvLogicalCpIfCapEntry 25 }

deployProvLogicalCpIfCapIpAddr OBJECT-TYPE
    SYNTAX      FspR7YesNo
    MAX-ACCESS  read-only
    STATUS      current
    DESCRIPTION
        "IP Address assigned to LAN IP Interface" 
    ::=  { deployProvLogicalCpIfCapEntry 26 }

deployProvLogicalCpIfCapIpAddrMask OBJECT-TYPE
    SYNTAX      FspR7YesNo
    MAX-ACCESS  read-only
    STATUS      current
    DESCRIPTION
        "IP MASK assigned to LAN IP Interface" 
    ::=  { deployProvLogicalCpIfCapEntry 27 }

deployProvLogicalCpIfCapAdmin OBJECT-TYPE
    SYNTAX      FspR7AdminStateCaps
    MAX-ACCESS  read-only
    STATUS      current
    DESCRIPTION
        "Administrative State is displayed in the GUI and Craft. Transition to Unassigend requires the entity to be deleted." 
    ::=  { deployProvLogicalCpIfCapEntry 28 }

deployProvLogicalCpIfCapEncapsulation OBJECT-TYPE
    SYNTAX      FspR7CpEncapsulationCaps
    MAX-ACCESS  read-only
    STATUS      current
    DESCRIPTION
        "Encapsulation" 
    ::=  { deployProvLogicalCpIfCapEntry 29 }

deployProvLogicalCpIfCapPushedNendIpHeader OBJECT-TYPE
    SYNTAX      FspR7YesNo
    MAX-ACCESS  read-only
    STATUS      current
    DESCRIPTION
        "Pushed Near End IP address in encapsulating header" 
    ::=  { deployProvLogicalCpIfCapEntry 30 }

deployProvLogicalCpIfCapPushedFarEndIpHeader OBJECT-TYPE
    SYNTAX      FspR7YesNo
    MAX-ACCESS  read-only
    STATUS      current
    DESCRIPTION
        "Pushed Far End IP address in encapsulating header" 
    ::=  { deployProvLogicalCpIfCapEntry 31 }

deployProvLogicalCpIfCapTimeToLive OBJECT-TYPE
    SYNTAX      FspR7Unsigned32Caps
    MAX-ACCESS  read-only
    STATUS      current
    DESCRIPTION
        "Time to Live" 
    ::=  { deployProvLogicalCpIfCapEntry 32 }

deployProvLogicalCpIfCapNendTeLinkIdNum OBJECT-TYPE
    SYNTAX      FspR7YesNo
    MAX-ACCESS  read-only
    STATUS      current
    DESCRIPTION
        "Local Traffic Engineering Link Identifier for Numbered Link" 
    ::=  { deployProvLogicalCpIfCapEntry 33 }

deployProvLogicalCpIfCapFendTeLinkIdNum OBJECT-TYPE
    SYNTAX      FspR7YesNo
    MAX-ACCESS  read-only
    STATUS      current
    DESCRIPTION
        "Remote Traffic Engineering Link Identifier for Numbered Link" 
    ::=  { deployProvLogicalCpIfCapEntry 34 }

deployProvLogicalCpIfCapFendDataLinkId OBJECT-TYPE
    SYNTAX      FspR7Unsigned32Caps
    MAX-ACCESS  read-only
    STATUS      current
    DESCRIPTION
        "Remote physical link identifier" 
    ::=  { deployProvLogicalCpIfCapEntry 35 }

deployProvLogicalCpIfCapNendTeLinkIdUnn OBJECT-TYPE
    SYNTAX      FspR7Unsigned32Caps
    MAX-ACCESS  read-only
    STATUS      current
    DESCRIPTION
        "Local Traffic Engineering Link Identifier for Unnumbered Link" 
    ::=  { deployProvLogicalCpIfCapEntry 36 }

deployProvLogicalCpIfCapFendTeLinkIdUnn OBJECT-TYPE
    SYNTAX      FspR7Unsigned32Caps
    MAX-ACCESS  read-only
    STATUS      current
    DESCRIPTION
        "Remote Traffic Engineering Link Identifier for Unnumbered Link" 
    ::=  { deployProvLogicalCpIfCapEntry 37 }

deployProvLogicalCpIfCapEncoding OBJECT-TYPE
    SYNTAX      FspR7CpEncodeCaps
    MAX-ACCESS  read-only
    STATUS      current
    DESCRIPTION
        "Encoding" 
    ::=  { deployProvLogicalCpIfCapEntry 38 }

deployProvLogicalCpIfCapTunnelAid OBJECT-TYPE
    SYNTAX      Integer32
    MAX-ACCESS  read-only
    STATUS      current
    DESCRIPTION
        "Supporting Tunnel" 
    ::=  { deployProvLogicalCpIfCapEntry 39 }

deployProvLogicalCpIfCapExtAdvertised OBJECT-TYPE
    SYNTAX      FspR7YesNoCaps
    MAX-ACCESS  read-only
    STATUS      current
    DESCRIPTION
        "Externally Advertised TE Link" 
    ::=  { deployProvLogicalCpIfCapEntry 40 }

deployProvLogicalCpIfCapVTeType OBJECT-TYPE
    SYNTAX      FspR7CpVTeTypeCaps
    MAX-ACCESS  read-only
    STATUS      current
    DESCRIPTION
        "Type of Virtual TE configuration" 
    ::=  { deployProvLogicalCpIfCapEntry 41 }

deployProvLogicalCpIfCapVNodeIp OBJECT-TYPE
    SYNTAX      FspR7YesNo
    MAX-ACCESS  read-only
    STATUS      current
    DESCRIPTION
        "Virtual Node IP" 
    ::=  { deployProvLogicalCpIfCapEntry 42 }

deployProvLogicalCpIfCapVNodeTltp OBJECT-TYPE
    SYNTAX      FspR7SnmpLongString
    MAX-ACCESS  read-only
    STATUS      current
    DESCRIPTION
        "Virtual Node Transport Layer Termination Point" 
    ::=  { deployProvLogicalCpIfCapEntry 43 }

deployProvLogicalCpIfCapDcnAidString OBJECT-TYPE
    SYNTAX      FspR7SnmpLongString
    MAX-ACCESS  read-only
    STATUS      current
    DESCRIPTION   "Alias."
    ::=  { deployProvLogicalCpIfCapEntry 44 }

deployProvLogicalCpIfCapFarEndLifIdString OBJECT-TYPE
    SYNTAX      Integer32
    MAX-ACCESS  read-only
    STATUS      current
    DESCRIPTION   "Far End Transport Layer Termination Point - index of AID"
    ::=  { deployProvLogicalCpIfCapEntry 45 }

deployProvLogicalCpIfCapTunnelAidString OBJECT-TYPE
    SYNTAX      Integer32
    MAX-ACCESS  read-only
    STATUS      current
    DESCRIPTION
        "Supporting Tunnel" 
    ::=  { deployProvLogicalCpIfCapEntry 46 }

deployProvLogicalCpIfCapTransportString OBJECT-TYPE
    SYNTAX      FspR7SnmpLongString
    MAX-ACCESS  read-only
    STATUS      current
    DESCRIPTION   "Transport Layer Termination Point (Aid String format)"
    ::=  { deployProvLogicalCpIfCapEntry 47 }

deployProvLogicalCpIfDefaultsTable  OBJECT-TYPE
    SYNTAX      SEQUENCE OF DeployProvLogicalCpIfDefaultsEntry
    MAX-ACCESS  not-accessible
    STATUS      current
    DESCRIPTION   ""
    ::=  { controlPlaneDeployProv 48  }

deployProvLogicalCpIfDefaultsEntry OBJECT-TYPE
    SYNTAX      DeployProvLogicalCpIfDefaultsEntry
    MAX-ACCESS  not-accessible
    STATUS      current
    DESCRIPTION   ""
    INDEX       { entityIndex }
    ::=  { deployProvLogicalCpIfDefaultsTable 1 }

DeployProvLogicalCpIfDefaultsEntry ::=  SEQUENCE
  { deployProvLogicalCpIfDefaultsRowStatus RowStatus,
    deployProvLogicalCpIfDefaultsFacilityType FspR7InterfaceType,
    deployProvLogicalCpIfDefaultsAlias SnmpAdminString,
    deployProvLogicalCpIfDefaultsDcnAid EntityIndex,
    deployProvLogicalCpIfDefaultsOspf FspR7OspfMode,
    deployProvLogicalCpIfDefaultsAreaId IpAddress,
    deployProvLogicalCpIfDefaultsMetric Unsigned32,
    deployProvLogicalCpIfDefaultsHelloInterval Unsigned32,
    deployProvLogicalCpIfDefaultsDeadInterval Unsigned32,
    deployProvLogicalCpIfDefaultsPrio Unsigned32,
    deployProvLogicalCpIfDefaultsRetransmitInterval Unsigned32,
    deployProvLogicalCpIfDefaultsAuthType FspR7CpAuthType,
    deployProvLogicalCpIfDefaultsAuthString SnmpAdminString,
    deployProvLogicalCpIfDefaultsTransport SnmpAdminString,
    deployProvLogicalCpIfDefaultsFarEndLifId EntityIndex,
    deployProvLogicalCpIfDefaultsFarEndNodeIp IpAddress,
    deployProvLogicalCpIfDefaultsFarEndTid SnmpAdminString,
    deployProvLogicalCpIfDefaultsLayer FspR7PacketsLayer,
    deployProvLogicalCpIfDefaultsCpType FspR7CpType,
    deployProvLogicalCpIfDefaultsRefreshTimeout Unsigned32,
    deployProvLogicalCpIfDefaultsRefreshMultiplier Unsigned32,
    deployProvLogicalCpIfDefaultsTeMetric Unsigned32,
    deployProvLogicalCpIfDefaultsTeAreaId IpAddress,
    deployProvLogicalCpIfDefaultsLinkColor Unsigned32,
    deployProvLogicalCpIfDefaultsIpType FspR7IpType,
    deployProvLogicalCpIfDefaultsIpAddr IpAddress,
    deployProvLogicalCpIfDefaultsIpAddrMask IpAddress,
    deployProvLogicalCpIfDefaultsAdmin FspR7AdminState,
    deployProvLogicalCpIfDefaultsEncapsulation FspR7CpEncapsulation,
    deployProvLogicalCpIfDefaultsPushedNendIpHeader IpAddress,
    deployProvLogicalCpIfDefaultsPushedFarEndIpHeader IpAddress,
    deployProvLogicalCpIfDefaultsTimeToLive Unsigned32,
    deployProvLogicalCpIfDefaultsNendTeLinkIdNum IpAddress,
    deployProvLogicalCpIfDefaultsFendTeLinkIdNum IpAddress,
    deployProvLogicalCpIfDefaultsFendDataLinkId Unsigned32,
    deployProvLogicalCpIfDefaultsNendTeLinkIdUnn Unsigned32,
    deployProvLogicalCpIfDefaultsFendTeLinkIdUnn Unsigned32,
    deployProvLogicalCpIfDefaultsEncoding FspR7CpEncode,
    deployProvLogicalCpIfDefaultsTunnelAid EntityIndex,
    deployProvLogicalCpIfDefaultsExtAdvertised FspR7YesNo,
    deployProvLogicalCpIfDefaultsVTeType FspR7CpVTeType,
    deployProvLogicalCpIfDefaultsVNodeIp IpAddress,
    deployProvLogicalCpIfDefaultsVNodeTltp SnmpAdminString,
    deployProvLogicalCpIfDefaultsDcnAidString SnmpAdminString,
    deployProvLogicalCpIfDefaultsFarEndLifIdString SnmpAdminString,
    deployProvLogicalCpIfDefaultsTunnelAidString SnmpAdminString,
    deployProvLogicalCpIfDefaultsTransportString SnmpAdminString }

deployProvLogicalCpIfDefaultsRowStatus OBJECT-TYPE
    SYNTAX      RowStatus
    MAX-ACCESS  read-only
    STATUS      current
    DESCRIPTION
        "RowStatus" 
    ::=  { deployProvLogicalCpIfDefaultsEntry 1 }

deployProvLogicalCpIfDefaultsFacilityType OBJECT-TYPE
    SYNTAX      FspR7InterfaceType
    MAX-ACCESS  read-only
    STATUS      current
    DESCRIPTION   "Facility Type."
    ::=  { deployProvLogicalCpIfDefaultsEntry 2 }

deployProvLogicalCpIfDefaultsAlias OBJECT-TYPE
    SYNTAX      SnmpAdminString
    MAX-ACCESS  read-only
    STATUS      current
    DESCRIPTION   "Alias."
    ::=  { deployProvLogicalCpIfDefaultsEntry 3 }

deployProvLogicalCpIfDefaultsDcnAid OBJECT-TYPE
    SYNTAX      EntityIndex
    MAX-ACCESS  read-only
    STATUS      current
    DESCRIPTION   "Alias."
    ::=  { deployProvLogicalCpIfDefaultsEntry 4 }

deployProvLogicalCpIfDefaultsOspf OBJECT-TYPE
    SYNTAX      FspR7OspfMode
    MAX-ACCESS  read-only
    STATUS      current
    DESCRIPTION
        "OSPF Routing (Dynamic)" 
    ::=  { deployProvLogicalCpIfDefaultsEntry 5 }

deployProvLogicalCpIfDefaultsAreaId OBJECT-TYPE
    SYNTAX      IpAddress
    MAX-ACCESS  read-only
    STATUS      current
    DESCRIPTION
        "OSPF Area ID for IP Interface" 
    ::=  { deployProvLogicalCpIfDefaultsEntry 6 }

deployProvLogicalCpIfDefaultsMetric OBJECT-TYPE
    SYNTAX      Unsigned32 (0..65535 | 4294967295)
    MAX-ACCESS  read-only
    STATUS      current
    DESCRIPTION
        "Routing Metric" 
    ::=  { deployProvLogicalCpIfDefaultsEntry 7 }

deployProvLogicalCpIfDefaultsHelloInterval OBJECT-TYPE
    SYNTAX      Unsigned32 (1..65535 | 4294967295) 
    UNITS       "s"
    MAX-ACCESS  read-only
    STATUS      current
    DESCRIPTION
        "Hello Interval" 
    ::=  { deployProvLogicalCpIfDefaultsEntry 8 }

deployProvLogicalCpIfDefaultsDeadInterval OBJECT-TYPE
    SYNTAX      Unsigned32 (1..65535 | 4294967295) 
    UNITS       "s"
    MAX-ACCESS  read-only
    STATUS      current
    DESCRIPTION
        "Dead Interval" 
    ::=  { deployProvLogicalCpIfDefaultsEntry 9 }

deployProvLogicalCpIfDefaultsPrio OBJECT-TYPE
    SYNTAX      Unsigned32 (0..255 | 4294967295)
    MAX-ACCESS  read-only
    STATUS      current
    DESCRIPTION
        "Priority" 
    ::=  { deployProvLogicalCpIfDefaultsEntry 10 }

deployProvLogicalCpIfDefaultsRetransmitInterval OBJECT-TYPE
    SYNTAX      Unsigned32 (0..3600 | 4294967295) 
    UNITS       "s"
    MAX-ACCESS  read-only
    STATUS      current
    DESCRIPTION
        "Retransmit Interval" 
    ::=  { deployProvLogicalCpIfDefaultsEntry 11 }

deployProvLogicalCpIfDefaultsAuthType OBJECT-TYPE
    SYNTAX      FspR7CpAuthType
    MAX-ACCESS  read-only
    STATUS      current
    DESCRIPTION
        "OSPF Authentication Type" 
    ::=  { deployProvLogicalCpIfDefaultsEntry 12 }

deployProvLogicalCpIfDefaultsAuthString OBJECT-TYPE
    SYNTAX      SnmpAdminString
    MAX-ACCESS  read-only
    STATUS      current
    DESCRIPTION
        "OSPF Authentication Key/String depending on Authentication Type" 
    ::=  { deployProvLogicalCpIfDefaultsEntry 13 }

deployProvLogicalCpIfDefaultsTransport OBJECT-TYPE
    SYNTAX      SnmpAdminString
    MAX-ACCESS  read-only
    STATUS      current
    DESCRIPTION   "Transport Layer Termination Point."
    ::=  { deployProvLogicalCpIfDefaultsEntry 14 }

deployProvLogicalCpIfDefaultsFarEndLifId OBJECT-TYPE
    SYNTAX      EntityIndex
    MAX-ACCESS  read-only
    STATUS      current
    DESCRIPTION   "Far End Transport Layer Termination Point - index of AID"
    ::=  { deployProvLogicalCpIfDefaultsEntry 15 }

deployProvLogicalCpIfDefaultsFarEndNodeIp OBJECT-TYPE
    SYNTAX      IpAddress
    MAX-ACCESS  read-only
    STATUS      current
    DESCRIPTION   "FEND Log. Interf. ID."
    ::=  { deployProvLogicalCpIfDefaultsEntry 16 }

deployProvLogicalCpIfDefaultsFarEndTid OBJECT-TYPE
    SYNTAX      SnmpAdminString
    MAX-ACCESS  read-only
    STATUS      current
    DESCRIPTION   "Far End Tid."
    ::=  { deployProvLogicalCpIfDefaultsEntry 17 }

deployProvLogicalCpIfDefaultsLayer OBJECT-TYPE
    SYNTAX      FspR7PacketsLayer
    MAX-ACCESS  read-only
    STATUS      current
    DESCRIPTION   "Layer of Packets on LIF."
    ::=  { deployProvLogicalCpIfDefaultsEntry 18 }

deployProvLogicalCpIfDefaultsCpType OBJECT-TYPE
    SYNTAX      FspR7CpType
    MAX-ACCESS  read-only
    STATUS      current
    DESCRIPTION
        "Control Plane Type" 
    ::=  { deployProvLogicalCpIfDefaultsEntry 19 }

deployProvLogicalCpIfDefaultsRefreshTimeout OBJECT-TYPE
    SYNTAX      Unsigned32 (1..65535 | 4294967295) 
    UNITS       "s"
    MAX-ACCESS  read-only
    STATUS      current
    DESCRIPTION
        "Refresh Timeout" 
    ::=  { deployProvLogicalCpIfDefaultsEntry 20 }

deployProvLogicalCpIfDefaultsRefreshMultiplier OBJECT-TYPE
    SYNTAX      Unsigned32 (1..20 | 4294967295)
    MAX-ACCESS  read-only
    STATUS      current
    DESCRIPTION
        "Refresh Multiplier" 
    ::=  { deployProvLogicalCpIfDefaultsEntry 21 }

deployProvLogicalCpIfDefaultsTeMetric OBJECT-TYPE
    SYNTAX      Unsigned32 (0..65535 | 4294967295)
    MAX-ACCESS  read-only
    STATUS      current
    DESCRIPTION
        "Traffic Engineering Metric" 
    ::=  { deployProvLogicalCpIfDefaultsEntry 22 }

deployProvLogicalCpIfDefaultsTeAreaId OBJECT-TYPE
    SYNTAX      IpAddress
    MAX-ACCESS  read-only
    STATUS      current
    DESCRIPTION
        "OSPF Area ID for Traffic Engineering" 
    ::=  { deployProvLogicalCpIfDefaultsEntry 23 }

deployProvLogicalCpIfDefaultsLinkColor OBJECT-TYPE
    SYNTAX      Unsigned32
    MAX-ACCESS  read-only
    STATUS      current
    DESCRIPTION
        "Bitfield to express up to 32 colors" 
    ::=  { deployProvLogicalCpIfDefaultsEntry 24 }

deployProvLogicalCpIfDefaultsIpType OBJECT-TYPE
    SYNTAX      FspR7IpType
    MAX-ACCESS  read-only
    STATUS      current
    DESCRIPTION
        "Type of IP configuration" 
    ::=  { deployProvLogicalCpIfDefaultsEntry 25 }

deployProvLogicalCpIfDefaultsIpAddr OBJECT-TYPE
    SYNTAX      IpAddress
    MAX-ACCESS  read-only
    STATUS      current
    DESCRIPTION
        "IP Address assigned to LAN IP Interface" 
    ::=  { deployProvLogicalCpIfDefaultsEntry 26 }

deployProvLogicalCpIfDefaultsIpAddrMask OBJECT-TYPE
    SYNTAX      IpAddress
    MAX-ACCESS  read-only
    STATUS      current
    DESCRIPTION
        "IP MASK assigned to LAN IP Interface" 
    ::=  { deployProvLogicalCpIfDefaultsEntry 27 }

deployProvLogicalCpIfDefaultsAdmin OBJECT-TYPE
    SYNTAX      FspR7AdminState
    MAX-ACCESS  read-only
    STATUS      current
    DESCRIPTION
        "Administrative State is displayed in the GUI and Craft. Transition to Unassigend requires the entity to be deleted." 
    ::=  { deployProvLogicalCpIfDefaultsEntry 28 }

deployProvLogicalCpIfDefaultsEncapsulation OBJECT-TYPE
    SYNTAX      FspR7CpEncapsulation
    MAX-ACCESS  read-only
    STATUS      current
    DESCRIPTION
        "Encapsulation" 
    ::=  { deployProvLogicalCpIfDefaultsEntry 29 }

deployProvLogicalCpIfDefaultsPushedNendIpHeader OBJECT-TYPE
    SYNTAX      IpAddress
    MAX-ACCESS  read-only
    STATUS      current
    DESCRIPTION
        "Pushed Near End IP address in encapsulating header" 
    ::=  { deployProvLogicalCpIfDefaultsEntry 30 }

deployProvLogicalCpIfDefaultsPushedFarEndIpHeader OBJECT-TYPE
    SYNTAX      IpAddress
    MAX-ACCESS  read-only
    STATUS      current
    DESCRIPTION
        "Pushed Far End IP address in encapsulating header" 
    ::=  { deployProvLogicalCpIfDefaultsEntry 31 }

deployProvLogicalCpIfDefaultsTimeToLive OBJECT-TYPE
    SYNTAX      Unsigned32 (1..255 | 4294967295)
    MAX-ACCESS  read-only
    STATUS      current
    DESCRIPTION
        "Time to Live" 
    ::=  { deployProvLogicalCpIfDefaultsEntry 32 }

deployProvLogicalCpIfDefaultsNendTeLinkIdNum OBJECT-TYPE
    SYNTAX      IpAddress
    MAX-ACCESS  read-only
    STATUS      current
    DESCRIPTION
        "Local Traffic Engineering Link Identifier for Numbered Link" 
    ::=  { deployProvLogicalCpIfDefaultsEntry 33 }

deployProvLogicalCpIfDefaultsFendTeLinkIdNum OBJECT-TYPE
    SYNTAX      IpAddress
    MAX-ACCESS  read-only
    STATUS      current
    DESCRIPTION
        "Remote Traffic Engineering Link Identifier for Numbered Link" 
    ::=  { deployProvLogicalCpIfDefaultsEntry 34 }

deployProvLogicalCpIfDefaultsFendDataLinkId OBJECT-TYPE
    SYNTAX      Unsigned32
    MAX-ACCESS  read-only
    STATUS      current
    DESCRIPTION
        "Remote physical link identifier" 
    ::=  { deployProvLogicalCpIfDefaultsEntry 35 }

deployProvLogicalCpIfDefaultsNendTeLinkIdUnn OBJECT-TYPE
    SYNTAX      Unsigned32
    MAX-ACCESS  read-only
    STATUS      current
    DESCRIPTION
        "Local Traffic Engineering Link Identifier for Unnumbered Link" 
    ::=  { deployProvLogicalCpIfDefaultsEntry 36 }

deployProvLogicalCpIfDefaultsFendTeLinkIdUnn OBJECT-TYPE
    SYNTAX      Unsigned32
    MAX-ACCESS  read-only
    STATUS      current
    DESCRIPTION
        "Remote Traffic Engineering Link Identifier for Unnumbered Link" 
    ::=  { deployProvLogicalCpIfDefaultsEntry 37 }

deployProvLogicalCpIfDefaultsEncoding OBJECT-TYPE
    SYNTAX      FspR7CpEncode
    MAX-ACCESS  read-only
    STATUS      current
    DESCRIPTION
        "Encoding" 
    ::=  { deployProvLogicalCpIfDefaultsEntry 38 }

deployProvLogicalCpIfDefaultsTunnelAid OBJECT-TYPE
    SYNTAX      EntityIndex
    MAX-ACCESS  read-only
    STATUS      current
    DESCRIPTION
        "Supporting Tunnel" 
    ::=  { deployProvLogicalCpIfDefaultsEntry 39 }

deployProvLogicalCpIfDefaultsExtAdvertised OBJECT-TYPE
    SYNTAX      FspR7YesNo
    MAX-ACCESS  read-only
    STATUS      current
    DESCRIPTION
        "Externally Advertised TE Link" 
    ::=  { deployProvLogicalCpIfDefaultsEntry 40 }

deployProvLogicalCpIfDefaultsVTeType OBJECT-TYPE
    SYNTAX      FspR7CpVTeType
    MAX-ACCESS  read-only
    STATUS      current
    DESCRIPTION
        "Type of Virtual TE configuration" 
    ::=  { deployProvLogicalCpIfDefaultsEntry 41 }

deployProvLogicalCpIfDefaultsVNodeIp OBJECT-TYPE
    SYNTAX      IpAddress
    MAX-ACCESS  read-only
    STATUS      current
    DESCRIPTION
        "Virtual Node IP" 
    ::=  { deployProvLogicalCpIfDefaultsEntry 42 }

deployProvLogicalCpIfDefaultsVNodeTltp OBJECT-TYPE
    SYNTAX      SnmpAdminString
    MAX-ACCESS  read-only
    STATUS      current
    DESCRIPTION
        "Virtual Node Transport Layer Termination Point" 
    ::=  { deployProvLogicalCpIfDefaultsEntry 43 }

deployProvLogicalCpIfDefaultsDcnAidString OBJECT-TYPE
    SYNTAX      SnmpAdminString
    MAX-ACCESS  read-only
    STATUS      current
    DESCRIPTION   "Alias."
    ::=  { deployProvLogicalCpIfDefaultsEntry 44 }

deployProvLogicalCpIfDefaultsFarEndLifIdString OBJECT-TYPE
    SYNTAX      SnmpAdminString
    MAX-ACCESS  read-only
    STATUS      current
    DESCRIPTION   "Far End Transport Layer Termination Point - index of AID"
    ::=  { deployProvLogicalCpIfDefaultsEntry 45 }

deployProvLogicalCpIfDefaultsTunnelAidString OBJECT-TYPE
    SYNTAX      SnmpAdminString
    MAX-ACCESS  read-only
    STATUS      current
    DESCRIPTION
        "Supporting Tunnel" 
    ::=  { deployProvLogicalCpIfDefaultsEntry 46 }

deployProvLogicalCpIfDefaultsTransportString OBJECT-TYPE
    SYNTAX      SnmpAdminString
    MAX-ACCESS  read-only
    STATUS      current
    DESCRIPTION   "Transport Layer Termination Point (Aid String format)"
    ::=  { deployProvLogicalCpIfDefaultsEntry 47 }

deployProvControlPlaneEthTable OBJECT-TYPE
    SYNTAX      SEQUENCE OF DeployProvControlPlaneEthEntry
    MAX-ACCESS  not-accessible
    STATUS      current
    DESCRIPTION   ""
    ::=  { controlPlaneDeployProv 61 }

deployProvControlPlaneEthEntry OBJECT-TYPE
    SYNTAX      DeployProvControlPlaneEthEntry
    MAX-ACCESS  not-accessible
    STATUS      current
    DESCRIPTION   ""
    INDEX       {
                  controlPlaneEthEntityIndex
                }
    ::=  { deployProvControlPlaneEthTable 1 }

DeployProvControlPlaneEthEntry ::=  SEQUENCE
  { deployProvControlPlaneEthRowStatus RowStatus,
    deployProvControlPlaneEthCtmConfigFlag Unsigned32,
    deployProvControlPlaneEthCtmTraceDetail Unsigned32,
    deployProvControlPlaneEthCtmSetupTimeout Unsigned32,
    deployProvControlPlaneEthCtmShutdownTimeout Unsigned32,
    deployProvControlPlaneEthCtmRetryWait Unsigned32,
    deployProvControlPlaneEthCtmRetryWaitMultiplier Unsigned32,
    deployProvControlPlaneEthCtmMaximumRetryWait Unsigned32,
    deployProvControlPlaneEthCtmMaximumRetryNumber Unsigned32,
    deployProvControlPlaneEthRaConfigFlag Unsigned32,
    deployProvControlPlaneEthRaTraceDetail Unsigned32,
    deployProvControlPlaneEthRaAlarmActivationTime Unsigned32,
    deployProvControlPlaneEthCmConfigFlag Unsigned32,
    deployProvControlPlaneEthCmTraceDetail Unsigned32,
    deployProvControlPlaneEthCmAlarmActivationTime Unsigned32,
    deployProvControlPlaneEthCmFisFrsTimeout Unsigned32,
    deployProvControlPlaneEthCmCrankBackTimeout Unsigned32,
    deployProvControlPlaneEthCdbConfigFlag Unsigned32,
    deployProvControlPlaneEthCdbDetail Unsigned32,
    deployProvControlPlaneEthCdbMaxSize Unsigned32,
    deployProvControlPlaneEthRsvpMaxExpRestartTime Counter64String,
    deployProvControlPlaneEthRsvpMaxExpRecoveryTime Unsigned32,
    deployProvControlPlaneEthRsvpConfigFlag Unsigned32,
    deployProvControlPlaneEthTedbConfigFlag Unsigned32,
    deployProvControlPlaneEthTedbTraceDetail Unsigned32,
    deployProvControlPlaneEthTedbMaxSize Unsigned32,
    deployProvControlPlaneEthTedbRouterId IpAddress,
    deployProvControlPlaneEthTedbMinAdvertWait Unsigned32,
    deployProvControlPlaneEthNaasConfigFlag Unsigned32,
    deployProvControlPlaneEthNaasTraceDetail Unsigned32,
    deployProvControlPlaneEthNaasMaxSize Unsigned32,
    deployProvControlPlaneEthNaasAdvertWait Unsigned32,
    deployProvControlPlaneEthPcConfigFlag Unsigned32,
    deployProvControlPlaneEthPcTraceDetail Unsigned32,
    deployProvControlPlaneEthCdConfigFlag Unsigned32,
    deployProvControlPlaneEthCdTraceDetail Unsigned32,
    deployProvControlPlaneEthCdResyncTimeout Unsigned32,
    deployProvControlPlaneEthRmConfigFlag Unsigned32,
    deployProvControlPlaneEthRmTraceDetail Unsigned32,
    deployProvControlPlaneEthRmTraceTarget Unsigned32 }

deployProvControlPlaneEthRowStatus OBJECT-TYPE
    SYNTAX      RowStatus
    MAX-ACCESS  read-write
    STATUS      current
    DESCRIPTION   ""
    ::=  { deployProvControlPlaneEthEntry 1 }

deployProvControlPlaneEthCtmConfigFlag OBJECT-TYPE
    SYNTAX      Unsigned32
    MAX-ACCESS  read-write
    STATUS      current
    DESCRIPTION   "Label Switched Path Edge Component' Configuration Bitfield"
    ::=  { deployProvControlPlaneEthEntry 2 }

deployProvControlPlaneEthCtmTraceDetail OBJECT-TYPE
    SYNTAX      Unsigned32
    MAX-ACCESS  read-write
    STATUS      current
    DESCRIPTION   "Label Switched Path Edge Component' Trace Detail"
    ::=  { deployProvControlPlaneEthEntry 3 }

deployProvControlPlaneEthCtmSetupTimeout OBJECT-TYPE
    SYNTAX      Unsigned32 
    UNITS       "s"
    MAX-ACCESS  read-write
    STATUS      current
    DESCRIPTION   "Label Switched Path Edge Component' Set-Up Timeout"
    ::=  { deployProvControlPlaneEthEntry 4 }

deployProvControlPlaneEthCtmShutdownTimeout OBJECT-TYPE
    SYNTAX      Unsigned32 
    UNITS       "s"
    MAX-ACCESS  read-write
    STATUS      current
    DESCRIPTION   "Label Switched Path Edge Component' Shut-Down Timeout"
    ::=  { deployProvControlPlaneEthEntry 5 }

deployProvControlPlaneEthCtmRetryWait OBJECT-TYPE
    SYNTAX      Unsigned32 
    UNITS       "s"
    MAX-ACCESS  read-write
    STATUS      current
    DESCRIPTION   "Label Switched Path Edge Component' Initialization Retry Wait"
    ::=  { deployProvControlPlaneEthEntry 6 }

deployProvControlPlaneEthCtmRetryWaitMultiplier OBJECT-TYPE
    SYNTAX      Unsigned32
    MAX-ACCESS  read-write
    STATUS      current
    DESCRIPTION   "Label Switched Path Edge Component' Initialization Retry Wait Multiplier"
    ::=  { deployProvControlPlaneEthEntry 7 }

deployProvControlPlaneEthCtmMaximumRetryWait OBJECT-TYPE
    SYNTAX      Unsigned32 
    UNITS       "s"
    MAX-ACCESS  read-write
    STATUS      current
    DESCRIPTION   "Label Switched Path Edge Component' Initialization Maximum Retry Wait"
    ::=  { deployProvControlPlaneEthEntry 8 }

deployProvControlPlaneEthCtmMaximumRetryNumber OBJECT-TYPE
    SYNTAX      Unsigned32
    MAX-ACCESS  read-write
    STATUS      current
    DESCRIPTION   "Label Switched Path Edge Component' Initialization Maximum Retry Number"
    ::=  { deployProvControlPlaneEthEntry 9 }

deployProvControlPlaneEthRaConfigFlag OBJECT-TYPE
    SYNTAX      Unsigned32
    MAX-ACCESS  read-write
    STATUS      current
    DESCRIPTION   "Resource Allocator Component' Configuration Bitfield"
    ::=  { deployProvControlPlaneEthEntry 10 }

deployProvControlPlaneEthRaTraceDetail OBJECT-TYPE
    SYNTAX      Unsigned32
    MAX-ACCESS  read-write
    STATUS      current
    DESCRIPTION   "Resource Allocator Component' Trace Detail"
    ::=  { deployProvControlPlaneEthEntry 11 }

deployProvControlPlaneEthRaAlarmActivationTime OBJECT-TYPE
    SYNTAX      Unsigned32 
    UNITS       "s"
    MAX-ACCESS  read-write
    STATUS      current
    DESCRIPTION   "Resource Allocator Component' Alarm Activation Time"
    ::=  { deployProvControlPlaneEthEntry 12 }

deployProvControlPlaneEthCmConfigFlag OBJECT-TYPE
    SYNTAX      Unsigned32
    MAX-ACCESS  read-write
    STATUS      current
    DESCRIPTION   "GMPLS Tunnel Manager Component' Configuration Bitfield"
    ::=  { deployProvControlPlaneEthEntry 13 }

deployProvControlPlaneEthCmTraceDetail OBJECT-TYPE
    SYNTAX      Unsigned32
    MAX-ACCESS  read-write
    STATUS      current
    DESCRIPTION   "GMPLS Tunnel Manager Component' Trace Detail"
    ::=  { deployProvControlPlaneEthEntry 14 }

deployProvControlPlaneEthCmAlarmActivationTime OBJECT-TYPE
    SYNTAX      Unsigned32 
    UNITS       "s"
    MAX-ACCESS  read-write
    STATUS      current
    DESCRIPTION   "GMPLS Tunnel Manager Component' Alarm Activation Time"
    ::=  { deployProvControlPlaneEthEntry 15 }

deployProvControlPlaneEthCmFisFrsTimeout OBJECT-TYPE
    SYNTAX      Unsigned32 
    UNITS       "s"
    MAX-ACCESS  read-write
    STATUS      current
    DESCRIPTION   "GMPLS Tunnel Manager Component' FIS-FRS Timeout"
    ::=  { deployProvControlPlaneEthEntry 16 }

deployProvControlPlaneEthCmCrankBackTimeout OBJECT-TYPE
    SYNTAX      Unsigned32 
    UNITS       "s"
    MAX-ACCESS  read-write
    STATUS      current
    DESCRIPTION   "GMPLS Tunnel Manager Component' Crank-Back Timeout"
    ::=  { deployProvControlPlaneEthEntry 17 }

deployProvControlPlaneEthCdbConfigFlag OBJECT-TYPE
    SYNTAX      Unsigned32
    MAX-ACCESS  read-write
    STATUS      current
    DESCRIPTION   "Label Swithed Path Database Component Configuration Bitfield"
    ::=  { deployProvControlPlaneEthEntry 18 }

deployProvControlPlaneEthCdbDetail OBJECT-TYPE
    SYNTAX      Unsigned32
    MAX-ACCESS  read-write
    STATUS      current
    DESCRIPTION   "Label Swithed Path Database Component Trace Detail"
    ::=  { deployProvControlPlaneEthEntry 19 }

deployProvControlPlaneEthCdbMaxSize OBJECT-TYPE
    SYNTAX      Unsigned32
    MAX-ACCESS  read-write
    STATUS      current
    DESCRIPTION   "Label Swithed Path Database Component Maximum Size; 0 implies no limit"
    ::=  { deployProvControlPlaneEthEntry 20 }

deployProvControlPlaneEthRsvpMaxExpRestartTime OBJECT-TYPE
    SYNTAX      Counter64String 
    UNITS       "ms"
    MAX-ACCESS  read-write
    STATUS      current
    DESCRIPTION   "Maximum Expected Resource Reservation Protocol Component' Restart Time"
    ::=  { deployProvControlPlaneEthEntry 21 }

deployProvControlPlaneEthRsvpMaxExpRecoveryTime OBJECT-TYPE
    SYNTAX      Unsigned32 
    UNITS       "ms"
    MAX-ACCESS  read-write
    STATUS      current
    DESCRIPTION   "Maximum Expected Resource Reservation Protocol Component' Recovery Time"
    ::=  { deployProvControlPlaneEthEntry 22 }

deployProvControlPlaneEthRsvpConfigFlag OBJECT-TYPE
    SYNTAX      Unsigned32
    MAX-ACCESS  read-write
    STATUS      current
    DESCRIPTION   "Resource Reservation Protocol Component' Configuration Bitfield"
    ::=  { deployProvControlPlaneEthEntry 23 }

deployProvControlPlaneEthTedbConfigFlag OBJECT-TYPE
    SYNTAX      Unsigned32
    MAX-ACCESS  read-write
    STATUS      current
    DESCRIPTION   "Traffic Engineering Component' Configuration Bitfield"
    ::=  { deployProvControlPlaneEthEntry 24 }

deployProvControlPlaneEthTedbTraceDetail OBJECT-TYPE
    SYNTAX      Unsigned32
    MAX-ACCESS  read-write
    STATUS      current
    DESCRIPTION   "Traffic Engineering Component' Trace Detail"
    ::=  { deployProvControlPlaneEthEntry 25 }

deployProvControlPlaneEthTedbMaxSize OBJECT-TYPE
    SYNTAX      Unsigned32
    MAX-ACCESS  read-write
    STATUS      current
    DESCRIPTION   "Traffic Engineering Component' Maximum Size"
    ::=  { deployProvControlPlaneEthEntry 26 }

deployProvControlPlaneEthTedbRouterId OBJECT-TYPE
    SYNTAX      IpAddress
    MAX-ACCESS  read-write
    STATUS      current
    DESCRIPTION   "Traffic Engineering Component' Router ID"
    ::=  { deployProvControlPlaneEthEntry 27 }

deployProvControlPlaneEthTedbMinAdvertWait OBJECT-TYPE
    SYNTAX      Unsigned32 
    UNITS       "s"
    MAX-ACCESS  read-write
    STATUS      current
    DESCRIPTION   "Traffic Engineering Component' Minimum Advertisement Wait"
    ::=  { deployProvControlPlaneEthEntry 28 }

deployProvControlPlaneEthNaasConfigFlag OBJECT-TYPE
    SYNTAX      Unsigned32
    MAX-ACCESS  read-write
    STATUS      current
    DESCRIPTION   "Node Attribute Advertising Service Database Component' Configuration Bitfield"
    ::=  { deployProvControlPlaneEthEntry 29 }

deployProvControlPlaneEthNaasTraceDetail OBJECT-TYPE
    SYNTAX      Unsigned32
    MAX-ACCESS  read-write
    STATUS      current
    DESCRIPTION   "Node Attribute Advertising Service Database Component' Trace Detail"
    ::=  { deployProvControlPlaneEthEntry 30 }

deployProvControlPlaneEthNaasMaxSize OBJECT-TYPE
    SYNTAX      Unsigned32
    MAX-ACCESS  read-write
    STATUS      current
    DESCRIPTION   "Node Attribute Advertising Service Database Component' Maximum Size"
    ::=  { deployProvControlPlaneEthEntry 31 }

deployProvControlPlaneEthNaasAdvertWait OBJECT-TYPE
    SYNTAX      Unsigned32 
    UNITS       "s"
    MAX-ACCESS  read-write
    STATUS      current
    DESCRIPTION   "Node Attribute Advertising Service Database Component' Advertisement Wait"
    ::=  { deployProvControlPlaneEthEntry 32 }

deployProvControlPlaneEthPcConfigFlag OBJECT-TYPE
    SYNTAX      Unsigned32
    MAX-ACCESS  read-write
    STATUS      current
    DESCRIPTION   "Path Computation Component' Configuration Bitfield"
    ::=  { deployProvControlPlaneEthEntry 33 }

deployProvControlPlaneEthPcTraceDetail OBJECT-TYPE
    SYNTAX      Unsigned32
    MAX-ACCESS  read-write
    STATUS      current
    DESCRIPTION   "Path Computation Component' Trace Detail"
    ::=  { deployProvControlPlaneEthEntry 34 }

deployProvControlPlaneEthCdConfigFlag OBJECT-TYPE
    SYNTAX      Unsigned32
    MAX-ACCESS  read-write
    STATUS      current
    DESCRIPTION   "Configuration Data Component' Configuration Bitfield"
    ::=  { deployProvControlPlaneEthEntry 35 }

deployProvControlPlaneEthCdTraceDetail OBJECT-TYPE
    SYNTAX      Unsigned32
    MAX-ACCESS  read-write
    STATUS      current
    DESCRIPTION   "Configuration Data Component' Trace Detail"
    ::=  { deployProvControlPlaneEthEntry 36 }

deployProvControlPlaneEthCdResyncTimeout OBJECT-TYPE
    SYNTAX      Unsigned32
    MAX-ACCESS  read-write
    STATUS      current
    DESCRIPTION   "Configuration Data Component' Resync Timeout"
    ::=  { deployProvControlPlaneEthEntry 37 }

deployProvControlPlaneEthRmConfigFlag OBJECT-TYPE
    SYNTAX      Unsigned32
    MAX-ACCESS  read-write
    STATUS      current
    DESCRIPTION   "Resource Management Component' Configuration Bitfield"
    ::=  { deployProvControlPlaneEthEntry 38 }

deployProvControlPlaneEthRmTraceDetail OBJECT-TYPE
    SYNTAX      Unsigned32
    MAX-ACCESS  read-write
    STATUS      current
    DESCRIPTION   "Resource Management Component' Trace Detail"
    ::=  { deployProvControlPlaneEthEntry 39 }

deployProvControlPlaneEthRmTraceTarget OBJECT-TYPE
    SYNTAX      Unsigned32
    MAX-ACCESS  read-write
    STATUS      current
    DESCRIPTION   "Resource Management Component' Trace Target"
    ::=  { deployProvControlPlaneEthEntry 40 }

deployProvControlPlaneEthCapTable OBJECT-TYPE
    SYNTAX      SEQUENCE OF DeployProvControlPlaneEthCapEntry
    MAX-ACCESS  not-accessible
    STATUS      current
    DESCRIPTION   ""
    ::=  { controlPlaneDeployProv 62  }

deployProvControlPlaneEthCapEntry OBJECT-TYPE
    SYNTAX      DeployProvControlPlaneEthCapEntry
    MAX-ACCESS  not-accessible
    STATUS      current
    DESCRIPTION   ""
    INDEX       { controlPlaneEthEntityIndex }
    ::=  { deployProvControlPlaneEthCapTable 1 }

DeployProvControlPlaneEthCapEntry ::=  SEQUENCE
  { deployProvControlPlaneEthCapRowStatus FspR7RowStatusCaps,
    deployProvControlPlaneEthCapCtmConfigFlag FspR7Unsigned32Caps,
    deployProvControlPlaneEthCapCtmTraceDetail FspR7Unsigned32Caps,
    deployProvControlPlaneEthCapCtmSetupTimeout FspR7Unsigned32Caps,
    deployProvControlPlaneEthCapCtmShutdownTimeout FspR7Unsigned32Caps,
    deployProvControlPlaneEthCapCtmRetryWait FspR7Unsigned32Caps,
    deployProvControlPlaneEthCapCtmRetryWaitMultiplier FspR7Unsigned32Caps,
    deployProvControlPlaneEthCapCtmMaximumRetryWait FspR7Unsigned32Caps,
    deployProvControlPlaneEthCapCtmMaximumRetryNumber FspR7Unsigned32Caps,
    deployProvControlPlaneEthCapRaConfigFlag FspR7Unsigned32Caps,
    deployProvControlPlaneEthCapRaTraceDetail FspR7Unsigned32Caps,
    deployProvControlPlaneEthCapRaAlarmActivationTime FspR7Unsigned32Caps,
    deployProvControlPlaneEthCapCmConfigFlag FspR7Unsigned32Caps,
    deployProvControlPlaneEthCapCmTraceDetail FspR7Unsigned32Caps,
    deployProvControlPlaneEthCapCmAlarmActivationTime FspR7Unsigned32Caps,
    deployProvControlPlaneEthCapCmFisFrsTimeout FspR7Unsigned32Caps,
    deployProvControlPlaneEthCapCmCrankBackTimeout FspR7Unsigned32Caps,
    deployProvControlPlaneEthCapCdbConfigFlag FspR7Unsigned32Caps,
    deployProvControlPlaneEthCapCdbDetail FspR7Unsigned32Caps,
    deployProvControlPlaneEthCapCdbMaxSize FspR7Unsigned32Caps,
    deployProvControlPlaneEthCapRsvpMaxExpRestartTime Counter64StringCaps,
    deployProvControlPlaneEthCapRsvpMaxExpRecoveryTime FspR7Unsigned32Caps,
    deployProvControlPlaneEthCapRsvpConfigFlag FspR7Unsigned32Caps,
    deployProvControlPlaneEthCapTedbConfigFlag FspR7Unsigned32Caps,
    deployProvControlPlaneEthCapTedbTraceDetail FspR7Unsigned32Caps,
    deployProvControlPlaneEthCapTedbMaxSize FspR7Unsigned32Caps,
    deployProvControlPlaneEthCapTedbRouterId FspR7YesNo,
    deployProvControlPlaneEthCapTedbMinAdvertWait FspR7Unsigned32Caps,
    deployProvControlPlaneEthCapNaasConfigFlag FspR7Unsigned32Caps,
    deployProvControlPlaneEthCapNaasTraceDetail FspR7Unsigned32Caps,
    deployProvControlPlaneEthCapNaasMaxSize FspR7Unsigned32Caps,
    deployProvControlPlaneEthCapNaasAdvertWait FspR7Unsigned32Caps,
    deployProvControlPlaneEthCapPcConfigFlag FspR7Unsigned32Caps,
    deployProvControlPlaneEthCapPcTraceDetail FspR7Unsigned32Caps,
    deployProvControlPlaneEthCapCdConfigFlag FspR7Unsigned32Caps,
    deployProvControlPlaneEthCapCdTraceDetail FspR7Unsigned32Caps,
    deployProvControlPlaneEthCapCdResyncTimeout FspR7Unsigned32Caps,
    deployProvControlPlaneEthCapRmConfigFlag FspR7Unsigned32Caps,
    deployProvControlPlaneEthCapRmTraceDetail FspR7Unsigned32Caps,
    deployProvControlPlaneEthCapRmTraceTarget FspR7Unsigned32Caps }

deployProvControlPlaneEthCapRowStatus OBJECT-TYPE
    SYNTAX      FspR7RowStatusCaps
    MAX-ACCESS  read-only
    STATUS      current
    DESCRIPTION   ""
    ::=  { deployProvControlPlaneEthCapEntry 1 }

deployProvControlPlaneEthCapCtmConfigFlag OBJECT-TYPE
    SYNTAX      FspR7Unsigned32Caps
    MAX-ACCESS  read-only
    STATUS      current
    DESCRIPTION   "Label Switched Path Edge Component' Configuration Bitfield"
    ::=  { deployProvControlPlaneEthCapEntry 2 }

deployProvControlPlaneEthCapCtmTraceDetail OBJECT-TYPE
    SYNTAX      FspR7Unsigned32Caps
    MAX-ACCESS  read-only
    STATUS      current
    DESCRIPTION   "Label Switched Path Edge Component' Trace Detail"
    ::=  { deployProvControlPlaneEthCapEntry 3 }

deployProvControlPlaneEthCapCtmSetupTimeout OBJECT-TYPE
    SYNTAX      FspR7Unsigned32Caps
    UNITS       "s"
    MAX-ACCESS  read-only
    STATUS      current
    DESCRIPTION   "Label Switched Path Edge Component' Set-Up Timeout"
    ::=  { deployProvControlPlaneEthCapEntry 4 }

deployProvControlPlaneEthCapCtmShutdownTimeout OBJECT-TYPE
    SYNTAX      FspR7Unsigned32Caps
    UNITS       "s"
    MAX-ACCESS  read-only
    STATUS      current
    DESCRIPTION   "Label Switched Path Edge Component' Shut-Down Timeout"
    ::=  { deployProvControlPlaneEthCapEntry 5 }

deployProvControlPlaneEthCapCtmRetryWait OBJECT-TYPE
    SYNTAX      FspR7Unsigned32Caps
    UNITS       "s"
    MAX-ACCESS  read-only
    STATUS      current
    DESCRIPTION   "Label Switched Path Edge Component' Initialization Retry Wait"
    ::=  { deployProvControlPlaneEthCapEntry 6 }

deployProvControlPlaneEthCapCtmRetryWaitMultiplier OBJECT-TYPE
    SYNTAX      FspR7Unsigned32Caps
    MAX-ACCESS  read-only
    STATUS      current
    DESCRIPTION   "Label Switched Path Edge Component' Initialization Retry Wait Multiplier"
    ::=  { deployProvControlPlaneEthCapEntry 7 }

deployProvControlPlaneEthCapCtmMaximumRetryWait OBJECT-TYPE
    SYNTAX      FspR7Unsigned32Caps
    UNITS       "s"
    MAX-ACCESS  read-only
    STATUS      current
    DESCRIPTION   "Label Switched Path Edge Component' Initialization Maximum Retry Wait"
    ::=  { deployProvControlPlaneEthCapEntry 8 }

deployProvControlPlaneEthCapCtmMaximumRetryNumber OBJECT-TYPE
    SYNTAX      FspR7Unsigned32Caps
    MAX-ACCESS  read-only
    STATUS      current
    DESCRIPTION   "Label Switched Path Edge Component' Initialization Maximum Retry Number"
    ::=  { deployProvControlPlaneEthCapEntry 9 }

deployProvControlPlaneEthCapRaConfigFlag OBJECT-TYPE
    SYNTAX      FspR7Unsigned32Caps
    MAX-ACCESS  read-only
    STATUS      current
    DESCRIPTION   "Resource Allocator Component' Configuration Bitfield"
    ::=  { deployProvControlPlaneEthCapEntry 10 }

deployProvControlPlaneEthCapRaTraceDetail OBJECT-TYPE
    SYNTAX      FspR7Unsigned32Caps
    MAX-ACCESS  read-only
    STATUS      current
    DESCRIPTION   "Resource Allocator Component' Trace Detail"
    ::=  { deployProvControlPlaneEthCapEntry 11 }

deployProvControlPlaneEthCapRaAlarmActivationTime OBJECT-TYPE
    SYNTAX      FspR7Unsigned32Caps
    UNITS       "s"
    MAX-ACCESS  read-only
    STATUS      current
    DESCRIPTION   "Resource Allocator Component' Alarm Activation Time"
    ::=  { deployProvControlPlaneEthCapEntry 12 }

deployProvControlPlaneEthCapCmConfigFlag OBJECT-TYPE
    SYNTAX      FspR7Unsigned32Caps
    MAX-ACCESS  read-only
    STATUS      current
    DESCRIPTION   "GMPLS Tunnel Manager Component' Configuration Bitfield"
    ::=  { deployProvControlPlaneEthCapEntry 13 }

deployProvControlPlaneEthCapCmTraceDetail OBJECT-TYPE
    SYNTAX      FspR7Unsigned32Caps
    MAX-ACCESS  read-only
    STATUS      current
    DESCRIPTION   "GMPLS Tunnel Manager Component' Trace Detail"
    ::=  { deployProvControlPlaneEthCapEntry 14 }

deployProvControlPlaneEthCapCmAlarmActivationTime OBJECT-TYPE
    SYNTAX      FspR7Unsigned32Caps
    UNITS       "s"
    MAX-ACCESS  read-only
    STATUS      current
    DESCRIPTION   "GMPLS Tunnel Manager Component' Alarm Activation Time"
    ::=  { deployProvControlPlaneEthCapEntry 15 }

deployProvControlPlaneEthCapCmFisFrsTimeout OBJECT-TYPE
    SYNTAX      FspR7Unsigned32Caps
    UNITS       "s"
    MAX-ACCESS  read-only
    STATUS      current
    DESCRIPTION   "GMPLS Tunnel Manager Component' FIS-FRS Timeout"
    ::=  { deployProvControlPlaneEthCapEntry 16 }

deployProvControlPlaneEthCapCmCrankBackTimeout OBJECT-TYPE
    SYNTAX      FspR7Unsigned32Caps
    UNITS       "s"
    MAX-ACCESS  read-only
    STATUS      current
    DESCRIPTION   "GMPLS Tunnel Manager Component' Crank-Back Timeout"
    ::=  { deployProvControlPlaneEthCapEntry 17 }

deployProvControlPlaneEthCapCdbConfigFlag OBJECT-TYPE
    SYNTAX      FspR7Unsigned32Caps
    MAX-ACCESS  read-only
    STATUS      current
    DESCRIPTION   "Label Swithed Path Database Component Configuration Bitfield"
    ::=  { deployProvControlPlaneEthCapEntry 18 }

deployProvControlPlaneEthCapCdbDetail OBJECT-TYPE
    SYNTAX      FspR7Unsigned32Caps
    MAX-ACCESS  read-only
    STATUS      current
    DESCRIPTION   "Label Swithed Path Database Component Trace Detail"
    ::=  { deployProvControlPlaneEthCapEntry 19 }

deployProvControlPlaneEthCapCdbMaxSize OBJECT-TYPE
    SYNTAX      FspR7Unsigned32Caps
    MAX-ACCESS  read-only
    STATUS      current
    DESCRIPTION   "Label Swithed Path Database Component Maximum Size; 0 implies no limit"
    ::=  { deployProvControlPlaneEthCapEntry 20 }

deployProvControlPlaneEthCapRsvpMaxExpRestartTime OBJECT-TYPE
    SYNTAX      Counter64StringCaps
    UNITS       "ms"
    MAX-ACCESS  read-only
    STATUS      current
    DESCRIPTION   "Maximum Expected Resource Reservation Protocol Component' Restart Time"
    ::=  { deployProvControlPlaneEthCapEntry 21 }

deployProvControlPlaneEthCapRsvpMaxExpRecoveryTime OBJECT-TYPE
    SYNTAX      FspR7Unsigned32Caps
    UNITS       "ms"
    MAX-ACCESS  read-only
    STATUS      current
    DESCRIPTION   "Maximum Expected Resource Reservation Protocol Component' Recovery Time"
    ::=  { deployProvControlPlaneEthCapEntry 22 }

deployProvControlPlaneEthCapRsvpConfigFlag OBJECT-TYPE
    SYNTAX      FspR7Unsigned32Caps
    MAX-ACCESS  read-only
    STATUS      current
    DESCRIPTION   "Resource Reservation Protocol Component' Configuration Bitfield"
    ::=  { deployProvControlPlaneEthCapEntry 23 }

deployProvControlPlaneEthCapTedbConfigFlag OBJECT-TYPE
    SYNTAX      FspR7Unsigned32Caps
    MAX-ACCESS  read-only
    STATUS      current
    DESCRIPTION   "Traffic Engineering Component' Configuration Bitfield"
    ::=  { deployProvControlPlaneEthCapEntry 24 }

deployProvControlPlaneEthCapTedbTraceDetail OBJECT-TYPE
    SYNTAX      FspR7Unsigned32Caps
    MAX-ACCESS  read-only
    STATUS      current
    DESCRIPTION   "Traffic Engineering Component' Trace Detail"
    ::=  { deployProvControlPlaneEthCapEntry 25 }

deployProvControlPlaneEthCapTedbMaxSize OBJECT-TYPE
    SYNTAX      FspR7Unsigned32Caps
    MAX-ACCESS  read-only
    STATUS      current
    DESCRIPTION   "Traffic Engineering Component' Maximum Size"
    ::=  { deployProvControlPlaneEthCapEntry 26 }

deployProvControlPlaneEthCapTedbRouterId OBJECT-TYPE
    SYNTAX      FspR7YesNo
    MAX-ACCESS  read-only
    STATUS      current
    DESCRIPTION   "Traffic Engineering Component' Router ID"
    ::=  { deployProvControlPlaneEthCapEntry 27 }

deployProvControlPlaneEthCapTedbMinAdvertWait OBJECT-TYPE
    SYNTAX      FspR7Unsigned32Caps
    UNITS       "s"
    MAX-ACCESS  read-only
    STATUS      current
    DESCRIPTION   "Traffic Engineering Component' Minimum Advertisement Wait"
    ::=  { deployProvControlPlaneEthCapEntry 28 }

deployProvControlPlaneEthCapNaasConfigFlag OBJECT-TYPE
    SYNTAX      FspR7Unsigned32Caps
    MAX-ACCESS  read-only
    STATUS      current
    DESCRIPTION   "Node Attribute Advertising Service Database Component' Configuration Bitfield"
    ::=  { deployProvControlPlaneEthCapEntry 29 }

deployProvControlPlaneEthCapNaasTraceDetail OBJECT-TYPE
    SYNTAX      FspR7Unsigned32Caps
    MAX-ACCESS  read-only
    STATUS      current
    DESCRIPTION   "Node Attribute Advertising Service Database Component' Trace Detail"
    ::=  { deployProvControlPlaneEthCapEntry 30 }

deployProvControlPlaneEthCapNaasMaxSize OBJECT-TYPE
    SYNTAX      FspR7Unsigned32Caps
    MAX-ACCESS  read-only
    STATUS      current
    DESCRIPTION   "Node Attribute Advertising Service Database Component' Maximum Size"
    ::=  { deployProvControlPlaneEthCapEntry 31 }

deployProvControlPlaneEthCapNaasAdvertWait OBJECT-TYPE
    SYNTAX      FspR7Unsigned32Caps
    UNITS       "s"
    MAX-ACCESS  read-only
    STATUS      current
    DESCRIPTION   "Node Attribute Advertising Service Database Component' Advertisement Wait"
    ::=  { deployProvControlPlaneEthCapEntry 32 }

deployProvControlPlaneEthCapPcConfigFlag OBJECT-TYPE
    SYNTAX      FspR7Unsigned32Caps
    MAX-ACCESS  read-only
    STATUS      current
    DESCRIPTION   "Path Computation Component' Configuration Bitfield"
    ::=  { deployProvControlPlaneEthCapEntry 33 }

deployProvControlPlaneEthCapPcTraceDetail OBJECT-TYPE
    SYNTAX      FspR7Unsigned32Caps
    MAX-ACCESS  read-only
    STATUS      current
    DESCRIPTION   "Path Computation Component' Trace Detail"
    ::=  { deployProvControlPlaneEthCapEntry 34 }

deployProvControlPlaneEthCapCdConfigFlag OBJECT-TYPE
    SYNTAX      FspR7Unsigned32Caps
    MAX-ACCESS  read-only
    STATUS      current
    DESCRIPTION   "Configuration Data Component' Configuration Bitfield"
    ::=  { deployProvControlPlaneEthCapEntry 35 }

deployProvControlPlaneEthCapCdTraceDetail OBJECT-TYPE
    SYNTAX      FspR7Unsigned32Caps
    MAX-ACCESS  read-only
    STATUS      current
    DESCRIPTION   "Configuration Data Component' Trace Detail"
    ::=  { deployProvControlPlaneEthCapEntry 36 }

deployProvControlPlaneEthCapCdResyncTimeout OBJECT-TYPE
    SYNTAX      FspR7Unsigned32Caps
    MAX-ACCESS  read-only
    STATUS      current
    DESCRIPTION   "Configuration Data Component' Resync Timeout"
    ::=  { deployProvControlPlaneEthCapEntry 37 }

deployProvControlPlaneEthCapRmConfigFlag OBJECT-TYPE
    SYNTAX      FspR7Unsigned32Caps
    MAX-ACCESS  read-only
    STATUS      current
    DESCRIPTION   "Resource Management Component' Configuration Bitfield"
    ::=  { deployProvControlPlaneEthCapEntry 38 }

deployProvControlPlaneEthCapRmTraceDetail OBJECT-TYPE
    SYNTAX      FspR7Unsigned32Caps
    MAX-ACCESS  read-only
    STATUS      current
    DESCRIPTION   "Resource Management Component' Trace Detail"
    ::=  { deployProvControlPlaneEthCapEntry 39 }

deployProvControlPlaneEthCapRmTraceTarget OBJECT-TYPE
    SYNTAX      FspR7Unsigned32Caps
    MAX-ACCESS  read-only
    STATUS      current
    DESCRIPTION   "Resource Management Component' Trace Target"
    ::=  { deployProvControlPlaneEthCapEntry 40 }

deployProvControlPlaneEthDefaultsTable  OBJECT-TYPE
    SYNTAX      SEQUENCE OF DeployProvControlPlaneEthDefaultsEntry
    MAX-ACCESS  not-accessible
    STATUS      current
    DESCRIPTION   ""
    ::=  { controlPlaneDeployProv 63  }

deployProvControlPlaneEthDefaultsEntry OBJECT-TYPE
    SYNTAX      DeployProvControlPlaneEthDefaultsEntry
    MAX-ACCESS  not-accessible
    STATUS      current
    DESCRIPTION   ""
    INDEX       { controlPlaneEthEntityIndex }
    ::=  { deployProvControlPlaneEthDefaultsTable 1 }

DeployProvControlPlaneEthDefaultsEntry ::=  SEQUENCE
  { deployProvControlPlaneEthDefaultsRowStatus RowStatus,
    deployProvControlPlaneEthDefaultsCtmConfigFlag Unsigned32,
    deployProvControlPlaneEthDefaultsCtmTraceDetail Unsigned32,
    deployProvControlPlaneEthDefaultsCtmSetupTimeout Unsigned32,
    deployProvControlPlaneEthDefaultsCtmShutdownTimeout Unsigned32,
    deployProvControlPlaneEthDefaultsCtmRetryWait Unsigned32,
    deployProvControlPlaneEthDefaultsCtmRetryWaitMultiplier Unsigned32,
    deployProvControlPlaneEthDefaultsCtmMaximumRetryWait Unsigned32,
    deployProvControlPlaneEthDefaultsCtmMaximumRetryNumber Unsigned32,
    deployProvControlPlaneEthDefaultsRaConfigFlag Unsigned32,
    deployProvControlPlaneEthDefaultsRaTraceDetail Unsigned32,
    deployProvControlPlaneEthDefaultsRaAlarmActivationTime Unsigned32,
    deployProvControlPlaneEthDefaultsCmConfigFlag Unsigned32,
    deployProvControlPlaneEthDefaultsCmTraceDetail Unsigned32,
    deployProvControlPlaneEthDefaultsCmAlarmActivationTime Unsigned32,
    deployProvControlPlaneEthDefaultsCmFisFrsTimeout Unsigned32,
    deployProvControlPlaneEthDefaultsCmCrankBackTimeout Unsigned32,
    deployProvControlPlaneEthDefaultsCdbConfigFlag Unsigned32,
    deployProvControlPlaneEthDefaultsCdbDetail Unsigned32,
    deployProvControlPlaneEthDefaultsCdbMaxSize Unsigned32,
    deployProvControlPlaneEthDefaultsRsvpMaxExpRestartTime Counter64String,
    deployProvControlPlaneEthDefaultsRsvpMaxExpRecoveryTime Unsigned32,
    deployProvControlPlaneEthDefaultsRsvpConfigFlag Unsigned32,
    deployProvControlPlaneEthDefaultsTedbConfigFlag Unsigned32,
    deployProvControlPlaneEthDefaultsTedbTraceDetail Unsigned32,
    deployProvControlPlaneEthDefaultsTedbMaxSize Unsigned32,
    deployProvControlPlaneEthDefaultsTedbRouterId IpAddress,
    deployProvControlPlaneEthDefaultsTedbMinAdvertWait Unsigned32,
    deployProvControlPlaneEthDefaultsNaasConfigFlag Unsigned32,
    deployProvControlPlaneEthDefaultsNaasTraceDetail Unsigned32,
    deployProvControlPlaneEthDefaultsNaasMaxSize Unsigned32,
    deployProvControlPlaneEthDefaultsNaasAdvertWait Unsigned32,
    deployProvControlPlaneEthDefaultsPcConfigFlag Unsigned32,
    deployProvControlPlaneEthDefaultsPcTraceDetail Unsigned32,
    deployProvControlPlaneEthDefaultsCdConfigFlag Unsigned32,
    deployProvControlPlaneEthDefaultsCdTraceDetail Unsigned32,
    deployProvControlPlaneEthDefaultsCdResyncTimeout Unsigned32,
    deployProvControlPlaneEthDefaultsRmConfigFlag Unsigned32,
    deployProvControlPlaneEthDefaultsRmTraceDetail Unsigned32,
    deployProvControlPlaneEthDefaultsRmTraceTarget Unsigned32 }

deployProvControlPlaneEthDefaultsRowStatus OBJECT-TYPE
    SYNTAX      RowStatus
    MAX-ACCESS  read-only
    STATUS      current
    DESCRIPTION   ""
    ::=  { deployProvControlPlaneEthDefaultsEntry 1 }

deployProvControlPlaneEthDefaultsCtmConfigFlag OBJECT-TYPE
    SYNTAX      Unsigned32
    MAX-ACCESS  read-only
    STATUS      current
    DESCRIPTION   "Label Switched Path Edge Component' Configuration Bitfield"
    ::=  { deployProvControlPlaneEthDefaultsEntry 2 }

deployProvControlPlaneEthDefaultsCtmTraceDetail OBJECT-TYPE
    SYNTAX      Unsigned32
    MAX-ACCESS  read-only
    STATUS      current
    DESCRIPTION   "Label Switched Path Edge Component' Trace Detail"
    ::=  { deployProvControlPlaneEthDefaultsEntry 3 }

deployProvControlPlaneEthDefaultsCtmSetupTimeout OBJECT-TYPE
    SYNTAX      Unsigned32 
    UNITS       "s"
    MAX-ACCESS  read-only
    STATUS      current
    DESCRIPTION   "Label Switched Path Edge Component' Set-Up Timeout"
    ::=  { deployProvControlPlaneEthDefaultsEntry 4 }

deployProvControlPlaneEthDefaultsCtmShutdownTimeout OBJECT-TYPE
    SYNTAX      Unsigned32 
    UNITS       "s"
    MAX-ACCESS  read-only
    STATUS      current
    DESCRIPTION   "Label Switched Path Edge Component' Shut-Down Timeout"
    ::=  { deployProvControlPlaneEthDefaultsEntry 5 }

deployProvControlPlaneEthDefaultsCtmRetryWait OBJECT-TYPE
    SYNTAX      Unsigned32 
    UNITS       "s"
    MAX-ACCESS  read-only
    STATUS      current
    DESCRIPTION   "Label Switched Path Edge Component' Initialization Retry Wait"
    ::=  { deployProvControlPlaneEthDefaultsEntry 6 }

deployProvControlPlaneEthDefaultsCtmRetryWaitMultiplier OBJECT-TYPE
    SYNTAX      Unsigned32
    MAX-ACCESS  read-only
    STATUS      current
    DESCRIPTION   "Label Switched Path Edge Component' Initialization Retry Wait Multiplier"
    ::=  { deployProvControlPlaneEthDefaultsEntry 7 }

deployProvControlPlaneEthDefaultsCtmMaximumRetryWait OBJECT-TYPE
    SYNTAX      Unsigned32 
    UNITS       "s"
    MAX-ACCESS  read-only
    STATUS      current
    DESCRIPTION   "Label Switched Path Edge Component' Initialization Maximum Retry Wait"
    ::=  { deployProvControlPlaneEthDefaultsEntry 8 }

deployProvControlPlaneEthDefaultsCtmMaximumRetryNumber OBJECT-TYPE
    SYNTAX      Unsigned32
    MAX-ACCESS  read-only
    STATUS      current
    DESCRIPTION   "Label Switched Path Edge Component' Initialization Maximum Retry Number"
    ::=  { deployProvControlPlaneEthDefaultsEntry 9 }

deployProvControlPlaneEthDefaultsRaConfigFlag OBJECT-TYPE
    SYNTAX      Unsigned32
    MAX-ACCESS  read-only
    STATUS      current
    DESCRIPTION   "Resource Allocator Component' Configuration Bitfield"
    ::=  { deployProvControlPlaneEthDefaultsEntry 10 }

deployProvControlPlaneEthDefaultsRaTraceDetail OBJECT-TYPE
    SYNTAX      Unsigned32
    MAX-ACCESS  read-only
    STATUS      current
    DESCRIPTION   "Resource Allocator Component' Trace Detail"
    ::=  { deployProvControlPlaneEthDefaultsEntry 11 }

deployProvControlPlaneEthDefaultsRaAlarmActivationTime OBJECT-TYPE
    SYNTAX      Unsigned32 
    UNITS       "s"
    MAX-ACCESS  read-only
    STATUS      current
    DESCRIPTION   "Resource Allocator Component' Alarm Activation Time"
    ::=  { deployProvControlPlaneEthDefaultsEntry 12 }

deployProvControlPlaneEthDefaultsCmConfigFlag OBJECT-TYPE
    SYNTAX      Unsigned32
    MAX-ACCESS  read-only
    STATUS      current
    DESCRIPTION   "GMPLS Tunnel Manager Component' Configuration Bitfield"
    ::=  { deployProvControlPlaneEthDefaultsEntry 13 }

deployProvControlPlaneEthDefaultsCmTraceDetail OBJECT-TYPE
    SYNTAX      Unsigned32
    MAX-ACCESS  read-only
    STATUS      current
    DESCRIPTION   "GMPLS Tunnel Manager Component' Trace Detail"
    ::=  { deployProvControlPlaneEthDefaultsEntry 14 }

deployProvControlPlaneEthDefaultsCmAlarmActivationTime OBJECT-TYPE
    SYNTAX      Unsigned32 
    UNITS       "s"
    MAX-ACCESS  read-only
    STATUS      current
    DESCRIPTION   "GMPLS Tunnel Manager Component' Alarm Activation Time"
    ::=  { deployProvControlPlaneEthDefaultsEntry 15 }

deployProvControlPlaneEthDefaultsCmFisFrsTimeout OBJECT-TYPE
    SYNTAX      Unsigned32 
    UNITS       "s"
    MAX-ACCESS  read-only
    STATUS      current
    DESCRIPTION   "GMPLS Tunnel Manager Component' FIS-FRS Timeout"
    ::=  { deployProvControlPlaneEthDefaultsEntry 16 }

deployProvControlPlaneEthDefaultsCmCrankBackTimeout OBJECT-TYPE
    SYNTAX      Unsigned32 
    UNITS       "s"
    MAX-ACCESS  read-only
    STATUS      current
    DESCRIPTION   "GMPLS Tunnel Manager Component' Crank-Back Timeout"
    ::=  { deployProvControlPlaneEthDefaultsEntry 17 }

deployProvControlPlaneEthDefaultsCdbConfigFlag OBJECT-TYPE
    SYNTAX      Unsigned32
    MAX-ACCESS  read-only
    STATUS      current
    DESCRIPTION   "Label Swithed Path Database Component Configuration Bitfield"
    ::=  { deployProvControlPlaneEthDefaultsEntry 18 }

deployProvControlPlaneEthDefaultsCdbDetail OBJECT-TYPE
    SYNTAX      Unsigned32
    MAX-ACCESS  read-only
    STATUS      current
    DESCRIPTION   "Label Swithed Path Database Component Trace Detail"
    ::=  { deployProvControlPlaneEthDefaultsEntry 19 }

deployProvControlPlaneEthDefaultsCdbMaxSize OBJECT-TYPE
    SYNTAX      Unsigned32
    MAX-ACCESS  read-only
    STATUS      current
    DESCRIPTION   "Label Swithed Path Database Component Maximum Size; 0 implies no limit"
    ::=  { deployProvControlPlaneEthDefaultsEntry 20 }

deployProvControlPlaneEthDefaultsRsvpMaxExpRestartTime OBJECT-TYPE
    SYNTAX      Counter64String 
    UNITS       "ms"
    MAX-ACCESS  read-only
    STATUS      current
    DESCRIPTION   "Maximum Expected Resource Reservation Protocol Component' Restart Time"
    ::=  { deployProvControlPlaneEthDefaultsEntry 21 }

deployProvControlPlaneEthDefaultsRsvpMaxExpRecoveryTime OBJECT-TYPE
    SYNTAX      Unsigned32 
    UNITS       "ms"
    MAX-ACCESS  read-only
    STATUS      current
    DESCRIPTION   "Maximum Expected Resource Reservation Protocol Component' Recovery Time"
    ::=  { deployProvControlPlaneEthDefaultsEntry 22 }

deployProvControlPlaneEthDefaultsRsvpConfigFlag OBJECT-TYPE
    SYNTAX      Unsigned32
    MAX-ACCESS  read-only
    STATUS      current
    DESCRIPTION   "Resource Reservation Protocol Component' Configuration Bitfield"
    ::=  { deployProvControlPlaneEthDefaultsEntry 23 }

deployProvControlPlaneEthDefaultsTedbConfigFlag OBJECT-TYPE
    SYNTAX      Unsigned32
    MAX-ACCESS  read-only
    STATUS      current
    DESCRIPTION   "Traffic Engineering Component' Configuration Bitfield"
    ::=  { deployProvControlPlaneEthDefaultsEntry 24 }

deployProvControlPlaneEthDefaultsTedbTraceDetail OBJECT-TYPE
    SYNTAX      Unsigned32
    MAX-ACCESS  read-only
    STATUS      current
    DESCRIPTION   "Traffic Engineering Component' Trace Detail"
    ::=  { deployProvControlPlaneEthDefaultsEntry 25 }

deployProvControlPlaneEthDefaultsTedbMaxSize OBJECT-TYPE
    SYNTAX      Unsigned32
    MAX-ACCESS  read-only
    STATUS      current
    DESCRIPTION   "Traffic Engineering Component' Maximum Size"
    ::=  { deployProvControlPlaneEthDefaultsEntry 26 }

deployProvControlPlaneEthDefaultsTedbRouterId OBJECT-TYPE
    SYNTAX      IpAddress
    MAX-ACCESS  read-only
    STATUS      current
    DESCRIPTION   "Traffic Engineering Component' Router ID"
    ::=  { deployProvControlPlaneEthDefaultsEntry 27 }

deployProvControlPlaneEthDefaultsTedbMinAdvertWait OBJECT-TYPE
    SYNTAX      Unsigned32 
    UNITS       "s"
    MAX-ACCESS  read-only
    STATUS      current
    DESCRIPTION   "Traffic Engineering Component' Minimum Advertisement Wait"
    ::=  { deployProvControlPlaneEthDefaultsEntry 28 }

deployProvControlPlaneEthDefaultsNaasConfigFlag OBJECT-TYPE
    SYNTAX      Unsigned32
    MAX-ACCESS  read-only
    STATUS      current
    DESCRIPTION   "Node Attribute Advertising Service Database Component' Configuration Bitfield"
    ::=  { deployProvControlPlaneEthDefaultsEntry 29 }

deployProvControlPlaneEthDefaultsNaasTraceDetail OBJECT-TYPE
    SYNTAX      Unsigned32
    MAX-ACCESS  read-only
    STATUS      current
    DESCRIPTION   "Node Attribute Advertising Service Database Component' Trace Detail"
    ::=  { deployProvControlPlaneEthDefaultsEntry 30 }

deployProvControlPlaneEthDefaultsNaasMaxSize OBJECT-TYPE
    SYNTAX      Unsigned32
    MAX-ACCESS  read-only
    STATUS      current
    DESCRIPTION   "Node Attribute Advertising Service Database Component' Maximum Size"
    ::=  { deployProvControlPlaneEthDefaultsEntry 31 }

deployProvControlPlaneEthDefaultsNaasAdvertWait OBJECT-TYPE
    SYNTAX      Unsigned32 
    UNITS       "s"
    MAX-ACCESS  read-only
    STATUS      current
    DESCRIPTION   "Node Attribute Advertising Service Database Component' Advertisement Wait"
    ::=  { deployProvControlPlaneEthDefaultsEntry 32 }

deployProvControlPlaneEthDefaultsPcConfigFlag OBJECT-TYPE
    SYNTAX      Unsigned32
    MAX-ACCESS  read-only
    STATUS      current
    DESCRIPTION   "Path Computation Component' Configuration Bitfield"
    ::=  { deployProvControlPlaneEthDefaultsEntry 33 }

deployProvControlPlaneEthDefaultsPcTraceDetail OBJECT-TYPE
    SYNTAX      Unsigned32
    MAX-ACCESS  read-only
    STATUS      current
    DESCRIPTION   "Path Computation Component' Trace Detail"
    ::=  { deployProvControlPlaneEthDefaultsEntry 34 }

deployProvControlPlaneEthDefaultsCdConfigFlag OBJECT-TYPE
    SYNTAX      Unsigned32
    MAX-ACCESS  read-only
    STATUS      current
    DESCRIPTION   "Configuration Data Component' Configuration Bitfield"
    ::=  { deployProvControlPlaneEthDefaultsEntry 35 }

deployProvControlPlaneEthDefaultsCdTraceDetail OBJECT-TYPE
    SYNTAX      Unsigned32
    MAX-ACCESS  read-only
    STATUS      current
    DESCRIPTION   "Configuration Data Component' Trace Detail"
    ::=  { deployProvControlPlaneEthDefaultsEntry 36 }

deployProvControlPlaneEthDefaultsCdResyncTimeout OBJECT-TYPE
    SYNTAX      Unsigned32
    MAX-ACCESS  read-only
    STATUS      current
    DESCRIPTION   "Configuration Data Component' Resync Timeout"
    ::=  { deployProvControlPlaneEthDefaultsEntry 37 }

deployProvControlPlaneEthDefaultsRmConfigFlag OBJECT-TYPE
    SYNTAX      Unsigned32
    MAX-ACCESS  read-only
    STATUS      current
    DESCRIPTION   "Resource Management Component' Configuration Bitfield"
    ::=  { deployProvControlPlaneEthDefaultsEntry 38 }

deployProvControlPlaneEthDefaultsRmTraceDetail OBJECT-TYPE
    SYNTAX      Unsigned32
    MAX-ACCESS  read-only
    STATUS      current
    DESCRIPTION   "Resource Management Component' Trace Detail"
    ::=  { deployProvControlPlaneEthDefaultsEntry 39 }

deployProvControlPlaneEthDefaultsRmTraceTarget OBJECT-TYPE
    SYNTAX      Unsigned32
    MAX-ACCESS  read-only
    STATUS      current
    DESCRIPTION   "Resource Management Component' Trace Target"
    ::=  { deployProvControlPlaneEthDefaultsEntry 40 }

deployProvTunnelEthTable OBJECT-TYPE
    SYNTAX      SEQUENCE OF DeployProvTunnelEthEntry
    MAX-ACCESS  not-accessible
    STATUS      current
    DESCRIPTION   ""
    ::=  { controlPlaneDeployProv 64 }

deployProvTunnelEthEntry OBJECT-TYPE
    SYNTAX      DeployProvTunnelEthEntry
    MAX-ACCESS  not-accessible
    STATUS      current
    DESCRIPTION   ""
    INDEX       {
                  controlPlaneEthEntityIndex
                }
    ::=  { deployProvTunnelEthTable 1 }

DeployProvTunnelEthEntry ::=  SEQUENCE
  { deployProvTunnelEthRowStatus RowStatus,
    deployProvTunnelEthTunnelId SnmpAdminString,
    deployProvTunnelEthTunnelNo Unsigned32,
    deployProvTunnelEthAlias SnmpAdminString,
    deployProvTunnelEthTunnelType FspR7CpTunnelType,
    deployProvTunnelEthToTid SnmpAdminString,
    deployProvTunnelEthToNodeIp IpAddress,
    deployProvTunnelEthFromAid EntityIndex,
    deployProvTunnelEthToAid EntityIndex,
    deployProvTunnelEthConnectionDirection FspR7Conn,
    deployProvTunnelEthFacilityType FspR7InterfaceType,
    deployProvTunnelEthProvisionedPaths SnmpAdminString,
    deployProvTunnelEthPin FspR7CpPinning,
    deployProvTunnelEthCirRcv Unsigned32,
    deployProvTunnelEthCbsRcv Unsigned32,
    deployProvTunnelEthProtectionType FspR7CpProtectionType,
    deployProvTunnelEthRestorationType FspR7CpRestorationType,
    deployProvTunnelEthMonitorEntities FspR7EnableDisable,
    deployProvTunnelEthTunnelScope FspR7CpTunnelScope,
    deployProvTunnelEthLayer FspR7PacketsLayer,
    deployProvTunnelEthOifUni FspR7YesNo,
    deployProvTunnelEthFromAidString SnmpAdminString,
    deployProvTunnelEthToAidString SnmpAdminString,
    deployProvTunnelEthExcludedPaths SnmpAdminString,
    deployProvTunnelEthPreferPcs FspR7YesNo,
    deployProvTunnelEthEroScope SnmpAdminString,
    deployProvTunnelEthEroLifeCycle SnmpAdminString,
    deployProvTunnelEthXroScope SnmpAdminString,
    deployProvTunnelEthXroLifeCycle SnmpAdminString }

deployProvTunnelEthRowStatus OBJECT-TYPE
    SYNTAX      RowStatus
    MAX-ACCESS  read-write
    STATUS      current
    DESCRIPTION   ""
    ::=  { deployProvTunnelEthEntry 1 }

deployProvTunnelEthTunnelId OBJECT-TYPE
    SYNTAX      SnmpAdminString
    MAX-ACCESS  read-write
    STATUS      current
    DESCRIPTION   ""
    ::=  { deployProvTunnelEthEntry 2 }

deployProvTunnelEthTunnelNo OBJECT-TYPE
    SYNTAX      Unsigned32
    MAX-ACCESS  read-write
    STATUS      current
    DESCRIPTION   ""
    ::=  { deployProvTunnelEthEntry 3 }

deployProvTunnelEthAlias OBJECT-TYPE
    SYNTAX      SnmpAdminString
    MAX-ACCESS  read-write
    STATUS      current
    DESCRIPTION   ""
    ::=  { deployProvTunnelEthEntry 4 }

deployProvTunnelEthTunnelType OBJECT-TYPE
    SYNTAX      FspR7CpTunnelType
    MAX-ACCESS  read-write
    STATUS      current
    DESCRIPTION   ""
    ::=  { deployProvTunnelEthEntry 5 }

deployProvTunnelEthToTid OBJECT-TYPE
    SYNTAX      SnmpAdminString
    MAX-ACCESS  read-write
    STATUS      current
    DESCRIPTION   ""
    ::=  { deployProvTunnelEthEntry 6 }

deployProvTunnelEthToNodeIp OBJECT-TYPE
    SYNTAX      IpAddress
    MAX-ACCESS  read-write
    STATUS      current
    DESCRIPTION   ""
    ::=  { deployProvTunnelEthEntry 7 }

deployProvTunnelEthFromAid OBJECT-TYPE
    SYNTAX      EntityIndex
    MAX-ACCESS  read-write
    STATUS      current
    DESCRIPTION   ""
    ::=  { deployProvTunnelEthEntry 8 }

deployProvTunnelEthToAid OBJECT-TYPE
    SYNTAX      EntityIndex
    MAX-ACCESS  read-write
    STATUS      current
    DESCRIPTION   ""
    ::=  { deployProvTunnelEthEntry 9 }

deployProvTunnelEthConnectionDirection OBJECT-TYPE
    SYNTAX      FspR7Conn
    MAX-ACCESS  read-write
    STATUS      current
    DESCRIPTION   ""
    ::=  { deployProvTunnelEthEntry 10 }

deployProvTunnelEthFacilityType OBJECT-TYPE
    SYNTAX      FspR7InterfaceType
    MAX-ACCESS  read-write
    STATUS      current
    DESCRIPTION   ""
    ::=  { deployProvTunnelEthEntry 11 }

deployProvTunnelEthProvisionedPaths OBJECT-TYPE
    SYNTAX      SnmpAdminString
    MAX-ACCESS  read-write
    STATUS      current
    DESCRIPTION   ""
    ::=  { deployProvTunnelEthEntry 12 }

deployProvTunnelEthPin OBJECT-TYPE
    SYNTAX      FspR7CpPinning
    MAX-ACCESS  read-write
    STATUS      current
    DESCRIPTION   ""
    ::=  { deployProvTunnelEthEntry 13 }

deployProvTunnelEthCirRcv OBJECT-TYPE
    SYNTAX      Unsigned32 
    UNITS       "Mbps"
    MAX-ACCESS  read-write
    STATUS      current
    DESCRIPTION   ""
    ::=  { deployProvTunnelEthEntry 14 }

deployProvTunnelEthCbsRcv OBJECT-TYPE
    SYNTAX      Unsigned32 (0..26214400 | 4294967295) 
    UNITS       "Byte"
    MAX-ACCESS  read-write
    STATUS      current
    DESCRIPTION   ""
    ::=  { deployProvTunnelEthEntry 15 }

deployProvTunnelEthProtectionType OBJECT-TYPE
    SYNTAX      FspR7CpProtectionType
    MAX-ACCESS  read-write
    STATUS      current
    DESCRIPTION   ""
    ::=  { deployProvTunnelEthEntry 16 }

deployProvTunnelEthRestorationType OBJECT-TYPE
    SYNTAX      FspR7CpRestorationType
    MAX-ACCESS  read-write
    STATUS      current
    DESCRIPTION   ""
    ::=  { deployProvTunnelEthEntry 17 }

deployProvTunnelEthMonitorEntities OBJECT-TYPE
    SYNTAX      FspR7EnableDisable
    MAX-ACCESS  read-write
    STATUS      current
    DESCRIPTION   ""
    ::=  { deployProvTunnelEthEntry 18 }

deployProvTunnelEthTunnelScope OBJECT-TYPE
    SYNTAX      FspR7CpTunnelScope
    MAX-ACCESS  read-write
    STATUS      current
    DESCRIPTION
        "Service Scope extending over either Client or Network Ports of Modules or Links (UN or NR) for Connection Segements" 
    ::=  { deployProvTunnelEthEntry 19 }

deployProvTunnelEthLayer OBJECT-TYPE
    SYNTAX      FspR7PacketsLayer
    MAX-ACCESS  read-write
    STATUS      current
    DESCRIPTION
        "Notional Layer of Advertisement on Packets on the LIF" 
    ::=  { deployProvTunnelEthEntry 20 }

deployProvTunnelEthOifUni OBJECT-TYPE
    SYNTAX      FspR7YesNo
    MAX-ACCESS  read-write
    STATUS      current
    DESCRIPTION
        "OIF UNI Tunnel" 
    ::=  { deployProvTunnelEthEntry 21 }

deployProvTunnelEthFromAidString OBJECT-TYPE
    SYNTAX      SnmpAdminString
    MAX-ACCESS  read-write
    STATUS      current
    DESCRIPTION
        "" 
    ::=  { deployProvTunnelEthEntry 22 }

deployProvTunnelEthToAidString OBJECT-TYPE
    SYNTAX      SnmpAdminString
    MAX-ACCESS  read-write
    STATUS      current
    DESCRIPTION
        "" 
    ::=  { deployProvTunnelEthEntry 23 }

deployProvTunnelEthExcludedPaths OBJECT-TYPE
    SYNTAX      SnmpAdminString
    MAX-ACCESS  read-write
    STATUS      current
    DESCRIPTION
        "Lists of Path Elements to be excluded" 
    ::=  { deployProvTunnelEthEntry 24 }

deployProvTunnelEthPreferPcs OBJECT-TYPE
    SYNTAX      FspR7YesNo
    MAX-ACCESS  read-write
    STATUS      current
    DESCRIPTION
        "Preferred Path Computation Engine (Server)" 
    ::=  { deployProvTunnelEthEntry 25 }

deployProvTunnelEthEroScope OBJECT-TYPE
    SYNTAX      SnmpAdminString
    MAX-ACCESS  read-write
    STATUS      current
    DESCRIPTION
        "Inclusion Route - Scope" 
    ::=  { deployProvTunnelEthEntry 26 }

deployProvTunnelEthEroLifeCycle OBJECT-TYPE
    SYNTAX      SnmpAdminString
    MAX-ACCESS  read-write
    STATUS      current
    DESCRIPTION
        "Inclusion Route - Life Cycle" 
    ::=  { deployProvTunnelEthEntry 27 }

deployProvTunnelEthXroScope OBJECT-TYPE
    SYNTAX      SnmpAdminString
    MAX-ACCESS  read-write
    STATUS      current
    DESCRIPTION
        "Exclusion Path Elements - Scope" 
    ::=  { deployProvTunnelEthEntry 28 }

deployProvTunnelEthXroLifeCycle OBJECT-TYPE
    SYNTAX      SnmpAdminString
    MAX-ACCESS  read-write
    STATUS      current
    DESCRIPTION
        "Exclusion Path Elements - Life Cycle" 
    ::=  { deployProvTunnelEthEntry 29 }

deployProvTunnelEthCapTable OBJECT-TYPE
    SYNTAX      SEQUENCE OF DeployProvTunnelEthCapEntry
    MAX-ACCESS  not-accessible
    STATUS      current
    DESCRIPTION   ""
    ::=  { controlPlaneDeployProv 65  }

deployProvTunnelEthCapEntry OBJECT-TYPE
    SYNTAX      DeployProvTunnelEthCapEntry
    MAX-ACCESS  not-accessible
    STATUS      current
    DESCRIPTION   ""
    INDEX       { controlPlaneEthEntityIndex }
    ::=  { deployProvTunnelEthCapTable 1 }

DeployProvTunnelEthCapEntry ::=  SEQUENCE
  { deployProvTunnelEthCapRowStatus FspR7RowStatusCaps,
    deployProvTunnelEthCapTunnelId Integer32,
    deployProvTunnelEthCapTunnelNo FspR7Unsigned32Caps,
    deployProvTunnelEthCapAlias Integer32,
    deployProvTunnelEthCapTunnelType FspR7CpTunnelTypeCaps,
    deployProvTunnelEthCapToTid Integer32,
    deployProvTunnelEthCapToNodeIp FspR7YesNo,
    deployProvTunnelEthCapFromAid Integer32,
    deployProvTunnelEthCapToAid Integer32,
    deployProvTunnelEthCapConnectionDirection FspR7ConnCaps,
    deployProvTunnelEthCapFacilityType FspR7InterfaceTypeCaps,
    deployProvTunnelEthCapProvisionedPaths Integer32,
    deployProvTunnelEthCapPin FspR7CpPinningCaps,
    deployProvTunnelEthCapCirRcv FspR7Unsigned32Caps,
    deployProvTunnelEthCapCbsRcv Unsigned32,
    deployProvTunnelEthCapProtectionType FspR7CpProtectionTypeCaps,
    deployProvTunnelEthCapRestorationType FspR7CpRestorationTypeCaps,
    deployProvTunnelEthCapMonitorEntities FspR7EnableDisableCaps,
    deployProvTunnelEthCapTunnelScope FspR7CpTunnelScopeCaps,
    deployProvTunnelEthCapLayer FspR7PacketsLayerCaps,
    deployProvTunnelEthCapOifUni FspR7YesNoCaps,
    deployProvTunnelEthCapFromAidString Integer32,
    deployProvTunnelEthCapToAidString Integer32,
    deployProvTunnelEthCapExcludedPaths SnmpAdminString,
    deployProvTunnelEthCapPreferPcs FspR7YesNoCaps,
    deployProvTunnelEthCapEroScope SnmpAdminString,
    deployProvTunnelEthCapEroLifeCycle SnmpAdminString,
    deployProvTunnelEthCapXroScope SnmpAdminString,
    deployProvTunnelEthCapXroLifeCycle SnmpAdminString }

deployProvTunnelEthCapRowStatus OBJECT-TYPE
    SYNTAX      FspR7RowStatusCaps
    MAX-ACCESS  read-only
    STATUS      current
    DESCRIPTION   ""
    ::=  { deployProvTunnelEthCapEntry 1 }

deployProvTunnelEthCapTunnelId OBJECT-TYPE
    SYNTAX      Integer32
    MAX-ACCESS  read-only
    STATUS      current
    DESCRIPTION   ""
    ::=  { deployProvTunnelEthCapEntry 2 }

deployProvTunnelEthCapTunnelNo OBJECT-TYPE
    SYNTAX      FspR7Unsigned32Caps
    MAX-ACCESS  read-only
    STATUS      current
    DESCRIPTION   ""
    ::=  { deployProvTunnelEthCapEntry 3 }

deployProvTunnelEthCapAlias OBJECT-TYPE
    SYNTAX      Integer32
    MAX-ACCESS  read-only
    STATUS      current
    DESCRIPTION   ""
    ::=  { deployProvTunnelEthCapEntry 4 }

deployProvTunnelEthCapTunnelType OBJECT-TYPE
    SYNTAX      FspR7CpTunnelTypeCaps
    MAX-ACCESS  read-only
    STATUS      current
    DESCRIPTION   ""
    ::=  { deployProvTunnelEthCapEntry 5 }

deployProvTunnelEthCapToTid OBJECT-TYPE
    SYNTAX      Integer32
    MAX-ACCESS  read-only
    STATUS      current
    DESCRIPTION   ""
    ::=  { deployProvTunnelEthCapEntry 6 }

deployProvTunnelEthCapToNodeIp OBJECT-TYPE
    SYNTAX      FspR7YesNo
    MAX-ACCESS  read-only
    STATUS      current
    DESCRIPTION   ""
    ::=  { deployProvTunnelEthCapEntry 7 }

deployProvTunnelEthCapFromAid OBJECT-TYPE
    SYNTAX      Integer32
    MAX-ACCESS  read-only
    STATUS      current
    DESCRIPTION   ""
    ::=  { deployProvTunnelEthCapEntry 8 }

deployProvTunnelEthCapToAid OBJECT-TYPE
    SYNTAX      Integer32
    MAX-ACCESS  read-only
    STATUS      current
    DESCRIPTION   ""
    ::=  { deployProvTunnelEthCapEntry 9 }

deployProvTunnelEthCapConnectionDirection OBJECT-TYPE
    SYNTAX      FspR7ConnCaps
    MAX-ACCESS  read-only
    STATUS      current
    DESCRIPTION   ""
    ::=  { deployProvTunnelEthCapEntry 10 }

deployProvTunnelEthCapFacilityType OBJECT-TYPE
    SYNTAX      FspR7InterfaceTypeCaps
    MAX-ACCESS  read-only
    STATUS      current
    DESCRIPTION   ""
    ::=  { deployProvTunnelEthCapEntry 11 }

deployProvTunnelEthCapProvisionedPaths OBJECT-TYPE
    SYNTAX      Integer32
    MAX-ACCESS  read-only
    STATUS      current
    DESCRIPTION   ""
    ::=  { deployProvTunnelEthCapEntry 12 }

deployProvTunnelEthCapPin OBJECT-TYPE
    SYNTAX      FspR7CpPinningCaps
    MAX-ACCESS  read-only
    STATUS      current
    DESCRIPTION   ""
    ::=  { deployProvTunnelEthCapEntry 13 }

deployProvTunnelEthCapCirRcv OBJECT-TYPE
    SYNTAX      FspR7Unsigned32Caps
    UNITS       "Mbps"
    MAX-ACCESS  read-only
    STATUS      current
    DESCRIPTION   ""
    ::=  { deployProvTunnelEthCapEntry 14 }

deployProvTunnelEthCapCbsRcv OBJECT-TYPE
    SYNTAX      Unsigned32
    UNITS       "Byte"
    MAX-ACCESS  read-only
    STATUS      current
    DESCRIPTION   ""
    ::=  { deployProvTunnelEthCapEntry 15 }

deployProvTunnelEthCapProtectionType OBJECT-TYPE
    SYNTAX      FspR7CpProtectionTypeCaps
    MAX-ACCESS  read-only
    STATUS      current
    DESCRIPTION   ""
    ::=  { deployProvTunnelEthCapEntry 16 }

deployProvTunnelEthCapRestorationType OBJECT-TYPE
    SYNTAX      FspR7CpRestorationTypeCaps
    MAX-ACCESS  read-only
    STATUS      current
    DESCRIPTION   ""
    ::=  { deployProvTunnelEthCapEntry 17 }

deployProvTunnelEthCapMonitorEntities OBJECT-TYPE
    SYNTAX      FspR7EnableDisableCaps
    MAX-ACCESS  read-only
    STATUS      current
    DESCRIPTION   ""
    ::=  { deployProvTunnelEthCapEntry 18 }

deployProvTunnelEthCapTunnelScope OBJECT-TYPE
    SYNTAX      FspR7CpTunnelScopeCaps
    MAX-ACCESS  read-only
    STATUS      current
    DESCRIPTION
        "Service Scope extending over either Client or Network Ports of Modules or Links (UN or NR) for Connection Segements" 
    ::=  { deployProvTunnelEthCapEntry 19 }

deployProvTunnelEthCapLayer OBJECT-TYPE
    SYNTAX      FspR7PacketsLayerCaps
    MAX-ACCESS  read-only
    STATUS      current
    DESCRIPTION
        "Notional Layer of Advertisement on Packets on the LIF" 
    ::=  { deployProvTunnelEthCapEntry 20 }

deployProvTunnelEthCapOifUni OBJECT-TYPE
    SYNTAX      FspR7YesNoCaps
    MAX-ACCESS  read-only
    STATUS      current
    DESCRIPTION
        "OIF UNI Tunnel" 
    ::=  { deployProvTunnelEthCapEntry 21 }

deployProvTunnelEthCapFromAidString OBJECT-TYPE
    SYNTAX      Integer32
    MAX-ACCESS  read-only
    STATUS      current
    DESCRIPTION
        "" 
    ::=  { deployProvTunnelEthCapEntry 22 }

deployProvTunnelEthCapToAidString OBJECT-TYPE
    SYNTAX      Integer32
    MAX-ACCESS  read-only
    STATUS      current
    DESCRIPTION
        "" 
    ::=  { deployProvTunnelEthCapEntry 23 }

deployProvTunnelEthCapExcludedPaths OBJECT-TYPE
    SYNTAX      SnmpAdminString
    MAX-ACCESS  read-only
    STATUS      current
    DESCRIPTION
        "Lists of Path Elements to be excluded" 
    ::=  { deployProvTunnelEthCapEntry 24 }

deployProvTunnelEthCapPreferPcs OBJECT-TYPE
    SYNTAX      FspR7YesNoCaps
    MAX-ACCESS  read-only
    STATUS      current
    DESCRIPTION
        "Preferred Path Computation Engine (Server)" 
    ::=  { deployProvTunnelEthCapEntry 25 }

deployProvTunnelEthCapEroScope OBJECT-TYPE
    SYNTAX      SnmpAdminString
    MAX-ACCESS  read-only
    STATUS      current
    DESCRIPTION
        "Inclusion Route - Scope" 
    ::=  { deployProvTunnelEthCapEntry 26 }

deployProvTunnelEthCapEroLifeCycle OBJECT-TYPE
    SYNTAX      SnmpAdminString
    MAX-ACCESS  read-only
    STATUS      current
    DESCRIPTION
        "Inclusion Route - Life Cycle" 
    ::=  { deployProvTunnelEthCapEntry 27 }

deployProvTunnelEthCapXroScope OBJECT-TYPE
    SYNTAX      SnmpAdminString
    MAX-ACCESS  read-only
    STATUS      current
    DESCRIPTION
        "Exclusion Path Elements - Scope" 
    ::=  { deployProvTunnelEthCapEntry 28 }

deployProvTunnelEthCapXroLifeCycle OBJECT-TYPE
    SYNTAX      SnmpAdminString
    MAX-ACCESS  read-only
    STATUS      current
    DESCRIPTION
        "Exclusion Path Elements - Life Cycle" 
    ::=  { deployProvTunnelEthCapEntry 29 }

deployProvTunnelEthDefaultsTable  OBJECT-TYPE
    SYNTAX      SEQUENCE OF DeployProvTunnelEthDefaultsEntry
    MAX-ACCESS  not-accessible
    STATUS      current
    DESCRIPTION   ""
    ::=  { controlPlaneDeployProv 66  }

deployProvTunnelEthDefaultsEntry OBJECT-TYPE
    SYNTAX      DeployProvTunnelEthDefaultsEntry
    MAX-ACCESS  not-accessible
    STATUS      current
    DESCRIPTION   ""
    INDEX       { controlPlaneEthEntityIndex }
    ::=  { deployProvTunnelEthDefaultsTable 1 }

DeployProvTunnelEthDefaultsEntry ::=  SEQUENCE
  { deployProvTunnelEthDefaultsRowStatus RowStatus,
    deployProvTunnelEthDefaultsTunnelId SnmpAdminString,
    deployProvTunnelEthDefaultsTunnelNo Unsigned32,
    deployProvTunnelEthDefaultsAlias SnmpAdminString,
    deployProvTunnelEthDefaultsTunnelType FspR7CpTunnelType,
    deployProvTunnelEthDefaultsToTid SnmpAdminString,
    deployProvTunnelEthDefaultsToNodeIp IpAddress,
    deployProvTunnelEthDefaultsFromAid EntityIndex,
    deployProvTunnelEthDefaultsToAid EntityIndex,
    deployProvTunnelEthDefaultsConnectionDirection FspR7Conn,
    deployProvTunnelEthDefaultsFacilityType FspR7InterfaceType,
    deployProvTunnelEthDefaultsProvisionedPaths SnmpAdminString,
    deployProvTunnelEthDefaultsPin FspR7CpPinning,
    deployProvTunnelEthDefaultsCirRcv Unsigned32,
    deployProvTunnelEthDefaultsCbsRcv Unsigned32,
    deployProvTunnelEthDefaultsProtectionType FspR7CpProtectionType,
    deployProvTunnelEthDefaultsRestorationType FspR7CpRestorationType,
    deployProvTunnelEthDefaultsMonitorEntities FspR7EnableDisable,
    deployProvTunnelEthDefaultsTunnelScope FspR7CpTunnelScope,
    deployProvTunnelEthDefaultsLayer FspR7PacketsLayer,
    deployProvTunnelEthDefaultsOifUni FspR7YesNo,
    deployProvTunnelEthDefaultsFromAidString SnmpAdminString,
    deployProvTunnelEthDefaultsToAidString SnmpAdminString,
    deployProvTunnelEthDefaultsExcludedPaths SnmpAdminString,
    deployProvTunnelEthDefaultsPreferPcs FspR7YesNo,
    deployProvTunnelEthDefaultsEroScope SnmpAdminString,
    deployProvTunnelEthDefaultsEroLifeCycle SnmpAdminString,
    deployProvTunnelEthDefaultsXroScope SnmpAdminString,
    deployProvTunnelEthDefaultsXroLifeCycle SnmpAdminString }

deployProvTunnelEthDefaultsRowStatus OBJECT-TYPE
    SYNTAX      RowStatus
    MAX-ACCESS  read-only
    STATUS      current
    DESCRIPTION   ""
    ::=  { deployProvTunnelEthDefaultsEntry 1 }

deployProvTunnelEthDefaultsTunnelId OBJECT-TYPE
    SYNTAX      SnmpAdminString
    MAX-ACCESS  read-only
    STATUS      current
    DESCRIPTION   ""
    ::=  { deployProvTunnelEthDefaultsEntry 2 }

deployProvTunnelEthDefaultsTunnelNo OBJECT-TYPE
    SYNTAX      Unsigned32
    MAX-ACCESS  read-only
    STATUS      current
    DESCRIPTION   ""
    ::=  { deployProvTunnelEthDefaultsEntry 3 }

deployProvTunnelEthDefaultsAlias OBJECT-TYPE
    SYNTAX      SnmpAdminString
    MAX-ACCESS  read-only
    STATUS      current
    DESCRIPTION   ""
    ::=  { deployProvTunnelEthDefaultsEntry 4 }

deployProvTunnelEthDefaultsTunnelType OBJECT-TYPE
    SYNTAX      FspR7CpTunnelType
    MAX-ACCESS  read-only
    STATUS      current
    DESCRIPTION   ""
    ::=  { deployProvTunnelEthDefaultsEntry 5 }

deployProvTunnelEthDefaultsToTid OBJECT-TYPE
    SYNTAX      SnmpAdminString
    MAX-ACCESS  read-only
    STATUS      current
    DESCRIPTION   ""
    ::=  { deployProvTunnelEthDefaultsEntry 6 }

deployProvTunnelEthDefaultsToNodeIp OBJECT-TYPE
    SYNTAX      IpAddress
    MAX-ACCESS  read-only
    STATUS      current
    DESCRIPTION   ""
    ::=  { deployProvTunnelEthDefaultsEntry 7 }

deployProvTunnelEthDefaultsFromAid OBJECT-TYPE
    SYNTAX      EntityIndex
    MAX-ACCESS  read-only
    STATUS      current
    DESCRIPTION   ""
    ::=  { deployProvTunnelEthDefaultsEntry 8 }

deployProvTunnelEthDefaultsToAid OBJECT-TYPE
    SYNTAX      EntityIndex
    MAX-ACCESS  read-only
    STATUS      current
    DESCRIPTION   ""
    ::=  { deployProvTunnelEthDefaultsEntry 9 }

deployProvTunnelEthDefaultsConnectionDirection OBJECT-TYPE
    SYNTAX      FspR7Conn
    MAX-ACCESS  read-only
    STATUS      current
    DESCRIPTION   ""
    ::=  { deployProvTunnelEthDefaultsEntry 10 }

deployProvTunnelEthDefaultsFacilityType OBJECT-TYPE
    SYNTAX      FspR7InterfaceType
    MAX-ACCESS  read-only
    STATUS      current
    DESCRIPTION   ""
    ::=  { deployProvTunnelEthDefaultsEntry 11 }

deployProvTunnelEthDefaultsProvisionedPaths OBJECT-TYPE
    SYNTAX      SnmpAdminString
    MAX-ACCESS  read-only
    STATUS      current
    DESCRIPTION   ""
    ::=  { deployProvTunnelEthDefaultsEntry 12 }

deployProvTunnelEthDefaultsPin OBJECT-TYPE
    SYNTAX      FspR7CpPinning
    MAX-ACCESS  read-only
    STATUS      current
    DESCRIPTION   ""
    ::=  { deployProvTunnelEthDefaultsEntry 13 }

deployProvTunnelEthDefaultsCirRcv OBJECT-TYPE
    SYNTAX      Unsigned32 
    UNITS       "Mbps"
    MAX-ACCESS  read-only
    STATUS      current
    DESCRIPTION   ""
    ::=  { deployProvTunnelEthDefaultsEntry 14 }

deployProvTunnelEthDefaultsCbsRcv OBJECT-TYPE
    SYNTAX      Unsigned32 (0..26214400 | 4294967295) 
    UNITS       "Byte"
    MAX-ACCESS  read-only
    STATUS      current
    DESCRIPTION   ""
    ::=  { deployProvTunnelEthDefaultsEntry 15 }

deployProvTunnelEthDefaultsProtectionType OBJECT-TYPE
    SYNTAX      FspR7CpProtectionType
    MAX-ACCESS  read-only
    STATUS      current
    DESCRIPTION   ""
    ::=  { deployProvTunnelEthDefaultsEntry 16 }

deployProvTunnelEthDefaultsRestorationType OBJECT-TYPE
    SYNTAX      FspR7CpRestorationType
    MAX-ACCESS  read-only
    STATUS      current
    DESCRIPTION   ""
    ::=  { deployProvTunnelEthDefaultsEntry 17 }

deployProvTunnelEthDefaultsMonitorEntities OBJECT-TYPE
    SYNTAX      FspR7EnableDisable
    MAX-ACCESS  read-only
    STATUS      current
    DESCRIPTION   ""
    ::=  { deployProvTunnelEthDefaultsEntry 18 }

deployProvTunnelEthDefaultsTunnelScope OBJECT-TYPE
    SYNTAX      FspR7CpTunnelScope
    MAX-ACCESS  read-only
    STATUS      current
    DESCRIPTION
        "Service Scope extending over either Client or Network Ports of Modules or Links (UN or NR) for Connection Segements" 
    ::=  { deployProvTunnelEthDefaultsEntry 19 }

deployProvTunnelEthDefaultsLayer OBJECT-TYPE
    SYNTAX      FspR7PacketsLayer
    MAX-ACCESS  read-only
    STATUS      current
    DESCRIPTION
        "Notional Layer of Advertisement on Packets on the LIF" 
    ::=  { deployProvTunnelEthDefaultsEntry 20 }

deployProvTunnelEthDefaultsOifUni OBJECT-TYPE
    SYNTAX      FspR7YesNo
    MAX-ACCESS  read-only
    STATUS      current
    DESCRIPTION
        "OIF UNI Tunnel" 
    ::=  { deployProvTunnelEthDefaultsEntry 21 }

deployProvTunnelEthDefaultsFromAidString OBJECT-TYPE
    SYNTAX      SnmpAdminString
    MAX-ACCESS  read-only
    STATUS      current
    DESCRIPTION
        "" 
    ::=  { deployProvTunnelEthDefaultsEntry 22 }

deployProvTunnelEthDefaultsToAidString OBJECT-TYPE
    SYNTAX      SnmpAdminString
    MAX-ACCESS  read-only
    STATUS      current
    DESCRIPTION
        "" 
    ::=  { deployProvTunnelEthDefaultsEntry 23 }

deployProvTunnelEthDefaultsExcludedPaths OBJECT-TYPE
    SYNTAX      SnmpAdminString
    MAX-ACCESS  read-only
    STATUS      current
    DESCRIPTION
        "Lists of Path Elements to be excluded" 
    ::=  { deployProvTunnelEthDefaultsEntry 24 }

deployProvTunnelEthDefaultsPreferPcs OBJECT-TYPE
    SYNTAX      FspR7YesNo
    MAX-ACCESS  read-only
    STATUS      current
    DESCRIPTION
        "Preferred Path Computation Engine (Server)" 
    ::=  { deployProvTunnelEthDefaultsEntry 25 }

deployProvTunnelEthDefaultsEroScope OBJECT-TYPE
    SYNTAX      SnmpAdminString
    MAX-ACCESS  read-only
    STATUS      current
    DESCRIPTION
        "Inclusion Route - Scope" 
    ::=  { deployProvTunnelEthDefaultsEntry 26 }

deployProvTunnelEthDefaultsEroLifeCycle OBJECT-TYPE
    SYNTAX      SnmpAdminString
    MAX-ACCESS  read-only
    STATUS      current
    DESCRIPTION
        "Inclusion Route - Life Cycle" 
    ::=  { deployProvTunnelEthDefaultsEntry 27 }

deployProvTunnelEthDefaultsXroScope OBJECT-TYPE
    SYNTAX      SnmpAdminString
    MAX-ACCESS  read-only
    STATUS      current
    DESCRIPTION
        "Exclusion Path Elements - Scope" 
    ::=  { deployProvTunnelEthDefaultsEntry 28 }

deployProvTunnelEthDefaultsXroLifeCycle OBJECT-TYPE
    SYNTAX      SnmpAdminString
    MAX-ACCESS  read-only
    STATUS      current
    DESCRIPTION
        "Exclusion Path Elements - Life Cycle" 
    ::=  { deployProvTunnelEthDefaultsEntry 29 }

deployProvPathEthTable OBJECT-TYPE
    SYNTAX      SEQUENCE OF DeployProvPathEthEntry
    MAX-ACCESS  not-accessible
    STATUS      current
    DESCRIPTION   ""
    ::=  { controlPlaneDeployProv 67 }

deployProvPathEthEntry OBJECT-TYPE
    SYNTAX      DeployProvPathEthEntry
    MAX-ACCESS  not-accessible
    STATUS      current
    DESCRIPTION   ""
    INDEX       {
                  controlPlaneEthEntityIndex
                }
    ::=  { deployProvPathEthTable 1 }

DeployProvPathEthEntry ::=  SEQUENCE
  { deployProvPathEthRowStatus RowStatus,
    deployProvPathEthPathId SnmpAdminString }

deployProvPathEthRowStatus OBJECT-TYPE
    SYNTAX      RowStatus
    MAX-ACCESS  read-write
    STATUS      current
    DESCRIPTION   ""
    ::=  { deployProvPathEthEntry 1 }

deployProvPathEthPathId OBJECT-TYPE
    SYNTAX      SnmpAdminString
    MAX-ACCESS  read-write
    STATUS      current
    DESCRIPTION   ""
    ::=  { deployProvPathEthEntry 2 }

deployProvPathEthCapTable OBJECT-TYPE
    SYNTAX      SEQUENCE OF DeployProvPathEthCapEntry
    MAX-ACCESS  not-accessible
    STATUS      current
    DESCRIPTION   ""
    ::=  { controlPlaneDeployProv 68  }

deployProvPathEthCapEntry OBJECT-TYPE
    SYNTAX      DeployProvPathEthCapEntry
    MAX-ACCESS  not-accessible
    STATUS      current
    DESCRIPTION   ""
    INDEX       { controlPlaneEthEntityIndex }
    ::=  { deployProvPathEthCapTable 1 }

DeployProvPathEthCapEntry ::=  SEQUENCE
  { deployProvPathEthCapRowStatus FspR7RowStatusCaps,
    deployProvPathEthCapPathId Integer32 }

deployProvPathEthCapRowStatus OBJECT-TYPE
    SYNTAX      FspR7RowStatusCaps
    MAX-ACCESS  read-only
    STATUS      current
    DESCRIPTION   ""
    ::=  { deployProvPathEthCapEntry 1 }

deployProvPathEthCapPathId OBJECT-TYPE
    SYNTAX      Integer32
    MAX-ACCESS  read-only
    STATUS      current
    DESCRIPTION   ""
    ::=  { deployProvPathEthCapEntry 2 }

deployProvPathEthDefaultsTable  OBJECT-TYPE
    SYNTAX      SEQUENCE OF DeployProvPathEthDefaultsEntry
    MAX-ACCESS  not-accessible
    STATUS      current
    DESCRIPTION   ""
    ::=  { controlPlaneDeployProv 69  }

deployProvPathEthDefaultsEntry OBJECT-TYPE
    SYNTAX      DeployProvPathEthDefaultsEntry
    MAX-ACCESS  not-accessible
    STATUS      current
    DESCRIPTION   ""
    INDEX       { controlPlaneEthEntityIndex }
    ::=  { deployProvPathEthDefaultsTable 1 }

DeployProvPathEthDefaultsEntry ::=  SEQUENCE
  { deployProvPathEthDefaultsRowStatus RowStatus,
    deployProvPathEthDefaultsPathId SnmpAdminString }

deployProvPathEthDefaultsRowStatus OBJECT-TYPE
    SYNTAX      RowStatus
    MAX-ACCESS  read-only
    STATUS      current
    DESCRIPTION   ""
    ::=  { deployProvPathEthDefaultsEntry 1 }

deployProvPathEthDefaultsPathId OBJECT-TYPE
    SYNTAX      SnmpAdminString
    MAX-ACCESS  read-only
    STATUS      current
    DESCRIPTION   ""
    ::=  { deployProvPathEthDefaultsEntry 2 }

deployProvPathElementEthTable OBJECT-TYPE
    SYNTAX      SEQUENCE OF DeployProvPathElementEthEntry
    MAX-ACCESS  not-accessible
    STATUS      current
    DESCRIPTION   ""
    ::=  { controlPlaneDeployProv 70 }

deployProvPathElementEthEntry OBJECT-TYPE
    SYNTAX      DeployProvPathElementEthEntry
    MAX-ACCESS  not-accessible
    STATUS      current
    DESCRIPTION   ""
    INDEX       {
                  controlPlaneEthEntityIndex
                }
    ::=  { deployProvPathElementEthTable 1 }

DeployProvPathElementEthEntry ::=  SEQUENCE
  { deployProvPathElementEthRowStatus RowStatus,
    deployProvPathElementEthTrafficEngineeringType FspR7CpTEType,
    deployProvPathElementEthLifIp IpAddress,
    deployProvPathElementEthNodeIp IpAddress,
    deployProvPathElementEthTid SnmpAdminString,
    deployProvPathElementEthLogicalInterfaceId Unsigned32,
    deployProvPathElementEthTie FspR7CpTie,
    deployProvPathElementEthUpstreamSvid Unsigned32,
    deployProvPathElementEthDownstreamSvid Unsigned32 }

deployProvPathElementEthRowStatus OBJECT-TYPE
    SYNTAX      RowStatus
    MAX-ACCESS  read-write
    STATUS      current
    DESCRIPTION   ""
    ::=  { deployProvPathElementEthEntry 1 }

deployProvPathElementEthTrafficEngineeringType OBJECT-TYPE
    SYNTAX      FspR7CpTEType
    MAX-ACCESS  read-write
    STATUS      current
    DESCRIPTION   ""
    ::=  { deployProvPathElementEthEntry 2 }

deployProvPathElementEthLifIp OBJECT-TYPE
    SYNTAX      IpAddress
    MAX-ACCESS  read-write
    STATUS      current
    DESCRIPTION   ""
    ::=  { deployProvPathElementEthEntry 3 }

deployProvPathElementEthNodeIp OBJECT-TYPE
    SYNTAX      IpAddress
    MAX-ACCESS  read-write
    STATUS      current
    DESCRIPTION   ""
    ::=  { deployProvPathElementEthEntry 4 }

deployProvPathElementEthTid OBJECT-TYPE
    SYNTAX      SnmpAdminString
    MAX-ACCESS  read-write
    STATUS      current
    DESCRIPTION   ""
    ::=  { deployProvPathElementEthEntry 5 }

deployProvPathElementEthLogicalInterfaceId OBJECT-TYPE
    SYNTAX      Unsigned32
    MAX-ACCESS  read-write
    STATUS      current
    DESCRIPTION   ""
    ::=  { deployProvPathElementEthEntry 6 }

deployProvPathElementEthTie OBJECT-TYPE
    SYNTAX      FspR7CpTie
    MAX-ACCESS  read-write
    STATUS      current
    DESCRIPTION   ""
    ::=  { deployProvPathElementEthEntry 7 }

deployProvPathElementEthUpstreamSvid OBJECT-TYPE
    SYNTAX      Unsigned32
    MAX-ACCESS  read-write
    STATUS      current
    DESCRIPTION   ""
    ::=  { deployProvPathElementEthEntry 8 }

deployProvPathElementEthDownstreamSvid OBJECT-TYPE
    SYNTAX      Unsigned32
    MAX-ACCESS  read-write
    STATUS      current
    DESCRIPTION   ""
    ::=  { deployProvPathElementEthEntry 9 }

deployProvPathElementEthCapTable OBJECT-TYPE
    SYNTAX      SEQUENCE OF DeployProvPathElementEthCapEntry
    MAX-ACCESS  not-accessible
    STATUS      current
    DESCRIPTION   ""
    ::=  { controlPlaneDeployProv 71  }

deployProvPathElementEthCapEntry OBJECT-TYPE
    SYNTAX      DeployProvPathElementEthCapEntry
    MAX-ACCESS  not-accessible
    STATUS      current
    DESCRIPTION   ""
    INDEX       { controlPlaneEthEntityIndex }
    ::=  { deployProvPathElementEthCapTable 1 }

DeployProvPathElementEthCapEntry ::=  SEQUENCE
  { deployProvPathElementEthCapRowStatus FspR7RowStatusCaps,
    deployProvPathElementEthCapTrafficEngineeringType FspR7CpTETypeCaps,
    deployProvPathElementEthCapLifIp FspR7YesNo,
    deployProvPathElementEthCapNodeIp FspR7YesNo,
    deployProvPathElementEthCapTid Integer32,
    deployProvPathElementEthCapLogicalInterfaceId FspR7Unsigned32Caps,
    deployProvPathElementEthCapTie FspR7CpTieCaps,
    deployProvPathElementEthCapUpstreamSvid FspR7Unsigned32Caps,
    deployProvPathElementEthCapDownstreamSvid FspR7Unsigned32Caps }

deployProvPathElementEthCapRowStatus OBJECT-TYPE
    SYNTAX      FspR7RowStatusCaps
    MAX-ACCESS  read-only
    STATUS      current
    DESCRIPTION   ""
    ::=  { deployProvPathElementEthCapEntry 1 }

deployProvPathElementEthCapTrafficEngineeringType OBJECT-TYPE
    SYNTAX      FspR7CpTETypeCaps
    MAX-ACCESS  read-only
    STATUS      current
    DESCRIPTION   ""
    ::=  { deployProvPathElementEthCapEntry 2 }

deployProvPathElementEthCapLifIp OBJECT-TYPE
    SYNTAX      FspR7YesNo
    MAX-ACCESS  read-only
    STATUS      current
    DESCRIPTION   ""
    ::=  { deployProvPathElementEthCapEntry 3 }

deployProvPathElementEthCapNodeIp OBJECT-TYPE
    SYNTAX      FspR7YesNo
    MAX-ACCESS  read-only
    STATUS      current
    DESCRIPTION   ""
    ::=  { deployProvPathElementEthCapEntry 4 }

deployProvPathElementEthCapTid OBJECT-TYPE
    SYNTAX      Integer32
    MAX-ACCESS  read-only
    STATUS      current
    DESCRIPTION   ""
    ::=  { deployProvPathElementEthCapEntry 5 }

deployProvPathElementEthCapLogicalInterfaceId OBJECT-TYPE
    SYNTAX      FspR7Unsigned32Caps
    MAX-ACCESS  read-only
    STATUS      current
    DESCRIPTION   ""
    ::=  { deployProvPathElementEthCapEntry 6 }

deployProvPathElementEthCapTie OBJECT-TYPE
    SYNTAX      FspR7CpTieCaps
    MAX-ACCESS  read-only
    STATUS      current
    DESCRIPTION   ""
    ::=  { deployProvPathElementEthCapEntry 7 }

deployProvPathElementEthCapUpstreamSvid OBJECT-TYPE
    SYNTAX      FspR7Unsigned32Caps
    MAX-ACCESS  read-only
    STATUS      current
    DESCRIPTION   ""
    ::=  { deployProvPathElementEthCapEntry 8 }

deployProvPathElementEthCapDownstreamSvid OBJECT-TYPE
    SYNTAX      FspR7Unsigned32Caps
    MAX-ACCESS  read-only
    STATUS      current
    DESCRIPTION   ""
    ::=  { deployProvPathElementEthCapEntry 9 }

deployProvPathElementEthDefaultsTable  OBJECT-TYPE
    SYNTAX      SEQUENCE OF DeployProvPathElementEthDefaultsEntry
    MAX-ACCESS  not-accessible
    STATUS      current
    DESCRIPTION   ""
    ::=  { controlPlaneDeployProv 72  }

deployProvPathElementEthDefaultsEntry OBJECT-TYPE
    SYNTAX      DeployProvPathElementEthDefaultsEntry
    MAX-ACCESS  not-accessible
    STATUS      current
    DESCRIPTION   ""
    INDEX       { controlPlaneEthEntityIndex }
    ::=  { deployProvPathElementEthDefaultsTable 1 }

DeployProvPathElementEthDefaultsEntry ::=  SEQUENCE
  { deployProvPathElementEthDefaultsRowStatus RowStatus,
    deployProvPathElementEthDefaultsTrafficEngineeringType FspR7CpTEType,
    deployProvPathElementEthDefaultsLifIp IpAddress,
    deployProvPathElementEthDefaultsNodeIp IpAddress,
    deployProvPathElementEthDefaultsTid SnmpAdminString,
    deployProvPathElementEthDefaultsLogicalInterfaceId Unsigned32,
    deployProvPathElementEthDefaultsTie FspR7CpTie,
    deployProvPathElementEthDefaultsUpstreamSvid Unsigned32,
    deployProvPathElementEthDefaultsDownstreamSvid Unsigned32 }

deployProvPathElementEthDefaultsRowStatus OBJECT-TYPE
    SYNTAX      RowStatus
    MAX-ACCESS  read-only
    STATUS      current
    DESCRIPTION   ""
    ::=  { deployProvPathElementEthDefaultsEntry 1 }

deployProvPathElementEthDefaultsTrafficEngineeringType OBJECT-TYPE
    SYNTAX      FspR7CpTEType
    MAX-ACCESS  read-only
    STATUS      current
    DESCRIPTION   ""
    ::=  { deployProvPathElementEthDefaultsEntry 2 }

deployProvPathElementEthDefaultsLifIp OBJECT-TYPE
    SYNTAX      IpAddress
    MAX-ACCESS  read-only
    STATUS      current
    DESCRIPTION   ""
    ::=  { deployProvPathElementEthDefaultsEntry 3 }

deployProvPathElementEthDefaultsNodeIp OBJECT-TYPE
    SYNTAX      IpAddress
    MAX-ACCESS  read-only
    STATUS      current
    DESCRIPTION   ""
    ::=  { deployProvPathElementEthDefaultsEntry 4 }

deployProvPathElementEthDefaultsTid OBJECT-TYPE
    SYNTAX      SnmpAdminString
    MAX-ACCESS  read-only
    STATUS      current
    DESCRIPTION   ""
    ::=  { deployProvPathElementEthDefaultsEntry 5 }

deployProvPathElementEthDefaultsLogicalInterfaceId OBJECT-TYPE
    SYNTAX      Unsigned32
    MAX-ACCESS  read-only
    STATUS      current
    DESCRIPTION   ""
    ::=  { deployProvPathElementEthDefaultsEntry 6 }

deployProvPathElementEthDefaultsTie OBJECT-TYPE
    SYNTAX      FspR7CpTie
    MAX-ACCESS  read-only
    STATUS      current
    DESCRIPTION   ""
    ::=  { deployProvPathElementEthDefaultsEntry 7 }

deployProvPathElementEthDefaultsUpstreamSvid OBJECT-TYPE
    SYNTAX      Unsigned32
    MAX-ACCESS  read-only
    STATUS      current
    DESCRIPTION   ""
    ::=  { deployProvPathElementEthDefaultsEntry 8 }

deployProvPathElementEthDefaultsDownstreamSvid OBJECT-TYPE
    SYNTAX      Unsigned32
    MAX-ACCESS  read-only
    STATUS      current
    DESCRIPTION   ""
    ::=  { deployProvPathElementEthDefaultsEntry 9 }

deployProvCopyPathEthTable OBJECT-TYPE
    SYNTAX      SEQUENCE OF DeployProvCopyPathEthEntry
    MAX-ACCESS  not-accessible
    STATUS      current
    DESCRIPTION   ""
    ::=  { controlPlaneDeployProv 73 }

deployProvCopyPathEthEntry OBJECT-TYPE
    SYNTAX      DeployProvCopyPathEthEntry
    MAX-ACCESS  not-accessible
    STATUS      current
    DESCRIPTION   ""
    INDEX       {
                  controlPlaneEthEntityIndex
                }
    ::=  { deployProvCopyPathEthTable 1 }

DeployProvCopyPathEthEntry ::=  SEQUENCE
  { deployProvCopyPathEthRowStatus RowStatus,
    deployProvCopyPathEthSourcePathIndex EntityIndex,
    deployProvCopyPathEthPathId SnmpAdminString }

deployProvCopyPathEthRowStatus OBJECT-TYPE
    SYNTAX      RowStatus
    MAX-ACCESS  read-write
    STATUS      current
    DESCRIPTION   ""
    ::=  { deployProvCopyPathEthEntry 1 }

deployProvCopyPathEthSourcePathIndex OBJECT-TYPE
    SYNTAX      EntityIndex
    MAX-ACCESS  read-write
    STATUS      current
    DESCRIPTION   ""
    ::=  { deployProvCopyPathEthEntry 2 }

deployProvCopyPathEthPathId OBJECT-TYPE
    SYNTAX      SnmpAdminString
    MAX-ACCESS  read-write
    STATUS      current
    DESCRIPTION   ""
    ::=  { deployProvCopyPathEthEntry 3 }

deployProvCopyPathEthCapTable OBJECT-TYPE
    SYNTAX      SEQUENCE OF DeployProvCopyPathEthCapEntry
    MAX-ACCESS  not-accessible
    STATUS      current
    DESCRIPTION   ""
    ::=  { controlPlaneDeployProv 74  }

deployProvCopyPathEthCapEntry OBJECT-TYPE
    SYNTAX      DeployProvCopyPathEthCapEntry
    MAX-ACCESS  not-accessible
    STATUS      current
    DESCRIPTION   ""
    INDEX       { controlPlaneEthEntityIndex }
    ::=  { deployProvCopyPathEthCapTable 1 }

DeployProvCopyPathEthCapEntry ::=  SEQUENCE
  { deployProvCopyPathEthCapRowStatus FspR7RowStatusCaps,
    deployProvCopyPathEthCapSourcePathIndex Integer32,
    deployProvCopyPathEthCapPathId Integer32 }

deployProvCopyPathEthCapRowStatus OBJECT-TYPE
    SYNTAX      FspR7RowStatusCaps
    MAX-ACCESS  read-only
    STATUS      current
    DESCRIPTION   ""
    ::=  { deployProvCopyPathEthCapEntry 1 }

deployProvCopyPathEthCapSourcePathIndex OBJECT-TYPE
    SYNTAX      Integer32
    MAX-ACCESS  read-only
    STATUS      current
    DESCRIPTION   ""
    ::=  { deployProvCopyPathEthCapEntry 2 }

deployProvCopyPathEthCapPathId OBJECT-TYPE
    SYNTAX      Integer32
    MAX-ACCESS  read-only
    STATUS      current
    DESCRIPTION   ""
    ::=  { deployProvCopyPathEthCapEntry 3 }

deployProvCopyPathEthDefaultsTable  OBJECT-TYPE
    SYNTAX      SEQUENCE OF DeployProvCopyPathEthDefaultsEntry
    MAX-ACCESS  not-accessible
    STATUS      current
    DESCRIPTION   ""
    ::=  { controlPlaneDeployProv 75  }

deployProvCopyPathEthDefaultsEntry OBJECT-TYPE
    SYNTAX      DeployProvCopyPathEthDefaultsEntry
    MAX-ACCESS  not-accessible
    STATUS      current
    DESCRIPTION   ""
    INDEX       { controlPlaneEthEntityIndex }
    ::=  { deployProvCopyPathEthDefaultsTable 1 }

DeployProvCopyPathEthDefaultsEntry ::=  SEQUENCE
  { deployProvCopyPathEthDefaultsRowStatus RowStatus,
    deployProvCopyPathEthDefaultsSourcePathIndex EntityIndex,
    deployProvCopyPathEthDefaultsPathId SnmpAdminString }

deployProvCopyPathEthDefaultsRowStatus OBJECT-TYPE
    SYNTAX      RowStatus
    MAX-ACCESS  read-only
    STATUS      current
    DESCRIPTION   ""
    ::=  { deployProvCopyPathEthDefaultsEntry 1 }

deployProvCopyPathEthDefaultsSourcePathIndex OBJECT-TYPE
    SYNTAX      EntityIndex
    MAX-ACCESS  read-only
    STATUS      current
    DESCRIPTION   ""
    ::=  { deployProvCopyPathEthDefaultsEntry 2 }

deployProvCopyPathEthDefaultsPathId OBJECT-TYPE
    SYNTAX      SnmpAdminString
    MAX-ACCESS  read-only
    STATUS      current
    DESCRIPTION   ""
    ::=  { deployProvCopyPathEthDefaultsEntry 3 }

deployProvPortBindingTable OBJECT-TYPE
    SYNTAX      SEQUENCE OF DeployProvPortBindingEntry
    MAX-ACCESS  not-accessible
    STATUS      current
    DESCRIPTION   ""
    ::=  { controlPlaneDeployProv 76 }

deployProvPortBindingEntry OBJECT-TYPE
    SYNTAX      DeployProvPortBindingEntry
    MAX-ACCESS  not-accessible
    STATUS      current
    DESCRIPTION   ""
    INDEX       {
                  entityIndex
                }
    ::=  { deployProvPortBindingTable 1 }

DeployProvPortBindingEntry ::=  SEQUENCE
  { deployProvPortBindingRowStatus RowStatus,
    deployProvPortBindingLogicalIfAid EntityIndex,
    deployProvPortBindingLocalTna IpAddress,
    deployProvPortBindingRemotePort Unsigned32,
    deployProvPortBindingRemoteTna IpAddress,
    deployProvPortBindingRemoteTnaMask IpAddress,
    deployProvPortBindingRemoteNodeIp IpAddress,
    deployProvPortBindingRemoteScn IpAddress,
    deployProvPortBindingRemoteScPc IpAddress,
    deployProvPortBindingLayer FspR7PacketsLayer }

deployProvPortBindingRowStatus OBJECT-TYPE
    SYNTAX      RowStatus
    MAX-ACCESS  read-create
    STATUS      current
    DESCRIPTION   ""
    ::=  { deployProvPortBindingEntry 1 }

deployProvPortBindingLogicalIfAid OBJECT-TYPE
    SYNTAX      EntityIndex
    MAX-ACCESS  read-create
    STATUS      current
    DESCRIPTION
        "Logical Interface AID" 
    ::=  { deployProvPortBindingEntry 2 }

deployProvPortBindingLocalTna OBJECT-TYPE
    SYNTAX      IpAddress
    MAX-ACCESS  read-create
    STATUS      current
    DESCRIPTION
        "Port Binding Local Transport Network Assigned Name (OIF Signaling Interface)" 
    ::=  { deployProvPortBindingEntry 3 }

deployProvPortBindingRemotePort OBJECT-TYPE
    SYNTAX      Unsigned32
    MAX-ACCESS  read-create
    STATUS      current
    DESCRIPTION
        "Port Binding Remote Port Identifier (OIF Signaling Interface)" 
    ::=  { deployProvPortBindingEntry 4 }

deployProvPortBindingRemoteTna OBJECT-TYPE
    SYNTAX      IpAddress
    MAX-ACCESS  read-create
    STATUS      current
    DESCRIPTION
        "Port Binding Remote Transport Network Assigned Name (OIF Signaling Interface)" 
    ::=  { deployProvPortBindingEntry 5 }

deployProvPortBindingRemoteTnaMask OBJECT-TYPE
    SYNTAX      IpAddress
    MAX-ACCESS  read-create
    STATUS      current
    DESCRIPTION
        "Port Binding Remote Transport Network Assigned Name Mask (OIF Signaling Interface)" 
    ::=  { deployProvPortBindingEntry 6 }

deployProvPortBindingRemoteNodeIp OBJECT-TYPE
    SYNTAX      IpAddress
    MAX-ACCESS  read-create
    STATUS      current
    DESCRIPTION
        "Port Binding Remote Node IP (OIF Signaling Interface)" 
    ::=  { deployProvPortBindingEntry 7 }

deployProvPortBindingRemoteScn OBJECT-TYPE
    SYNTAX      IpAddress
    MAX-ACCESS  read-create
    STATUS      current
    DESCRIPTION
        "Port Binding Remote Signaling Connection Network Address (OIF Signaling Interface)" 
    ::=  { deployProvPortBindingEntry 8 }

deployProvPortBindingRemoteScPc OBJECT-TYPE
    SYNTAX      IpAddress
    MAX-ACCESS  read-create
    STATUS      current
    DESCRIPTION
        "Port Binding Remote Signaling Controller Protocol Controller Identifier (OIF Signaling Interface)" 
    ::=  { deployProvPortBindingEntry 9 }

deployProvPortBindingLayer OBJECT-TYPE
    SYNTAX      FspR7PacketsLayer
    MAX-ACCESS  read-create
    STATUS      current
    DESCRIPTION
        "Notional Layer of Advertisement on Packets on the LIF" 
    ::=  { deployProvPortBindingEntry 10 }

deployProvPortBindingCapTable OBJECT-TYPE
    SYNTAX      SEQUENCE OF DeployProvPortBindingCapEntry
    MAX-ACCESS  not-accessible
    STATUS      current
    DESCRIPTION   ""
    ::=  { controlPlaneDeployProv 77  }

deployProvPortBindingCapEntry OBJECT-TYPE
    SYNTAX      DeployProvPortBindingCapEntry
    MAX-ACCESS  not-accessible
    STATUS      current
    DESCRIPTION   ""
    INDEX       { entityIndex }
    ::=  { deployProvPortBindingCapTable 1 }

DeployProvPortBindingCapEntry ::=  SEQUENCE
  { deployProvPortBindingCapRowStatus FspR7RowStatusCaps,
    deployProvPortBindingCapLogicalIfAid Integer32,
    deployProvPortBindingCapLocalTna FspR7YesNo,
    deployProvPortBindingCapRemotePort FspR7Unsigned32Caps,
    deployProvPortBindingCapRemoteTna FspR7YesNo,
    deployProvPortBindingCapRemoteTnaMask FspR7YesNo,
    deployProvPortBindingCapRemoteNodeIp FspR7YesNo,
    deployProvPortBindingCapRemoteScn FspR7YesNo,
    deployProvPortBindingCapRemoteScPc FspR7YesNo,
    deployProvPortBindingCapLayer FspR7PacketsLayerCaps }

deployProvPortBindingCapRowStatus OBJECT-TYPE
    SYNTAX      FspR7RowStatusCaps
    MAX-ACCESS  read-only
    STATUS      current
    DESCRIPTION   ""
    ::=  { deployProvPortBindingCapEntry 1 }

deployProvPortBindingCapLogicalIfAid OBJECT-TYPE
    SYNTAX      Integer32
    MAX-ACCESS  read-only
    STATUS      current
    DESCRIPTION
        "Logical Interface AID" 
    ::=  { deployProvPortBindingCapEntry 2 }

deployProvPortBindingCapLocalTna OBJECT-TYPE
    SYNTAX      FspR7YesNo
    MAX-ACCESS  read-only
    STATUS      current
    DESCRIPTION
        "Port Binding Local Transport Network Assigned Name (OIF Signaling Interface)" 
    ::=  { deployProvPortBindingCapEntry 3 }

deployProvPortBindingCapRemotePort OBJECT-TYPE
    SYNTAX      FspR7Unsigned32Caps
    MAX-ACCESS  read-only
    STATUS      current
    DESCRIPTION
        "Port Binding Remote Port Identifier (OIF Signaling Interface)" 
    ::=  { deployProvPortBindingCapEntry 4 }

deployProvPortBindingCapRemoteTna OBJECT-TYPE
    SYNTAX      FspR7YesNo
    MAX-ACCESS  read-only
    STATUS      current
    DESCRIPTION
        "Port Binding Remote Transport Network Assigned Name (OIF Signaling Interface)" 
    ::=  { deployProvPortBindingCapEntry 5 }

deployProvPortBindingCapRemoteTnaMask OBJECT-TYPE
    SYNTAX      FspR7YesNo
    MAX-ACCESS  read-only
    STATUS      current
    DESCRIPTION
        "Port Binding Remote Transport Network Assigned Name Mask (OIF Signaling Interface)" 
    ::=  { deployProvPortBindingCapEntry 6 }

deployProvPortBindingCapRemoteNodeIp OBJECT-TYPE
    SYNTAX      FspR7YesNo
    MAX-ACCESS  read-only
    STATUS      current
    DESCRIPTION
        "Port Binding Remote Node IP (OIF Signaling Interface)" 
    ::=  { deployProvPortBindingCapEntry 7 }

deployProvPortBindingCapRemoteScn OBJECT-TYPE
    SYNTAX      FspR7YesNo
    MAX-ACCESS  read-only
    STATUS      current
    DESCRIPTION
        "Port Binding Remote Signaling Connection Network Address (OIF Signaling Interface)" 
    ::=  { deployProvPortBindingCapEntry 8 }

deployProvPortBindingCapRemoteScPc OBJECT-TYPE
    SYNTAX      FspR7YesNo
    MAX-ACCESS  read-only
    STATUS      current
    DESCRIPTION
        "Port Binding Remote Signaling Controller Protocol Controller Identifier (OIF Signaling Interface)" 
    ::=  { deployProvPortBindingCapEntry 9 }

deployProvPortBindingCapLayer OBJECT-TYPE
    SYNTAX      FspR7PacketsLayerCaps
    MAX-ACCESS  read-only
    STATUS      current
    DESCRIPTION
        "Notional Layer of Advertisement on Packets on the LIF" 
    ::=  { deployProvPortBindingCapEntry 10 }

deployProvPortBindingDefaultsTable  OBJECT-TYPE
    SYNTAX      SEQUENCE OF DeployProvPortBindingDefaultsEntry
    MAX-ACCESS  not-accessible
    STATUS      current
    DESCRIPTION   ""
    ::=  { controlPlaneDeployProv 78  }

deployProvPortBindingDefaultsEntry OBJECT-TYPE
    SYNTAX      DeployProvPortBindingDefaultsEntry
    MAX-ACCESS  not-accessible
    STATUS      current
    DESCRIPTION   ""
    INDEX       { entityIndex }
    ::=  { deployProvPortBindingDefaultsTable 1 }

DeployProvPortBindingDefaultsEntry ::=  SEQUENCE
  { deployProvPortBindingDefaultsRowStatus RowStatus,
    deployProvPortBindingDefaultsLogicalIfAid EntityIndex,
    deployProvPortBindingDefaultsLocalTna IpAddress,
    deployProvPortBindingDefaultsRemotePort Unsigned32,
    deployProvPortBindingDefaultsRemoteTna IpAddress,
    deployProvPortBindingDefaultsRemoteTnaMask IpAddress,
    deployProvPortBindingDefaultsRemoteNodeIp IpAddress,
    deployProvPortBindingDefaultsRemoteScn IpAddress,
    deployProvPortBindingDefaultsRemoteScPc IpAddress,
    deployProvPortBindingDefaultsLayer FspR7PacketsLayer }

deployProvPortBindingDefaultsRowStatus OBJECT-TYPE
    SYNTAX      RowStatus
    MAX-ACCESS  read-only
    STATUS      current
    DESCRIPTION   ""
    ::=  { deployProvPortBindingDefaultsEntry 1 }

deployProvPortBindingDefaultsLogicalIfAid OBJECT-TYPE
    SYNTAX      EntityIndex
    MAX-ACCESS  read-only
    STATUS      current
    DESCRIPTION
        "Logical Interface AID" 
    ::=  { deployProvPortBindingDefaultsEntry 2 }

deployProvPortBindingDefaultsLocalTna OBJECT-TYPE
    SYNTAX      IpAddress
    MAX-ACCESS  read-only
    STATUS      current
    DESCRIPTION
        "Port Binding Local Transport Network Assigned Name (OIF Signaling Interface)" 
    ::=  { deployProvPortBindingDefaultsEntry 3 }

deployProvPortBindingDefaultsRemotePort OBJECT-TYPE
    SYNTAX      Unsigned32
    MAX-ACCESS  read-only
    STATUS      current
    DESCRIPTION
        "Port Binding Remote Port Identifier (OIF Signaling Interface)" 
    ::=  { deployProvPortBindingDefaultsEntry 4 }

deployProvPortBindingDefaultsRemoteTna OBJECT-TYPE
    SYNTAX      IpAddress
    MAX-ACCESS  read-only
    STATUS      current
    DESCRIPTION
        "Port Binding Remote Transport Network Assigned Name (OIF Signaling Interface)" 
    ::=  { deployProvPortBindingDefaultsEntry 5 }

deployProvPortBindingDefaultsRemoteTnaMask OBJECT-TYPE
    SYNTAX      IpAddress
    MAX-ACCESS  read-only
    STATUS      current
    DESCRIPTION
        "Port Binding Remote Transport Network Assigned Name Mask (OIF Signaling Interface)" 
    ::=  { deployProvPortBindingDefaultsEntry 6 }

deployProvPortBindingDefaultsRemoteNodeIp OBJECT-TYPE
    SYNTAX      IpAddress
    MAX-ACCESS  read-only
    STATUS      current
    DESCRIPTION
        "Port Binding Remote Node IP (OIF Signaling Interface)" 
    ::=  { deployProvPortBindingDefaultsEntry 7 }

deployProvPortBindingDefaultsRemoteScn OBJECT-TYPE
    SYNTAX      IpAddress
    MAX-ACCESS  read-only
    STATUS      current
    DESCRIPTION
        "Port Binding Remote Signaling Connection Network Address (OIF Signaling Interface)" 
    ::=  { deployProvPortBindingDefaultsEntry 8 }

deployProvPortBindingDefaultsRemoteScPc OBJECT-TYPE
    SYNTAX      IpAddress
    MAX-ACCESS  read-only
    STATUS      current
    DESCRIPTION
        "Port Binding Remote Signaling Controller Protocol Controller Identifier (OIF Signaling Interface)" 
    ::=  { deployProvPortBindingDefaultsEntry 9 }

deployProvPortBindingDefaultsLayer OBJECT-TYPE
    SYNTAX      FspR7PacketsLayer
    MAX-ACCESS  read-only
    STATUS      current
    DESCRIPTION
        "Notional Layer of Advertisement on Packets on the LIF" 
    ::=  { deployProvPortBindingDefaultsEntry 10 }

deployProvPortBindingLifAidCapsTable OBJECT-TYPE
    SYNTAX      SEQUENCE OF DeployProvPortBindingLifAidCapsEntry
    MAX-ACCESS  not-accessible
    STATUS      current
    DESCRIPTION   "This table is used to get capabilities for LIFAID parameter. Regular
         cap tables including LogicalIfAid parameter show the number of supported entities (LIF-CP) on a given PB.
         Value 0 in regular cap tables means 'no capabilities'."
    ::=  { controlPlaneDeployProv 79 }

deployProvPortBindingLifAidCapsEntry OBJECT-TYPE
    SYNTAX      DeployProvPortBindingLifAidCapsEntry
    MAX-ACCESS  not-accessible
    STATUS      current
    DESCRIPTION   ""
    INDEX       {
                  controlPlaneWdmEntityIndex,
                  deployProvPortBindingLifAidCapsIndex
                }
    ::=  { deployProvPortBindingLifAidCapsTable 1 }

DeployProvPortBindingLifAidCapsEntry ::=  SEQUENCE
  { deployProvPortBindingLifAidCapsIndex EntityIndex }

deployProvPortBindingLifAidCapsIndex OBJECT-TYPE
    SYNTAX      EntityIndex
    MAX-ACCESS  read-only
    STATUS      current
    DESCRIPTION
        "Logical Interface AID" 
    ::=  { deployProvPortBindingLifAidCapsEntry 1 }

deployProvControlPlaneOtnTable OBJECT-TYPE
    SYNTAX      SEQUENCE OF DeployProvControlPlaneOtnEntry
    MAX-ACCESS  not-accessible
    STATUS      current
    DESCRIPTION   ""
    ::=  { controlPlaneDeployProv 100 }

deployProvControlPlaneOtnEntry OBJECT-TYPE
    SYNTAX      DeployProvControlPlaneOtnEntry
    MAX-ACCESS  not-accessible
    STATUS      current
    DESCRIPTION   ""
    INDEX       {
                  controlPlaneOtnEntityIndex
                }
    ::=  { deployProvControlPlaneOtnTable 1 }

DeployProvControlPlaneOtnEntry ::=  SEQUENCE
  { deployProvControlPlaneOtnRowStatus RowStatus,
    deployProvControlPlaneOtnCtmConfigFlag Unsigned32,
    deployProvControlPlaneOtnCtmTraceDetail Unsigned32,
    deployProvControlPlaneOtnCtmSetupTimeout Unsigned32,
    deployProvControlPlaneOtnCtmShutdownTimeout Unsigned32,
    deployProvControlPlaneOtnCtmRetryWait Unsigned32,
    deployProvControlPlaneOtnCtmRetryWaitMultiplier Unsigned32,
    deployProvControlPlaneOtnCtmMaximumRetryWait Unsigned32,
    deployProvControlPlaneOtnCtmMaximumRetryNumber Unsigned32,
    deployProvControlPlaneOtnRaConfigFlag Unsigned32,
    deployProvControlPlaneOtnRaTraceDetail Unsigned32,
    deployProvControlPlaneOtnRaAlarmActivationTime Unsigned32,
    deployProvControlPlaneOtnCmConfigFlag Unsigned32,
    deployProvControlPlaneOtnCmTraceDetail Unsigned32,
    deployProvControlPlaneOtnCmAlarmActivationTime Unsigned32,
    deployProvControlPlaneOtnCmFisFrsTimeout Unsigned32,
    deployProvControlPlaneOtnCmCrankBackTimeout Unsigned32,
    deployProvControlPlaneOtnCdbConfigFlag Unsigned32,
    deployProvControlPlaneOtnCdbDetail Unsigned32,
    deployProvControlPlaneOtnCdbMaxSize Unsigned32,
    deployProvControlPlaneOtnRsvpMaxExpRestartTime Counter64String,
    deployProvControlPlaneOtnRsvpMaxExpRecoveryTime Unsigned32,
    deployProvControlPlaneOtnRsvpConfigFlag Unsigned32,
    deployProvControlPlaneOtnTedbConfigFlag Unsigned32,
    deployProvControlPlaneOtnTedbTraceDetail Unsigned32,
    deployProvControlPlaneOtnTedbMaxSize Unsigned32,
    deployProvControlPlaneOtnTedbRouterId IpAddress,
    deployProvControlPlaneOtnTedbMinAdvertWait Unsigned32,
    deployProvControlPlaneOtnNaasConfigFlag Unsigned32,
    deployProvControlPlaneOtnNaasTraceDetail Unsigned32,
    deployProvControlPlaneOtnNaasMaxSize Unsigned32,
    deployProvControlPlaneOtnNaasAdvertWait Unsigned32,
    deployProvControlPlaneOtnPcConfigFlag Unsigned32,
    deployProvControlPlaneOtnPcTraceDetail Unsigned32,
    deployProvControlPlaneOtnCdConfigFlag Unsigned32,
    deployProvControlPlaneOtnCdTraceDetail Unsigned32,
    deployProvControlPlaneOtnCdResyncTimeout Unsigned32,
    deployProvControlPlaneOtnRmConfigFlag Unsigned32,
    deployProvControlPlaneOtnRmTraceDetail Unsigned32,
    deployProvControlPlaneOtnRmTraceTarget Unsigned32,
    deployProvControlPlaneOtnNodeNameSyntax FspR7NodeId }

deployProvControlPlaneOtnRowStatus OBJECT-TYPE
    SYNTAX      RowStatus
    MAX-ACCESS  read-write
    STATUS      current
    DESCRIPTION   ""
    ::=  { deployProvControlPlaneOtnEntry 1 }

deployProvControlPlaneOtnCtmConfigFlag OBJECT-TYPE
    SYNTAX      Unsigned32
    MAX-ACCESS  read-write
    STATUS      current
    DESCRIPTION   "Label Switched Path Edge Component' Configuration Bitfield"
    ::=  { deployProvControlPlaneOtnEntry 2 }

deployProvControlPlaneOtnCtmTraceDetail OBJECT-TYPE
    SYNTAX      Unsigned32
    MAX-ACCESS  read-write
    STATUS      current
    DESCRIPTION   "Label Switched Path Edge Component' Trace Detail"
    ::=  { deployProvControlPlaneOtnEntry 3 }

deployProvControlPlaneOtnCtmSetupTimeout OBJECT-TYPE
    SYNTAX      Unsigned32 
    UNITS       "s"
    MAX-ACCESS  read-write
    STATUS      current
    DESCRIPTION   "Label Switched Path Edge Component' Set-Up Timeout"
    ::=  { deployProvControlPlaneOtnEntry 4 }

deployProvControlPlaneOtnCtmShutdownTimeout OBJECT-TYPE
    SYNTAX      Unsigned32 
    UNITS       "s"
    MAX-ACCESS  read-write
    STATUS      current
    DESCRIPTION   "Label Switched Path Edge Component' Shut-Down Timeout"
    ::=  { deployProvControlPlaneOtnEntry 5 }

deployProvControlPlaneOtnCtmRetryWait OBJECT-TYPE
    SYNTAX      Unsigned32 
    UNITS       "s"
    MAX-ACCESS  read-write
    STATUS      current
    DESCRIPTION   "Label Switched Path Edge Component' Initialization Retry Wait"
    ::=  { deployProvControlPlaneOtnEntry 6 }

deployProvControlPlaneOtnCtmRetryWaitMultiplier OBJECT-TYPE
    SYNTAX      Unsigned32
    MAX-ACCESS  read-write
    STATUS      current
    DESCRIPTION   "Label Switched Path Edge Component' Initialization Retry Wait Multiplier"
    ::=  { deployProvControlPlaneOtnEntry 7 }

deployProvControlPlaneOtnCtmMaximumRetryWait OBJECT-TYPE
    SYNTAX      Unsigned32 
    UNITS       "s"
    MAX-ACCESS  read-write
    STATUS      current
    DESCRIPTION   "Label Switched Path Edge Component' Initialization Maximum Retry Wait"
    ::=  { deployProvControlPlaneOtnEntry 8 }

deployProvControlPlaneOtnCtmMaximumRetryNumber OBJECT-TYPE
    SYNTAX      Unsigned32
    MAX-ACCESS  read-write
    STATUS      current
    DESCRIPTION   "Label Switched Path Edge Component' Initialization Maximum Retry Number"
    ::=  { deployProvControlPlaneOtnEntry 9 }

deployProvControlPlaneOtnRaConfigFlag OBJECT-TYPE
    SYNTAX      Unsigned32
    MAX-ACCESS  read-write
    STATUS      current
    DESCRIPTION   "Resource Allocator Component' Configuration Bitfield"
    ::=  { deployProvControlPlaneOtnEntry 10 }

deployProvControlPlaneOtnRaTraceDetail OBJECT-TYPE
    SYNTAX      Unsigned32
    MAX-ACCESS  read-write
    STATUS      current
    DESCRIPTION   "Resource Allocator Component' Trace Detail"
    ::=  { deployProvControlPlaneOtnEntry 11 }

deployProvControlPlaneOtnRaAlarmActivationTime OBJECT-TYPE
    SYNTAX      Unsigned32 
    UNITS       "s"
    MAX-ACCESS  read-write
    STATUS      current
    DESCRIPTION   "Resource Allocator Component' Alarm Activation Time"
    ::=  { deployProvControlPlaneOtnEntry 12 }

deployProvControlPlaneOtnCmConfigFlag OBJECT-TYPE
    SYNTAX      Unsigned32
    MAX-ACCESS  read-write
    STATUS      current
    DESCRIPTION   "GMPLS Tunnel Manager Component' Configuration Bitfield"
    ::=  { deployProvControlPlaneOtnEntry 13 }

deployProvControlPlaneOtnCmTraceDetail OBJECT-TYPE
    SYNTAX      Unsigned32
    MAX-ACCESS  read-write
    STATUS      current
    DESCRIPTION   "GMPLS Tunnel Manager Component' Trace Detail"
    ::=  { deployProvControlPlaneOtnEntry 14 }

deployProvControlPlaneOtnCmAlarmActivationTime OBJECT-TYPE
    SYNTAX      Unsigned32 
    UNITS       "s"
    MAX-ACCESS  read-write
    STATUS      current
    DESCRIPTION   "GMPLS Tunnel Manager Component' Alarm Activation Time"
    ::=  { deployProvControlPlaneOtnEntry 15 }

deployProvControlPlaneOtnCmFisFrsTimeout OBJECT-TYPE
    SYNTAX      Unsigned32 
    UNITS       "s"
    MAX-ACCESS  read-write
    STATUS      current
    DESCRIPTION   "GMPLS Tunnel Manager Component' FIS-FRS Timeout"
    ::=  { deployProvControlPlaneOtnEntry 16 }

deployProvControlPlaneOtnCmCrankBackTimeout OBJECT-TYPE
    SYNTAX      Unsigned32 
    UNITS       "s"
    MAX-ACCESS  read-write
    STATUS      current
    DESCRIPTION   "GMPLS Tunnel Manager Component' Crank-Back Timeout"
    ::=  { deployProvControlPlaneOtnEntry 17 }

deployProvControlPlaneOtnCdbConfigFlag OBJECT-TYPE
    SYNTAX      Unsigned32
    MAX-ACCESS  read-write
    STATUS      current
    DESCRIPTION   "Label Swithed Path Database Component Configuration Bitfield"
    ::=  { deployProvControlPlaneOtnEntry 18 }

deployProvControlPlaneOtnCdbDetail OBJECT-TYPE
    SYNTAX      Unsigned32
    MAX-ACCESS  read-write
    STATUS      current
    DESCRIPTION   "Label Swithed Path Database Component Trace Detail"
    ::=  { deployProvControlPlaneOtnEntry 19 }

deployProvControlPlaneOtnCdbMaxSize OBJECT-TYPE
    SYNTAX      Unsigned32
    MAX-ACCESS  read-write
    STATUS      current
    DESCRIPTION   "Label Swithed Path Database Component Maximum Size; 0 implies no limit"
    ::=  { deployProvControlPlaneOtnEntry 20 }

deployProvControlPlaneOtnRsvpMaxExpRestartTime OBJECT-TYPE
    SYNTAX      Counter64String 
    UNITS       "ms"
    MAX-ACCESS  read-write
    STATUS      current
    DESCRIPTION   "Maximum Expected Resource Reservation Protocol Component' Restart Time"
    ::=  { deployProvControlPlaneOtnEntry 21 }

deployProvControlPlaneOtnRsvpMaxExpRecoveryTime OBJECT-TYPE
    SYNTAX      Unsigned32 
    UNITS       "ms"
    MAX-ACCESS  read-write
    STATUS      current
    DESCRIPTION   "Maximum Expected Resource Reservation Protocol Component' Recovery Time"
    ::=  { deployProvControlPlaneOtnEntry 22 }

deployProvControlPlaneOtnRsvpConfigFlag OBJECT-TYPE
    SYNTAX      Unsigned32
    MAX-ACCESS  read-write
    STATUS      current
    DESCRIPTION   "Resource Reservation Protocol Component' Configuration Bitfield"
    ::=  { deployProvControlPlaneOtnEntry 23 }

deployProvControlPlaneOtnTedbConfigFlag OBJECT-TYPE
    SYNTAX      Unsigned32
    MAX-ACCESS  read-write
    STATUS      current
    DESCRIPTION   "Traffic Engineering Component' Configuration Bitfield"
    ::=  { deployProvControlPlaneOtnEntry 24 }

deployProvControlPlaneOtnTedbTraceDetail OBJECT-TYPE
    SYNTAX      Unsigned32
    MAX-ACCESS  read-write
    STATUS      current
    DESCRIPTION   "Traffic Engineering Component' Trace Detail"
    ::=  { deployProvControlPlaneOtnEntry 25 }

deployProvControlPlaneOtnTedbMaxSize OBJECT-TYPE
    SYNTAX      Unsigned32
    MAX-ACCESS  read-write
    STATUS      current
    DESCRIPTION   "Traffic Engineering Component' Maximum Size"
    ::=  { deployProvControlPlaneOtnEntry 26 }

deployProvControlPlaneOtnTedbRouterId OBJECT-TYPE
    SYNTAX      IpAddress
    MAX-ACCESS  read-write
    STATUS      current
    DESCRIPTION   "Traffic Engineering Component' Router ID"
    ::=  { deployProvControlPlaneOtnEntry 27 }

deployProvControlPlaneOtnTedbMinAdvertWait OBJECT-TYPE
    SYNTAX      Unsigned32 
    UNITS       "s"
    MAX-ACCESS  read-write
    STATUS      current
    DESCRIPTION   "Traffic Engineering Component' Minimum Advertisement Wait"
    ::=  { deployProvControlPlaneOtnEntry 28 }

deployProvControlPlaneOtnNaasConfigFlag OBJECT-TYPE
    SYNTAX      Unsigned32
    MAX-ACCESS  read-write
    STATUS      current
    DESCRIPTION   "Node Attribute Advertising Service Database Component' Configuration Bitfield"
    ::=  { deployProvControlPlaneOtnEntry 29 }

deployProvControlPlaneOtnNaasTraceDetail OBJECT-TYPE
    SYNTAX      Unsigned32
    MAX-ACCESS  read-write
    STATUS      current
    DESCRIPTION   "Node Attribute Advertising Service Database Component' Trace Detail"
    ::=  { deployProvControlPlaneOtnEntry 30 }

deployProvControlPlaneOtnNaasMaxSize OBJECT-TYPE
    SYNTAX      Unsigned32
    MAX-ACCESS  read-write
    STATUS      current
    DESCRIPTION   "Node Attribute Advertising Service Database Component' Maximum Size"
    ::=  { deployProvControlPlaneOtnEntry 31 }

deployProvControlPlaneOtnNaasAdvertWait OBJECT-TYPE
    SYNTAX      Unsigned32 
    UNITS       "s"
    MAX-ACCESS  read-write
    STATUS      current
    DESCRIPTION   "Node Attribute Advertising Service Database Component' Advertisement Wait"
    ::=  { deployProvControlPlaneOtnEntry 32 }

deployProvControlPlaneOtnPcConfigFlag OBJECT-TYPE
    SYNTAX      Unsigned32
    MAX-ACCESS  read-write
    STATUS      current
    DESCRIPTION   "Path Computation Component' Configuration Bitfield"
    ::=  { deployProvControlPlaneOtnEntry 33 }

deployProvControlPlaneOtnPcTraceDetail OBJECT-TYPE
    SYNTAX      Unsigned32
    MAX-ACCESS  read-write
    STATUS      current
    DESCRIPTION   "Path Computation Component' Trace Detail"
    ::=  { deployProvControlPlaneOtnEntry 34 }

deployProvControlPlaneOtnCdConfigFlag OBJECT-TYPE
    SYNTAX      Unsigned32
    MAX-ACCESS  read-write
    STATUS      current
    DESCRIPTION   "Configuration Data Component' Configuration Bitfield"
    ::=  { deployProvControlPlaneOtnEntry 35 }

deployProvControlPlaneOtnCdTraceDetail OBJECT-TYPE
    SYNTAX      Unsigned32
    MAX-ACCESS  read-write
    STATUS      current
    DESCRIPTION   "Configuration Data Component' Trace Detail"
    ::=  { deployProvControlPlaneOtnEntry 36 }

deployProvControlPlaneOtnCdResyncTimeout OBJECT-TYPE
    SYNTAX      Unsigned32
    MAX-ACCESS  read-write
    STATUS      current
    DESCRIPTION   "Configuration Data Component' Resync Timeout"
    ::=  { deployProvControlPlaneOtnEntry 37 }

deployProvControlPlaneOtnRmConfigFlag OBJECT-TYPE
    SYNTAX      Unsigned32
    MAX-ACCESS  read-write
    STATUS      current
    DESCRIPTION   "Resource Management Component' Configuration Bitfield"
    ::=  { deployProvControlPlaneOtnEntry 38 }

deployProvControlPlaneOtnRmTraceDetail OBJECT-TYPE
    SYNTAX      Unsigned32
    MAX-ACCESS  read-write
    STATUS      current
    DESCRIPTION   "Resource Management Component' Trace Detail"
    ::=  { deployProvControlPlaneOtnEntry 39 }

deployProvControlPlaneOtnRmTraceTarget OBJECT-TYPE
    SYNTAX      Unsigned32
    MAX-ACCESS  read-write
    STATUS      current
    DESCRIPTION   "Resource Management Component' Trace Target"
    ::=  { deployProvControlPlaneOtnEntry 40 }

deployProvControlPlaneOtnNodeNameSyntax OBJECT-TYPE
    SYNTAX      FspR7NodeId
    MAX-ACCESS  read-write
    STATUS      deprecated
    DESCRIPTION   "Node Name Syntax"
    ::=  { deployProvControlPlaneOtnEntry 41 }

deployProvControlPlaneOtnCapTable OBJECT-TYPE
    SYNTAX      SEQUENCE OF DeployProvControlPlaneOtnCapEntry
    MAX-ACCESS  not-accessible
    STATUS      current
    DESCRIPTION   ""
    ::=  { controlPlaneDeployProv 101  }

deployProvControlPlaneOtnCapEntry OBJECT-TYPE
    SYNTAX      DeployProvControlPlaneOtnCapEntry
    MAX-ACCESS  not-accessible
    STATUS      current
    DESCRIPTION   ""
    INDEX       { controlPlaneOtnEntityIndex }
    ::=  { deployProvControlPlaneOtnCapTable 1 }

DeployProvControlPlaneOtnCapEntry ::=  SEQUENCE
  { deployProvControlPlaneOtnCapRowStatus FspR7RowStatusCaps,
    deployProvControlPlaneOtnCapCtmConfigFlag FspR7Unsigned32Caps,
    deployProvControlPlaneOtnCapCtmTraceDetail FspR7Unsigned32Caps,
    deployProvControlPlaneOtnCapCtmSetupTimeout FspR7Unsigned32Caps,
    deployProvControlPlaneOtnCapCtmShutdownTimeout FspR7Unsigned32Caps,
    deployProvControlPlaneOtnCapCtmRetryWait FspR7Unsigned32Caps,
    deployProvControlPlaneOtnCapCtmRetryWaitMultiplier FspR7Unsigned32Caps,
    deployProvControlPlaneOtnCapCtmMaximumRetryWait FspR7Unsigned32Caps,
    deployProvControlPlaneOtnCapCtmMaximumRetryNumber FspR7Unsigned32Caps,
    deployProvControlPlaneOtnCapRaConfigFlag FspR7Unsigned32Caps,
    deployProvControlPlaneOtnCapRaTraceDetail FspR7Unsigned32Caps,
    deployProvControlPlaneOtnCapRaAlarmActivationTime FspR7Unsigned32Caps,
    deployProvControlPlaneOtnCapCmConfigFlag FspR7Unsigned32Caps,
    deployProvControlPlaneOtnCapCmTraceDetail FspR7Unsigned32Caps,
    deployProvControlPlaneOtnCapCmAlarmActivationTime FspR7Unsigned32Caps,
    deployProvControlPlaneOtnCapCmFisFrsTimeout FspR7Unsigned32Caps,
    deployProvControlPlaneOtnCapCmCrankBackTimeout FspR7Unsigned32Caps,
    deployProvControlPlaneOtnCapCdbConfigFlag FspR7Unsigned32Caps,
    deployProvControlPlaneOtnCapCdbDetail FspR7Unsigned32Caps,
    deployProvControlPlaneOtnCapCdbMaxSize FspR7Unsigned32Caps,
    deployProvControlPlaneOtnCapRsvpMaxExpRestartTime Counter64StringCaps,
    deployProvControlPlaneOtnCapRsvpMaxExpRecoveryTime FspR7Unsigned32Caps,
    deployProvControlPlaneOtnCapRsvpConfigFlag FspR7Unsigned32Caps,
    deployProvControlPlaneOtnCapTedbConfigFlag FspR7Unsigned32Caps,
    deployProvControlPlaneOtnCapTedbTraceDetail FspR7Unsigned32Caps,
    deployProvControlPlaneOtnCapTedbMaxSize FspR7Unsigned32Caps,
    deployProvControlPlaneOtnCapTedbRouterId FspR7YesNo,
    deployProvControlPlaneOtnCapTedbMinAdvertWait FspR7Unsigned32Caps,
    deployProvControlPlaneOtnCapNaasConfigFlag FspR7Unsigned32Caps,
    deployProvControlPlaneOtnCapNaasTraceDetail FspR7Unsigned32Caps,
    deployProvControlPlaneOtnCapNaasMaxSize FspR7Unsigned32Caps,
    deployProvControlPlaneOtnCapNaasAdvertWait FspR7Unsigned32Caps,
    deployProvControlPlaneOtnCapPcConfigFlag FspR7Unsigned32Caps,
    deployProvControlPlaneOtnCapPcTraceDetail FspR7Unsigned32Caps,
    deployProvControlPlaneOtnCapCdConfigFlag FspR7Unsigned32Caps,
    deployProvControlPlaneOtnCapCdTraceDetail FspR7Unsigned32Caps,
    deployProvControlPlaneOtnCapCdResyncTimeout FspR7Unsigned32Caps,
    deployProvControlPlaneOtnCapRmConfigFlag FspR7Unsigned32Caps,
    deployProvControlPlaneOtnCapRmTraceDetail FspR7Unsigned32Caps,
    deployProvControlPlaneOtnCapRmTraceTarget FspR7Unsigned32Caps,
    deployProvControlPlaneOtnCapNodeNameSyntax FspR7NodeIdCaps }

deployProvControlPlaneOtnCapRowStatus OBJECT-TYPE
    SYNTAX      FspR7RowStatusCaps
    MAX-ACCESS  read-only
    STATUS      current
    DESCRIPTION   ""
    ::=  { deployProvControlPlaneOtnCapEntry 1 }

deployProvControlPlaneOtnCapCtmConfigFlag OBJECT-TYPE
    SYNTAX      FspR7Unsigned32Caps
    MAX-ACCESS  read-only
    STATUS      current
    DESCRIPTION   "Label Switched Path Edge Component' Configuration Bitfield"
    ::=  { deployProvControlPlaneOtnCapEntry 2 }

deployProvControlPlaneOtnCapCtmTraceDetail OBJECT-TYPE
    SYNTAX      FspR7Unsigned32Caps
    MAX-ACCESS  read-only
    STATUS      current
    DESCRIPTION   "Label Switched Path Edge Component' Trace Detail"
    ::=  { deployProvControlPlaneOtnCapEntry 3 }

deployProvControlPlaneOtnCapCtmSetupTimeout OBJECT-TYPE
    SYNTAX      FspR7Unsigned32Caps
    UNITS       "s"
    MAX-ACCESS  read-only
    STATUS      current
    DESCRIPTION   "Label Switched Path Edge Component' Set-Up Timeout"
    ::=  { deployProvControlPlaneOtnCapEntry 4 }

deployProvControlPlaneOtnCapCtmShutdownTimeout OBJECT-TYPE
    SYNTAX      FspR7Unsigned32Caps
    UNITS       "s"
    MAX-ACCESS  read-only
    STATUS      current
    DESCRIPTION   "Label Switched Path Edge Component' Shut-Down Timeout"
    ::=  { deployProvControlPlaneOtnCapEntry 5 }

deployProvControlPlaneOtnCapCtmRetryWait OBJECT-TYPE
    SYNTAX      FspR7Unsigned32Caps
    UNITS       "s"
    MAX-ACCESS  read-only
    STATUS      current
    DESCRIPTION   "Label Switched Path Edge Component' Initialization Retry Wait"
    ::=  { deployProvControlPlaneOtnCapEntry 6 }

deployProvControlPlaneOtnCapCtmRetryWaitMultiplier OBJECT-TYPE
    SYNTAX      FspR7Unsigned32Caps
    MAX-ACCESS  read-only
    STATUS      current
    DESCRIPTION   "Label Switched Path Edge Component' Initialization Retry Wait Multiplier"
    ::=  { deployProvControlPlaneOtnCapEntry 7 }

deployProvControlPlaneOtnCapCtmMaximumRetryWait OBJECT-TYPE
    SYNTAX      FspR7Unsigned32Caps
    UNITS       "s"
    MAX-ACCESS  read-only
    STATUS      current
    DESCRIPTION   "Label Switched Path Edge Component' Initialization Maximum Retry Wait"
    ::=  { deployProvControlPlaneOtnCapEntry 8 }

deployProvControlPlaneOtnCapCtmMaximumRetryNumber OBJECT-TYPE
    SYNTAX      FspR7Unsigned32Caps
    MAX-ACCESS  read-only
    STATUS      current
    DESCRIPTION   "Label Switched Path Edge Component' Initialization Maximum Retry Number"
    ::=  { deployProvControlPlaneOtnCapEntry 9 }

deployProvControlPlaneOtnCapRaConfigFlag OBJECT-TYPE
    SYNTAX      FspR7Unsigned32Caps
    MAX-ACCESS  read-only
    STATUS      current
    DESCRIPTION   "Resource Allocator Component' Configuration Bitfield"
    ::=  { deployProvControlPlaneOtnCapEntry 10 }

deployProvControlPlaneOtnCapRaTraceDetail OBJECT-TYPE
    SYNTAX      FspR7Unsigned32Caps
    MAX-ACCESS  read-only
    STATUS      current
    DESCRIPTION   "Resource Allocator Component' Trace Detail"
    ::=  { deployProvControlPlaneOtnCapEntry 11 }

deployProvControlPlaneOtnCapRaAlarmActivationTime OBJECT-TYPE
    SYNTAX      FspR7Unsigned32Caps
    UNITS       "s"
    MAX-ACCESS  read-only
    STATUS      current
    DESCRIPTION   "Resource Allocator Component' Alarm Activation Time"
    ::=  { deployProvControlPlaneOtnCapEntry 12 }

deployProvControlPlaneOtnCapCmConfigFlag OBJECT-TYPE
    SYNTAX      FspR7Unsigned32Caps
    MAX-ACCESS  read-only
    STATUS      current
    DESCRIPTION   "GMPLS Tunnel Manager Component' Configuration Bitfield"
    ::=  { deployProvControlPlaneOtnCapEntry 13 }

deployProvControlPlaneOtnCapCmTraceDetail OBJECT-TYPE
    SYNTAX      FspR7Unsigned32Caps
    MAX-ACCESS  read-only
    STATUS      current
    DESCRIPTION   "GMPLS Tunnel Manager Component' Trace Detail"
    ::=  { deployProvControlPlaneOtnCapEntry 14 }

deployProvControlPlaneOtnCapCmAlarmActivationTime OBJECT-TYPE
    SYNTAX      FspR7Unsigned32Caps
    UNITS       "s"
    MAX-ACCESS  read-only
    STATUS      current
    DESCRIPTION   "GMPLS Tunnel Manager Component' Alarm Activation Time"
    ::=  { deployProvControlPlaneOtnCapEntry 15 }

deployProvControlPlaneOtnCapCmFisFrsTimeout OBJECT-TYPE
    SYNTAX      FspR7Unsigned32Caps
    UNITS       "s"
    MAX-ACCESS  read-only
    STATUS      current
    DESCRIPTION   "GMPLS Tunnel Manager Component' FIS-FRS Timeout"
    ::=  { deployProvControlPlaneOtnCapEntry 16 }

deployProvControlPlaneOtnCapCmCrankBackTimeout OBJECT-TYPE
    SYNTAX      FspR7Unsigned32Caps
    UNITS       "s"
    MAX-ACCESS  read-only
    STATUS      current
    DESCRIPTION   "GMPLS Tunnel Manager Component' Crank-Back Timeout"
    ::=  { deployProvControlPlaneOtnCapEntry 17 }

deployProvControlPlaneOtnCapCdbConfigFlag OBJECT-TYPE
    SYNTAX      FspR7Unsigned32Caps
    MAX-ACCESS  read-only
    STATUS      current
    DESCRIPTION   "Label Swithed Path Database Component Configuration Bitfield"
    ::=  { deployProvControlPlaneOtnCapEntry 18 }

deployProvControlPlaneOtnCapCdbDetail OBJECT-TYPE
    SYNTAX      FspR7Unsigned32Caps
    MAX-ACCESS  read-only
    STATUS      current
    DESCRIPTION   "Label Swithed Path Database Component Trace Detail"
    ::=  { deployProvControlPlaneOtnCapEntry 19 }

deployProvControlPlaneOtnCapCdbMaxSize OBJECT-TYPE
    SYNTAX      FspR7Unsigned32Caps
    MAX-ACCESS  read-only
    STATUS      current
    DESCRIPTION   "Label Swithed Path Database Component Maximum Size; 0 implies no limit"
    ::=  { deployProvControlPlaneOtnCapEntry 20 }

deployProvControlPlaneOtnCapRsvpMaxExpRestartTime OBJECT-TYPE
    SYNTAX      Counter64StringCaps
    UNITS       "ms"
    MAX-ACCESS  read-only
    STATUS      current
    DESCRIPTION   "Maximum Expected Resource Reservation Protocol Component' Restart Time"
    ::=  { deployProvControlPlaneOtnCapEntry 21 }

deployProvControlPlaneOtnCapRsvpMaxExpRecoveryTime OBJECT-TYPE
    SYNTAX      FspR7Unsigned32Caps
    UNITS       "ms"
    MAX-ACCESS  read-only
    STATUS      current
    DESCRIPTION   "Maximum Expected Resource Reservation Protocol Component' Recovery Time"
    ::=  { deployProvControlPlaneOtnCapEntry 22 }

deployProvControlPlaneOtnCapRsvpConfigFlag OBJECT-TYPE
    SYNTAX      FspR7Unsigned32Caps
    MAX-ACCESS  read-only
    STATUS      current
    DESCRIPTION   "Resource Reservation Protocol Component' Configuration Bitfield"
    ::=  { deployProvControlPlaneOtnCapEntry 23 }

deployProvControlPlaneOtnCapTedbConfigFlag OBJECT-TYPE
    SYNTAX      FspR7Unsigned32Caps
    MAX-ACCESS  read-only
    STATUS      current
    DESCRIPTION   "Traffic Engineering Component' Configuration Bitfield"
    ::=  { deployProvControlPlaneOtnCapEntry 24 }

deployProvControlPlaneOtnCapTedbTraceDetail OBJECT-TYPE
    SYNTAX      FspR7Unsigned32Caps
    MAX-ACCESS  read-only
    STATUS      current
    DESCRIPTION   "Traffic Engineering Component' Trace Detail"
    ::=  { deployProvControlPlaneOtnCapEntry 25 }

deployProvControlPlaneOtnCapTedbMaxSize OBJECT-TYPE
    SYNTAX      FspR7Unsigned32Caps
    MAX-ACCESS  read-only
    STATUS      current
    DESCRIPTION   "Traffic Engineering Component' Maximum Size"
    ::=  { deployProvControlPlaneOtnCapEntry 26 }

deployProvControlPlaneOtnCapTedbRouterId OBJECT-TYPE
    SYNTAX      FspR7YesNo
    MAX-ACCESS  read-only
    STATUS      current
    DESCRIPTION   "Traffic Engineering Component' Router ID"
    ::=  { deployProvControlPlaneOtnCapEntry 27 }

deployProvControlPlaneOtnCapTedbMinAdvertWait OBJECT-TYPE
    SYNTAX      FspR7Unsigned32Caps
    UNITS       "s"
    MAX-ACCESS  read-only
    STATUS      current
    DESCRIPTION   "Traffic Engineering Component' Minimum Advertisement Wait"
    ::=  { deployProvControlPlaneOtnCapEntry 28 }

deployProvControlPlaneOtnCapNaasConfigFlag OBJECT-TYPE
    SYNTAX      FspR7Unsigned32Caps
    MAX-ACCESS  read-only
    STATUS      current
    DESCRIPTION   "Node Attribute Advertising Service Database Component' Configuration Bitfield"
    ::=  { deployProvControlPlaneOtnCapEntry 29 }

deployProvControlPlaneOtnCapNaasTraceDetail OBJECT-TYPE
    SYNTAX      FspR7Unsigned32Caps
    MAX-ACCESS  read-only
    STATUS      current
    DESCRIPTION   "Node Attribute Advertising Service Database Component' Trace Detail"
    ::=  { deployProvControlPlaneOtnCapEntry 30 }

deployProvControlPlaneOtnCapNaasMaxSize OBJECT-TYPE
    SYNTAX      FspR7Unsigned32Caps
    MAX-ACCESS  read-only
    STATUS      current
    DESCRIPTION   "Node Attribute Advertising Service Database Component' Maximum Size"
    ::=  { deployProvControlPlaneOtnCapEntry 31 }

deployProvControlPlaneOtnCapNaasAdvertWait OBJECT-TYPE
    SYNTAX      FspR7Unsigned32Caps
    UNITS       "s"
    MAX-ACCESS  read-only
    STATUS      current
    DESCRIPTION   "Node Attribute Advertising Service Database Component' Advertisement Wait"
    ::=  { deployProvControlPlaneOtnCapEntry 32 }

deployProvControlPlaneOtnCapPcConfigFlag OBJECT-TYPE
    SYNTAX      FspR7Unsigned32Caps
    MAX-ACCESS  read-only
    STATUS      current
    DESCRIPTION   "Path Computation Component' Configuration Bitfield"
    ::=  { deployProvControlPlaneOtnCapEntry 33 }

deployProvControlPlaneOtnCapPcTraceDetail OBJECT-TYPE
    SYNTAX      FspR7Unsigned32Caps
    MAX-ACCESS  read-only
    STATUS      current
    DESCRIPTION   "Path Computation Component' Trace Detail"
    ::=  { deployProvControlPlaneOtnCapEntry 34 }

deployProvControlPlaneOtnCapCdConfigFlag OBJECT-TYPE
    SYNTAX      FspR7Unsigned32Caps
    MAX-ACCESS  read-only
    STATUS      current
    DESCRIPTION   "Configuration Data Component' Configuration Bitfield"
    ::=  { deployProvControlPlaneOtnCapEntry 35 }

deployProvControlPlaneOtnCapCdTraceDetail OBJECT-TYPE
    SYNTAX      FspR7Unsigned32Caps
    MAX-ACCESS  read-only
    STATUS      current
    DESCRIPTION   "Configuration Data Component' Trace Detail"
    ::=  { deployProvControlPlaneOtnCapEntry 36 }

deployProvControlPlaneOtnCapCdResyncTimeout OBJECT-TYPE
    SYNTAX      FspR7Unsigned32Caps
    MAX-ACCESS  read-only
    STATUS      current
    DESCRIPTION   "Configuration Data Component' Resync Timeout"
    ::=  { deployProvControlPlaneOtnCapEntry 37 }

deployProvControlPlaneOtnCapRmConfigFlag OBJECT-TYPE
    SYNTAX      FspR7Unsigned32Caps
    MAX-ACCESS  read-only
    STATUS      current
    DESCRIPTION   "Resource Management Component' Configuration Bitfield"
    ::=  { deployProvControlPlaneOtnCapEntry 38 }

deployProvControlPlaneOtnCapRmTraceDetail OBJECT-TYPE
    SYNTAX      FspR7Unsigned32Caps
    MAX-ACCESS  read-only
    STATUS      current
    DESCRIPTION   "Resource Management Component' Trace Detail"
    ::=  { deployProvControlPlaneOtnCapEntry 39 }

deployProvControlPlaneOtnCapRmTraceTarget OBJECT-TYPE
    SYNTAX      FspR7Unsigned32Caps
    MAX-ACCESS  read-only
    STATUS      current
    DESCRIPTION   "Resource Management Component' Trace Target"
    ::=  { deployProvControlPlaneOtnCapEntry 40 }

deployProvControlPlaneOtnCapNodeNameSyntax OBJECT-TYPE
    SYNTAX      FspR7NodeIdCaps
    MAX-ACCESS  read-only
    STATUS      deprecated
    DESCRIPTION   "Node Name Syntax"
    ::=  { deployProvControlPlaneOtnCapEntry 41 }

deployProvControlPlaneOtnDefaultsTable  OBJECT-TYPE
    SYNTAX      SEQUENCE OF DeployProvControlPlaneOtnDefaultsEntry
    MAX-ACCESS  not-accessible
    STATUS      current
    DESCRIPTION   ""
    ::=  { controlPlaneDeployProv 102  }

deployProvControlPlaneOtnDefaultsEntry OBJECT-TYPE
    SYNTAX      DeployProvControlPlaneOtnDefaultsEntry
    MAX-ACCESS  not-accessible
    STATUS      current
    DESCRIPTION   ""
    INDEX       { controlPlaneOtnEntityIndex }
    ::=  { deployProvControlPlaneOtnDefaultsTable 1 }

DeployProvControlPlaneOtnDefaultsEntry ::=  SEQUENCE
  { deployProvControlPlaneOtnDefaultsRowStatus RowStatus,
    deployProvControlPlaneOtnDefaultsCtmConfigFlag Unsigned32,
    deployProvControlPlaneOtnDefaultsCtmTraceDetail Unsigned32,
    deployProvControlPlaneOtnDefaultsCtmSetupTimeout Unsigned32,
    deployProvControlPlaneOtnDefaultsCtmShutdownTimeout Unsigned32,
    deployProvControlPlaneOtnDefaultsCtmRetryWait Unsigned32,
    deployProvControlPlaneOtnDefaultsCtmRetryWaitMultiplier Unsigned32,
    deployProvControlPlaneOtnDefaultsCtmMaximumRetryWait Unsigned32,
    deployProvControlPlaneOtnDefaultsCtmMaximumRetryNumber Unsigned32,
    deployProvControlPlaneOtnDefaultsRaConfigFlag Unsigned32,
    deployProvControlPlaneOtnDefaultsRaTraceDetail Unsigned32,
    deployProvControlPlaneOtnDefaultsRaAlarmActivationTime Unsigned32,
    deployProvControlPlaneOtnDefaultsCmConfigFlag Unsigned32,
    deployProvControlPlaneOtnDefaultsCmTraceDetail Unsigned32,
    deployProvControlPlaneOtnDefaultsCmAlarmActivationTime Unsigned32,
    deployProvControlPlaneOtnDefaultsCmFisFrsTimeout Unsigned32,
    deployProvControlPlaneOtnDefaultsCmCrankBackTimeout Unsigned32,
    deployProvControlPlaneOtnDefaultsCdbConfigFlag Unsigned32,
    deployProvControlPlaneOtnDefaultsCdbDetail Unsigned32,
    deployProvControlPlaneOtnDefaultsCdbMaxSize Unsigned32,
    deployProvControlPlaneOtnDefaultsRsvpMaxExpRestartTime Counter64String,
    deployProvControlPlaneOtnDefaultsRsvpMaxExpRecoveryTime Unsigned32,
    deployProvControlPlaneOtnDefaultsRsvpConfigFlag Unsigned32,
    deployProvControlPlaneOtnDefaultsTedbConfigFlag Unsigned32,
    deployProvControlPlaneOtnDefaultsTedbTraceDetail Unsigned32,
    deployProvControlPlaneOtnDefaultsTedbMaxSize Unsigned32,
    deployProvControlPlaneOtnDefaultsTedbRouterId IpAddress,
    deployProvControlPlaneOtnDefaultsTedbMinAdvertWait Unsigned32,
    deployProvControlPlaneOtnDefaultsNaasConfigFlag Unsigned32,
    deployProvControlPlaneOtnDefaultsNaasTraceDetail Unsigned32,
    deployProvControlPlaneOtnDefaultsNaasMaxSize Unsigned32,
    deployProvControlPlaneOtnDefaultsNaasAdvertWait Unsigned32,
    deployProvControlPlaneOtnDefaultsPcConfigFlag Unsigned32,
    deployProvControlPlaneOtnDefaultsPcTraceDetail Unsigned32,
    deployProvControlPlaneOtnDefaultsCdConfigFlag Unsigned32,
    deployProvControlPlaneOtnDefaultsCdTraceDetail Unsigned32,
    deployProvControlPlaneOtnDefaultsCdResyncTimeout Unsigned32,
    deployProvControlPlaneOtnDefaultsRmConfigFlag Unsigned32,
    deployProvControlPlaneOtnDefaultsRmTraceDetail Unsigned32,
    deployProvControlPlaneOtnDefaultsRmTraceTarget Unsigned32,
    deployProvControlPlaneOtnDefaultsNodeNameSyntax FspR7NodeId }

deployProvControlPlaneOtnDefaultsRowStatus OBJECT-TYPE
    SYNTAX      RowStatus
    MAX-ACCESS  read-only
    STATUS      current
    DESCRIPTION   ""
    ::=  { deployProvControlPlaneOtnDefaultsEntry 1 }

deployProvControlPlaneOtnDefaultsCtmConfigFlag OBJECT-TYPE
    SYNTAX      Unsigned32
    MAX-ACCESS  read-only
    STATUS      current
    DESCRIPTION   "Label Switched Path Edge Component' Configuration Bitfield"
    ::=  { deployProvControlPlaneOtnDefaultsEntry 2 }

deployProvControlPlaneOtnDefaultsCtmTraceDetail OBJECT-TYPE
    SYNTAX      Unsigned32
    MAX-ACCESS  read-only
    STATUS      current
    DESCRIPTION   "Label Switched Path Edge Component' Trace Detail"
    ::=  { deployProvControlPlaneOtnDefaultsEntry 3 }

deployProvControlPlaneOtnDefaultsCtmSetupTimeout OBJECT-TYPE
    SYNTAX      Unsigned32 
    UNITS       "s"
    MAX-ACCESS  read-only
    STATUS      current
    DESCRIPTION   "Label Switched Path Edge Component' Set-Up Timeout"
    ::=  { deployProvControlPlaneOtnDefaultsEntry 4 }

deployProvControlPlaneOtnDefaultsCtmShutdownTimeout OBJECT-TYPE
    SYNTAX      Unsigned32 
    UNITS       "s"
    MAX-ACCESS  read-only
    STATUS      current
    DESCRIPTION   "Label Switched Path Edge Component' Shut-Down Timeout"
    ::=  { deployProvControlPlaneOtnDefaultsEntry 5 }

deployProvControlPlaneOtnDefaultsCtmRetryWait OBJECT-TYPE
    SYNTAX      Unsigned32 
    UNITS       "s"
    MAX-ACCESS  read-only
    STATUS      current
    DESCRIPTION   "Label Switched Path Edge Component' Initialization Retry Wait"
    ::=  { deployProvControlPlaneOtnDefaultsEntry 6 }

deployProvControlPlaneOtnDefaultsCtmRetryWaitMultiplier OBJECT-TYPE
    SYNTAX      Unsigned32
    MAX-ACCESS  read-only
    STATUS      current
    DESCRIPTION   "Label Switched Path Edge Component' Initialization Retry Wait Multiplier"
    ::=  { deployProvControlPlaneOtnDefaultsEntry 7 }

deployProvControlPlaneOtnDefaultsCtmMaximumRetryWait OBJECT-TYPE
    SYNTAX      Unsigned32 
    UNITS       "s"
    MAX-ACCESS  read-only
    STATUS      current
    DESCRIPTION   "Label Switched Path Edge Component' Initialization Maximum Retry Wait"
    ::=  { deployProvControlPlaneOtnDefaultsEntry 8 }

deployProvControlPlaneOtnDefaultsCtmMaximumRetryNumber OBJECT-TYPE
    SYNTAX      Unsigned32
    MAX-ACCESS  read-only
    STATUS      current
    DESCRIPTION   "Label Switched Path Edge Component' Initialization Maximum Retry Number"
    ::=  { deployProvControlPlaneOtnDefaultsEntry 9 }

deployProvControlPlaneOtnDefaultsRaConfigFlag OBJECT-TYPE
    SYNTAX      Unsigned32
    MAX-ACCESS  read-only
    STATUS      current
    DESCRIPTION   "Resource Allocator Component' Configuration Bitfield"
    ::=  { deployProvControlPlaneOtnDefaultsEntry 10 }

deployProvControlPlaneOtnDefaultsRaTraceDetail OBJECT-TYPE
    SYNTAX      Unsigned32
    MAX-ACCESS  read-only
    STATUS      current
    DESCRIPTION   "Resource Allocator Component' Trace Detail"
    ::=  { deployProvControlPlaneOtnDefaultsEntry 11 }

deployProvControlPlaneOtnDefaultsRaAlarmActivationTime OBJECT-TYPE
    SYNTAX      Unsigned32 
    UNITS       "s"
    MAX-ACCESS  read-only
    STATUS      current
    DESCRIPTION   "Resource Allocator Component' Alarm Activation Time"
    ::=  { deployProvControlPlaneOtnDefaultsEntry 12 }

deployProvControlPlaneOtnDefaultsCmConfigFlag OBJECT-TYPE
    SYNTAX      Unsigned32
    MAX-ACCESS  read-only
    STATUS      current
    DESCRIPTION   "GMPLS Tunnel Manager Component' Configuration Bitfield"
    ::=  { deployProvControlPlaneOtnDefaultsEntry 13 }

deployProvControlPlaneOtnDefaultsCmTraceDetail OBJECT-TYPE
    SYNTAX      Unsigned32
    MAX-ACCESS  read-only
    STATUS      current
    DESCRIPTION   "GMPLS Tunnel Manager Component' Trace Detail"
    ::=  { deployProvControlPlaneOtnDefaultsEntry 14 }

deployProvControlPlaneOtnDefaultsCmAlarmActivationTime OBJECT-TYPE
    SYNTAX      Unsigned32 
    UNITS       "s"
    MAX-ACCESS  read-only
    STATUS      current
    DESCRIPTION   "GMPLS Tunnel Manager Component' Alarm Activation Time"
    ::=  { deployProvControlPlaneOtnDefaultsEntry 15 }

deployProvControlPlaneOtnDefaultsCmFisFrsTimeout OBJECT-TYPE
    SYNTAX      Unsigned32 
    UNITS       "s"
    MAX-ACCESS  read-only
    STATUS      current
    DESCRIPTION   "GMPLS Tunnel Manager Component' FIS-FRS Timeout"
    ::=  { deployProvControlPlaneOtnDefaultsEntry 16 }

deployProvControlPlaneOtnDefaultsCmCrankBackTimeout OBJECT-TYPE
    SYNTAX      Unsigned32 
    UNITS       "s"
    MAX-ACCESS  read-only
    STATUS      current
    DESCRIPTION   "GMPLS Tunnel Manager Component' Crank-Back Timeout"
    ::=  { deployProvControlPlaneOtnDefaultsEntry 17 }

deployProvControlPlaneOtnDefaultsCdbConfigFlag OBJECT-TYPE
    SYNTAX      Unsigned32
    MAX-ACCESS  read-only
    STATUS      current
    DESCRIPTION   "Label Swithed Path Database Component Configuration Bitfield"
    ::=  { deployProvControlPlaneOtnDefaultsEntry 18 }

deployProvControlPlaneOtnDefaultsCdbDetail OBJECT-TYPE
    SYNTAX      Unsigned32
    MAX-ACCESS  read-only
    STATUS      current
    DESCRIPTION   "Label Swithed Path Database Component Trace Detail"
    ::=  { deployProvControlPlaneOtnDefaultsEntry 19 }

deployProvControlPlaneOtnDefaultsCdbMaxSize OBJECT-TYPE
    SYNTAX      Unsigned32
    MAX-ACCESS  read-only
    STATUS      current
    DESCRIPTION   "Label Swithed Path Database Component Maximum Size; 0 implies no limit"
    ::=  { deployProvControlPlaneOtnDefaultsEntry 20 }

deployProvControlPlaneOtnDefaultsRsvpMaxExpRestartTime OBJECT-TYPE
    SYNTAX      Counter64String 
    UNITS       "ms"
    MAX-ACCESS  read-only
    STATUS      current
    DESCRIPTION   "Maximum Expected Resource Reservation Protocol Component' Restart Time"
    ::=  { deployProvControlPlaneOtnDefaultsEntry 21 }

deployProvControlPlaneOtnDefaultsRsvpMaxExpRecoveryTime OBJECT-TYPE
    SYNTAX      Unsigned32 
    UNITS       "ms"
    MAX-ACCESS  read-only
    STATUS      current
    DESCRIPTION   "Maximum Expected Resource Reservation Protocol Component' Recovery Time"
    ::=  { deployProvControlPlaneOtnDefaultsEntry 22 }

deployProvControlPlaneOtnDefaultsRsvpConfigFlag OBJECT-TYPE
    SYNTAX      Unsigned32
    MAX-ACCESS  read-only
    STATUS      current
    DESCRIPTION   "Resource Reservation Protocol Component' Configuration Bitfield"
    ::=  { deployProvControlPlaneOtnDefaultsEntry 23 }

deployProvControlPlaneOtnDefaultsTedbConfigFlag OBJECT-TYPE
    SYNTAX      Unsigned32
    MAX-ACCESS  read-only
    STATUS      current
    DESCRIPTION   "Traffic Engineering Component' Configuration Bitfield"
    ::=  { deployProvControlPlaneOtnDefaultsEntry 24 }

deployProvControlPlaneOtnDefaultsTedbTraceDetail OBJECT-TYPE
    SYNTAX      Unsigned32
    MAX-ACCESS  read-only
    STATUS      current
    DESCRIPTION   "Traffic Engineering Component' Trace Detail"
    ::=  { deployProvControlPlaneOtnDefaultsEntry 25 }

deployProvControlPlaneOtnDefaultsTedbMaxSize OBJECT-TYPE
    SYNTAX      Unsigned32
    MAX-ACCESS  read-only
    STATUS      current
    DESCRIPTION   "Traffic Engineering Component' Maximum Size"
    ::=  { deployProvControlPlaneOtnDefaultsEntry 26 }

deployProvControlPlaneOtnDefaultsTedbRouterId OBJECT-TYPE
    SYNTAX      IpAddress
    MAX-ACCESS  read-only
    STATUS      current
    DESCRIPTION   "Traffic Engineering Component' Router ID"
    ::=  { deployProvControlPlaneOtnDefaultsEntry 27 }

deployProvControlPlaneOtnDefaultsTedbMinAdvertWait OBJECT-TYPE
    SYNTAX      Unsigned32 
    UNITS       "s"
    MAX-ACCESS  read-only
    STATUS      current
    DESCRIPTION   "Traffic Engineering Component' Minimum Advertisement Wait"
    ::=  { deployProvControlPlaneOtnDefaultsEntry 28 }

deployProvControlPlaneOtnDefaultsNaasConfigFlag OBJECT-TYPE
    SYNTAX      Unsigned32
    MAX-ACCESS  read-only
    STATUS      current
    DESCRIPTION   "Node Attribute Advertising Service Database Component' Configuration Bitfield"
    ::=  { deployProvControlPlaneOtnDefaultsEntry 29 }

deployProvControlPlaneOtnDefaultsNaasTraceDetail OBJECT-TYPE
    SYNTAX      Unsigned32
    MAX-ACCESS  read-only
    STATUS      current
    DESCRIPTION   "Node Attribute Advertising Service Database Component' Trace Detail"
    ::=  { deployProvControlPlaneOtnDefaultsEntry 30 }

deployProvControlPlaneOtnDefaultsNaasMaxSize OBJECT-TYPE
    SYNTAX      Unsigned32
    MAX-ACCESS  read-only
    STATUS      current
    DESCRIPTION   "Node Attribute Advertising Service Database Component' Maximum Size"
    ::=  { deployProvControlPlaneOtnDefaultsEntry 31 }

deployProvControlPlaneOtnDefaultsNaasAdvertWait OBJECT-TYPE
    SYNTAX      Unsigned32 
    UNITS       "s"
    MAX-ACCESS  read-only
    STATUS      current
    DESCRIPTION   "Node Attribute Advertising Service Database Component' Advertisement Wait"
    ::=  { deployProvControlPlaneOtnDefaultsEntry 32 }

deployProvControlPlaneOtnDefaultsPcConfigFlag OBJECT-TYPE
    SYNTAX      Unsigned32
    MAX-ACCESS  read-only
    STATUS      current
    DESCRIPTION   "Path Computation Component' Configuration Bitfield"
    ::=  { deployProvControlPlaneOtnDefaultsEntry 33 }

deployProvControlPlaneOtnDefaultsPcTraceDetail OBJECT-TYPE
    SYNTAX      Unsigned32
    MAX-ACCESS  read-only
    STATUS      current
    DESCRIPTION   "Path Computation Component' Trace Detail"
    ::=  { deployProvControlPlaneOtnDefaultsEntry 34 }

deployProvControlPlaneOtnDefaultsCdConfigFlag OBJECT-TYPE
    SYNTAX      Unsigned32
    MAX-ACCESS  read-only
    STATUS      current
    DESCRIPTION   "Configuration Data Component' Configuration Bitfield"
    ::=  { deployProvControlPlaneOtnDefaultsEntry 35 }

deployProvControlPlaneOtnDefaultsCdTraceDetail OBJECT-TYPE
    SYNTAX      Unsigned32
    MAX-ACCESS  read-only
    STATUS      current
    DESCRIPTION   "Configuration Data Component' Trace Detail"
    ::=  { deployProvControlPlaneOtnDefaultsEntry 36 }

deployProvControlPlaneOtnDefaultsCdResyncTimeout OBJECT-TYPE
    SYNTAX      Unsigned32
    MAX-ACCESS  read-only
    STATUS      current
    DESCRIPTION   "Configuration Data Component' Resync Timeout"
    ::=  { deployProvControlPlaneOtnDefaultsEntry 37 }

deployProvControlPlaneOtnDefaultsRmConfigFlag OBJECT-TYPE
    SYNTAX      Unsigned32
    MAX-ACCESS  read-only
    STATUS      current
    DESCRIPTION   "Resource Management Component' Configuration Bitfield"
    ::=  { deployProvControlPlaneOtnDefaultsEntry 38 }

deployProvControlPlaneOtnDefaultsRmTraceDetail OBJECT-TYPE
    SYNTAX      Unsigned32
    MAX-ACCESS  read-only
    STATUS      current
    DESCRIPTION   "Resource Management Component' Trace Detail"
    ::=  { deployProvControlPlaneOtnDefaultsEntry 39 }

deployProvControlPlaneOtnDefaultsRmTraceTarget OBJECT-TYPE
    SYNTAX      Unsigned32
    MAX-ACCESS  read-only
    STATUS      current
    DESCRIPTION   "Resource Management Component' Trace Target"
    ::=  { deployProvControlPlaneOtnDefaultsEntry 40 }

deployProvControlPlaneOtnDefaultsNodeNameSyntax OBJECT-TYPE
    SYNTAX      FspR7NodeId
    MAX-ACCESS  read-only
    STATUS      deprecated
    DESCRIPTION   "Node Name Syntax"
    ::=  { deployProvControlPlaneOtnDefaultsEntry 41 }

deployProvTunnelOtnTable OBJECT-TYPE
    SYNTAX      SEQUENCE OF DeployProvTunnelOtnEntry
    MAX-ACCESS  not-accessible
    STATUS      current
    DESCRIPTION   ""
    ::=  { controlPlaneDeployProv 103 }

deployProvTunnelOtnEntry OBJECT-TYPE
    SYNTAX      DeployProvTunnelOtnEntry
    MAX-ACCESS  not-accessible
    STATUS      current
    DESCRIPTION   ""
    INDEX       {
                  controlPlaneOtnEntityIndex
                }
    ::=  { deployProvTunnelOtnTable 1 }

DeployProvTunnelOtnEntry ::=  SEQUENCE
  { deployProvTunnelOtnRowStatus RowStatus,
    deployProvTunnelOtnTunnelId SnmpAdminString,
    deployProvTunnelOtnTunnelNo Unsigned32,
    deployProvTunnelOtnAlias SnmpAdminString,
    deployProvTunnelOtnTunnelType FspR7CpTunnelType,
    deployProvTunnelOtnToTid SnmpAdminString,
    deployProvTunnelOtnToNodeIp IpAddress,
    deployProvTunnelOtnFromAid EntityIndex,
    deployProvTunnelOtnToAid EntityIndex,
    deployProvTunnelOtnConnectionDirection FspR7Conn,
    deployProvTunnelOtnFacilityType FspR7InterfaceType,
    deployProvTunnelOtnProvisionedPaths SnmpAdminString,
    deployProvTunnelOtnProtectionType FspR7CpProtectionType,
    deployProvTunnelOtnPin FspR7CpPinning,
    deployProvTunnelOtnRestorationType FspR7CpRestorationType,
    deployProvTunnelOtnMonitorEntities FspR7EnableDisable,
    deployProvTunnelOtnTunnelScope FspR7CpTunnelScope,
    deployProvTunnelOtnLayer FspR7PacketsLayer,
    deployProvTunnelOtnOifUni FspR7YesNo,
    deployProvTunnelOtnFromAidString SnmpAdminString,
    deployProvTunnelOtnToAidString SnmpAdminString,
    deployProvTunnelOtnExcludedPaths SnmpAdminString,
    deployProvTunnelOtnTerminationLevel OhTerminationLevel,
    deployProvTunnelOtnFecType FspR7FecType,
    deployProvTunnelOtnStuff FspR7Stuff,
    deployProvTunnelOtnPreferPcs FspR7YesNo,
    deployProvTunnelOtnEroScope SnmpAdminString,
    deployProvTunnelOtnEroLifeCycle SnmpAdminString,
    deployProvTunnelOtnXroScope SnmpAdminString,
    deployProvTunnelOtnXroLifeCycle SnmpAdminString }

deployProvTunnelOtnRowStatus OBJECT-TYPE
    SYNTAX      RowStatus
    MAX-ACCESS  read-write
    STATUS      current
    DESCRIPTION
        "RowStatus" 
    ::=  { deployProvTunnelOtnEntry 1 }

deployProvTunnelOtnTunnelId OBJECT-TYPE
    SYNTAX      SnmpAdminString
    MAX-ACCESS  read-write
    STATUS      current
    DESCRIPTION   ""
    ::=  { deployProvTunnelOtnEntry 2 }

deployProvTunnelOtnTunnelNo OBJECT-TYPE
    SYNTAX      Unsigned32
    MAX-ACCESS  read-write
    STATUS      current
    DESCRIPTION   ""
    ::=  { deployProvTunnelOtnEntry 3 }

deployProvTunnelOtnAlias OBJECT-TYPE
    SYNTAX      SnmpAdminString
    MAX-ACCESS  read-write
    STATUS      current
    DESCRIPTION   ""
    ::=  { deployProvTunnelOtnEntry 4 }

deployProvTunnelOtnTunnelType OBJECT-TYPE
    SYNTAX      FspR7CpTunnelType
    MAX-ACCESS  read-write
    STATUS      current
    DESCRIPTION   ""
    ::=  { deployProvTunnelOtnEntry 5 }

deployProvTunnelOtnToTid OBJECT-TYPE
    SYNTAX      SnmpAdminString
    MAX-ACCESS  read-write
    STATUS      current
    DESCRIPTION   ""
    ::=  { deployProvTunnelOtnEntry 6 }

deployProvTunnelOtnToNodeIp OBJECT-TYPE
    SYNTAX      IpAddress
    MAX-ACCESS  read-write
    STATUS      current
    DESCRIPTION   ""
    ::=  { deployProvTunnelOtnEntry 7 }

deployProvTunnelOtnFromAid OBJECT-TYPE
    SYNTAX      EntityIndex
    MAX-ACCESS  read-write
    STATUS      current
    DESCRIPTION   ""
    ::=  { deployProvTunnelOtnEntry 8 }

deployProvTunnelOtnToAid OBJECT-TYPE
    SYNTAX      EntityIndex
    MAX-ACCESS  read-write
    STATUS      current
    DESCRIPTION   ""
    ::=  { deployProvTunnelOtnEntry 9 }

deployProvTunnelOtnConnectionDirection OBJECT-TYPE
    SYNTAX      FspR7Conn
    MAX-ACCESS  read-write
    STATUS      current
    DESCRIPTION   ""
    ::=  { deployProvTunnelOtnEntry 10 }

deployProvTunnelOtnFacilityType OBJECT-TYPE
    SYNTAX      FspR7InterfaceType
    MAX-ACCESS  read-write
    STATUS      current
    DESCRIPTION   ""
    ::=  { deployProvTunnelOtnEntry 11 }

deployProvTunnelOtnProvisionedPaths OBJECT-TYPE
    SYNTAX      SnmpAdminString
    MAX-ACCESS  read-write
    STATUS      current
    DESCRIPTION   ""
    ::=  { deployProvTunnelOtnEntry 12 }

deployProvTunnelOtnProtectionType OBJECT-TYPE
    SYNTAX      FspR7CpProtectionType
    MAX-ACCESS  read-write
    STATUS      current
    DESCRIPTION   ""
    ::=  { deployProvTunnelOtnEntry 13 }

deployProvTunnelOtnPin OBJECT-TYPE
    SYNTAX      FspR7CpPinning
    MAX-ACCESS  read-write
    STATUS      current
    DESCRIPTION   ""
    ::=  { deployProvTunnelOtnEntry 14 }

deployProvTunnelOtnRestorationType OBJECT-TYPE
    SYNTAX      FspR7CpRestorationType
    MAX-ACCESS  read-write
    STATUS      current
    DESCRIPTION   ""
    ::=  { deployProvTunnelOtnEntry 15 }

deployProvTunnelOtnMonitorEntities OBJECT-TYPE
    SYNTAX      FspR7EnableDisable
    MAX-ACCESS  read-write
    STATUS      current
    DESCRIPTION   ""
    ::=  { deployProvTunnelOtnEntry 16 }

deployProvTunnelOtnTunnelScope OBJECT-TYPE
    SYNTAX      FspR7CpTunnelScope
    MAX-ACCESS  read-write
    STATUS      current
    DESCRIPTION
        "Service Scope extending over either Client or Network Ports of Modules or Links (UN or NR) for Connection Segements" 
    ::=  { deployProvTunnelOtnEntry 17 }

deployProvTunnelOtnLayer OBJECT-TYPE
    SYNTAX      FspR7PacketsLayer
    MAX-ACCESS  read-write
    STATUS      current
    DESCRIPTION
        "Notional Layer of Advertisement on Packets on the LIF" 
    ::=  { deployProvTunnelOtnEntry 18 }

deployProvTunnelOtnOifUni OBJECT-TYPE
    SYNTAX      FspR7YesNo
    MAX-ACCESS  read-write
    STATUS      current
    DESCRIPTION
        "OIF UNI Tunnel" 
    ::=  { deployProvTunnelOtnEntry 19 }

deployProvTunnelOtnFromAidString OBJECT-TYPE
    SYNTAX      SnmpAdminString
    MAX-ACCESS  read-write
    STATUS      current
    DESCRIPTION
        "" 
    ::=  { deployProvTunnelOtnEntry 20 }

deployProvTunnelOtnToAidString OBJECT-TYPE
    SYNTAX      SnmpAdminString
    MAX-ACCESS  read-write
    STATUS      current
    DESCRIPTION
        "" 
    ::=  { deployProvTunnelOtnEntry 21 }

deployProvTunnelOtnExcludedPaths OBJECT-TYPE
    SYNTAX      SnmpAdminString
    MAX-ACCESS  read-write
    STATUS      current
    DESCRIPTION
        "Lists of Path Elements to be excluded" 
    ::=  { deployProvTunnelOtnEntry 22 }

deployProvTunnelOtnTerminationLevel OBJECT-TYPE
    SYNTAX      OhTerminationLevel
    MAX-ACCESS  read-write
    STATUS      current
    DESCRIPTION
        "Highest signal level hardware removes then generates for transmission." 
    ::=  { deployProvTunnelOtnEntry 23 }

deployProvTunnelOtnFecType OBJECT-TYPE
    SYNTAX      FspR7FecType
    MAX-ACCESS  read-only
    STATUS      current
    DESCRIPTION
        "Forward Error Correction (Only relevant where TYPE = OTU#)" 
    ::=  { deployProvTunnelOtnEntry 24 }

deployProvTunnelOtnStuff OBJECT-TYPE
    SYNTAX      FspR7Stuff
    MAX-ACCESS  read-only
    STATUS      current
    DESCRIPTION
        "Indicates if bit/byte stuffing is used in the transport signal." 
    ::=  { deployProvTunnelOtnEntry 25 }

deployProvTunnelOtnPreferPcs OBJECT-TYPE
    SYNTAX      FspR7YesNo
    MAX-ACCESS  read-write
    STATUS      current
    DESCRIPTION
        "Preferred Path Computation Engine (Server)" 
    ::=  { deployProvTunnelOtnEntry 26 }

deployProvTunnelOtnEroScope OBJECT-TYPE
    SYNTAX      SnmpAdminString
    MAX-ACCESS  read-write
    STATUS      current
    DESCRIPTION
        "Inclusion Route - Scope" 
    ::=  { deployProvTunnelOtnEntry 27 }

deployProvTunnelOtnEroLifeCycle OBJECT-TYPE
    SYNTAX      SnmpAdminString
    MAX-ACCESS  read-write
    STATUS      current
    DESCRIPTION
        "Inclusion Route - Life Cycle" 
    ::=  { deployProvTunnelOtnEntry 28 }

deployProvTunnelOtnXroScope OBJECT-TYPE
    SYNTAX      SnmpAdminString
    MAX-ACCESS  read-write
    STATUS      current
    DESCRIPTION
        "Exclusion Path Elements - Scope" 
    ::=  { deployProvTunnelOtnEntry 29 }

deployProvTunnelOtnXroLifeCycle OBJECT-TYPE
    SYNTAX      SnmpAdminString
    MAX-ACCESS  read-write
    STATUS      current
    DESCRIPTION
        "Exclusion Path Elements - Life Cycle" 
    ::=  { deployProvTunnelOtnEntry 30 }

deployProvTunnelOtnCapTable OBJECT-TYPE
    SYNTAX      SEQUENCE OF DeployProvTunnelOtnCapEntry
    MAX-ACCESS  not-accessible
    STATUS      current
    DESCRIPTION   ""
    ::=  { controlPlaneDeployProv 104  }

deployProvTunnelOtnCapEntry OBJECT-TYPE
    SYNTAX      DeployProvTunnelOtnCapEntry
    MAX-ACCESS  not-accessible
    STATUS      current
    DESCRIPTION   ""
    INDEX       { controlPlaneOtnEntityIndex }
    ::=  { deployProvTunnelOtnCapTable 1 }

DeployProvTunnelOtnCapEntry ::=  SEQUENCE
  { deployProvTunnelOtnCapRowStatus FspR7RowStatusCaps,
    deployProvTunnelOtnCapTunnelId Integer32,
    deployProvTunnelOtnCapTunnelNo FspR7Unsigned32Caps,
    deployProvTunnelOtnCapAlias Integer32,
    deployProvTunnelOtnCapTunnelType FspR7CpTunnelTypeCaps,
    deployProvTunnelOtnCapToTid Integer32,
    deployProvTunnelOtnCapToNodeIp FspR7YesNo,
    deployProvTunnelOtnCapFromAid Integer32,
    deployProvTunnelOtnCapToAid Integer32,
    deployProvTunnelOtnCapConnectionDirection FspR7ConnCaps,
    deployProvTunnelOtnCapFacilityType FspR7InterfaceTypeCaps,
    deployProvTunnelOtnCapProvisionedPaths Integer32,
    deployProvTunnelOtnCapProtectionType FspR7CpProtectionTypeCaps,
    deployProvTunnelOtnCapPin FspR7CpPinningCaps,
    deployProvTunnelOtnCapRestorationType FspR7CpRestorationTypeCaps,
    deployProvTunnelOtnCapMonitorEntities FspR7EnableDisableCaps,
    deployProvTunnelOtnCapTunnelScope FspR7CpTunnelScopeCaps,
    deployProvTunnelOtnCapLayer FspR7PacketsLayerCaps,
    deployProvTunnelOtnCapOifUni FspR7YesNoCaps,
    deployProvTunnelOtnCapFromAidString Integer32,
    deployProvTunnelOtnCapToAidString Integer32,
    deployProvTunnelOtnCapExcludedPaths SnmpAdminString,
    deployProvTunnelOtnCapTerminationLevel OhTerminationLevelCaps,
    deployProvTunnelOtnCapFecType FspR7FecTypeCaps,
    deployProvTunnelOtnCapStuff FspR7StuffCaps,
    deployProvTunnelOtnCapPreferPcs FspR7YesNoCaps,
    deployProvTunnelOtnCapEroScope SnmpAdminString,
    deployProvTunnelOtnCapEroLifeCycle SnmpAdminString,
    deployProvTunnelOtnCapXroScope SnmpAdminString,
    deployProvTunnelOtnCapXroLifeCycle SnmpAdminString }

deployProvTunnelOtnCapRowStatus OBJECT-TYPE
    SYNTAX      FspR7RowStatusCaps
    MAX-ACCESS  read-only
    STATUS      current
    DESCRIPTION
        "RowStatus" 
    ::=  { deployProvTunnelOtnCapEntry 1 }

deployProvTunnelOtnCapTunnelId OBJECT-TYPE
    SYNTAX      Integer32
    MAX-ACCESS  read-only
    STATUS      current
    DESCRIPTION   ""
    ::=  { deployProvTunnelOtnCapEntry 2 }

deployProvTunnelOtnCapTunnelNo OBJECT-TYPE
    SYNTAX      FspR7Unsigned32Caps
    MAX-ACCESS  read-only
    STATUS      current
    DESCRIPTION   ""
    ::=  { deployProvTunnelOtnCapEntry 3 }

deployProvTunnelOtnCapAlias OBJECT-TYPE
    SYNTAX      Integer32
    MAX-ACCESS  read-only
    STATUS      current
    DESCRIPTION   ""
    ::=  { deployProvTunnelOtnCapEntry 4 }

deployProvTunnelOtnCapTunnelType OBJECT-TYPE
    SYNTAX      FspR7CpTunnelTypeCaps
    MAX-ACCESS  read-only
    STATUS      current
    DESCRIPTION   ""
    ::=  { deployProvTunnelOtnCapEntry 5 }

deployProvTunnelOtnCapToTid OBJECT-TYPE
    SYNTAX      Integer32
    MAX-ACCESS  read-only
    STATUS      current
    DESCRIPTION   ""
    ::=  { deployProvTunnelOtnCapEntry 6 }

deployProvTunnelOtnCapToNodeIp OBJECT-TYPE
    SYNTAX      FspR7YesNo
    MAX-ACCESS  read-only
    STATUS      current
    DESCRIPTION   ""
    ::=  { deployProvTunnelOtnCapEntry 7 }

deployProvTunnelOtnCapFromAid OBJECT-TYPE
    SYNTAX      Integer32
    MAX-ACCESS  read-only
    STATUS      current
    DESCRIPTION   ""
    ::=  { deployProvTunnelOtnCapEntry 8 }

deployProvTunnelOtnCapToAid OBJECT-TYPE
    SYNTAX      Integer32
    MAX-ACCESS  read-only
    STATUS      current
    DESCRIPTION   ""
    ::=  { deployProvTunnelOtnCapEntry 9 }

deployProvTunnelOtnCapConnectionDirection OBJECT-TYPE
    SYNTAX      FspR7ConnCaps
    MAX-ACCESS  read-only
    STATUS      current
    DESCRIPTION   ""
    ::=  { deployProvTunnelOtnCapEntry 10 }

deployProvTunnelOtnCapFacilityType OBJECT-TYPE
    SYNTAX      FspR7InterfaceTypeCaps
    MAX-ACCESS  read-only
    STATUS      current
    DESCRIPTION   ""
    ::=  { deployProvTunnelOtnCapEntry 11 }

deployProvTunnelOtnCapProvisionedPaths OBJECT-TYPE
    SYNTAX      Integer32
    MAX-ACCESS  read-only
    STATUS      current
    DESCRIPTION   ""
    ::=  { deployProvTunnelOtnCapEntry 12 }

deployProvTunnelOtnCapProtectionType OBJECT-TYPE
    SYNTAX      FspR7CpProtectionTypeCaps
    MAX-ACCESS  read-only
    STATUS      current
    DESCRIPTION   ""
    ::=  { deployProvTunnelOtnCapEntry 13 }

deployProvTunnelOtnCapPin OBJECT-TYPE
    SYNTAX      FspR7CpPinningCaps
    MAX-ACCESS  read-only
    STATUS      current
    DESCRIPTION   ""
    ::=  { deployProvTunnelOtnCapEntry 14 }

deployProvTunnelOtnCapRestorationType OBJECT-TYPE
    SYNTAX      FspR7CpRestorationTypeCaps
    MAX-ACCESS  read-only
    STATUS      current
    DESCRIPTION   ""
    ::=  { deployProvTunnelOtnCapEntry 15 }

deployProvTunnelOtnCapMonitorEntities OBJECT-TYPE
    SYNTAX      FspR7EnableDisableCaps
    MAX-ACCESS  read-only
    STATUS      current
    DESCRIPTION   ""
    ::=  { deployProvTunnelOtnCapEntry 16 }

deployProvTunnelOtnCapTunnelScope OBJECT-TYPE
    SYNTAX      FspR7CpTunnelScopeCaps
    MAX-ACCESS  read-only
    STATUS      current
    DESCRIPTION
        "Service Scope extending over either Client or Network Ports of Modules or Links (UN or NR) for Connection Segements" 
    ::=  { deployProvTunnelOtnCapEntry 17 }

deployProvTunnelOtnCapLayer OBJECT-TYPE
    SYNTAX      FspR7PacketsLayerCaps
    MAX-ACCESS  read-only
    STATUS      current
    DESCRIPTION
        "Notional Layer of Advertisement on Packets on the LIF" 
    ::=  { deployProvTunnelOtnCapEntry 18 }

deployProvTunnelOtnCapOifUni OBJECT-TYPE
    SYNTAX      FspR7YesNoCaps
    MAX-ACCESS  read-only
    STATUS      current
    DESCRIPTION
        "OIF UNI Tunnel" 
    ::=  { deployProvTunnelOtnCapEntry 19 }

deployProvTunnelOtnCapFromAidString OBJECT-TYPE
    SYNTAX      Integer32
    MAX-ACCESS  read-only
    STATUS      current
    DESCRIPTION
        "" 
    ::=  { deployProvTunnelOtnCapEntry 20 }

deployProvTunnelOtnCapToAidString OBJECT-TYPE
    SYNTAX      Integer32
    MAX-ACCESS  read-only
    STATUS      current
    DESCRIPTION
        "" 
    ::=  { deployProvTunnelOtnCapEntry 21 }

deployProvTunnelOtnCapExcludedPaths OBJECT-TYPE
    SYNTAX      SnmpAdminString
    MAX-ACCESS  read-only
    STATUS      current
    DESCRIPTION
        "Lists of Path Elements to be excluded" 
    ::=  { deployProvTunnelOtnCapEntry 22 }

deployProvTunnelOtnCapTerminationLevel OBJECT-TYPE
    SYNTAX      OhTerminationLevelCaps
    MAX-ACCESS  read-only
    STATUS      current
    DESCRIPTION
        "Highest signal level hardware removes then generates for transmission." 
    ::=  { deployProvTunnelOtnCapEntry 23 }

deployProvTunnelOtnCapFecType OBJECT-TYPE
    SYNTAX      FspR7FecTypeCaps
    MAX-ACCESS  read-only
    STATUS      current
    DESCRIPTION
        "Forward Error Correction (Only relevant where TYPE = OTU#)" 
    ::=  { deployProvTunnelOtnCapEntry 24 }

deployProvTunnelOtnCapStuff OBJECT-TYPE
    SYNTAX      FspR7StuffCaps
    MAX-ACCESS  read-only
    STATUS      current
    DESCRIPTION
        "Indicates if bit/byte stuffing is used in the transport signal." 
    ::=  { deployProvTunnelOtnCapEntry 25 }

deployProvTunnelOtnCapPreferPcs OBJECT-TYPE
    SYNTAX      FspR7YesNoCaps
    MAX-ACCESS  read-only
    STATUS      current
    DESCRIPTION
        "Preferred Path Computation Engine (Server)" 
    ::=  { deployProvTunnelOtnCapEntry 26 }

deployProvTunnelOtnCapEroScope OBJECT-TYPE
    SYNTAX      SnmpAdminString
    MAX-ACCESS  read-only
    STATUS      current
    DESCRIPTION
        "Inclusion Route - Scope" 
    ::=  { deployProvTunnelOtnCapEntry 27 }

deployProvTunnelOtnCapEroLifeCycle OBJECT-TYPE
    SYNTAX      SnmpAdminString
    MAX-ACCESS  read-only
    STATUS      current
    DESCRIPTION
        "Inclusion Route - Life Cycle" 
    ::=  { deployProvTunnelOtnCapEntry 28 }

deployProvTunnelOtnCapXroScope OBJECT-TYPE
    SYNTAX      SnmpAdminString
    MAX-ACCESS  read-only
    STATUS      current
    DESCRIPTION
        "Exclusion Path Elements - Scope" 
    ::=  { deployProvTunnelOtnCapEntry 29 }

deployProvTunnelOtnCapXroLifeCycle OBJECT-TYPE
    SYNTAX      SnmpAdminString
    MAX-ACCESS  read-only
    STATUS      current
    DESCRIPTION
        "Exclusion Path Elements - Life Cycle" 
    ::=  { deployProvTunnelOtnCapEntry 30 }

deployProvTunnelOtnDefaultsTable  OBJECT-TYPE
    SYNTAX      SEQUENCE OF DeployProvTunnelOtnDefaultsEntry
    MAX-ACCESS  not-accessible
    STATUS      current
    DESCRIPTION   ""
    ::=  { controlPlaneDeployProv 105  }

deployProvTunnelOtnDefaultsEntry OBJECT-TYPE
    SYNTAX      DeployProvTunnelOtnDefaultsEntry
    MAX-ACCESS  not-accessible
    STATUS      current
    DESCRIPTION   ""
    INDEX       { controlPlaneOtnEntityIndex }
    ::=  { deployProvTunnelOtnDefaultsTable 1 }

DeployProvTunnelOtnDefaultsEntry ::=  SEQUENCE
  { deployProvTunnelOtnDefaultsRowStatus RowStatus,
    deployProvTunnelOtnDefaultsTunnelId SnmpAdminString,
    deployProvTunnelOtnDefaultsTunnelNo Unsigned32,
    deployProvTunnelOtnDefaultsAlias SnmpAdminString,
    deployProvTunnelOtnDefaultsTunnelType FspR7CpTunnelType,
    deployProvTunnelOtnDefaultsToTid SnmpAdminString,
    deployProvTunnelOtnDefaultsToNodeIp IpAddress,
    deployProvTunnelOtnDefaultsFromAid EntityIndex,
    deployProvTunnelOtnDefaultsToAid EntityIndex,
    deployProvTunnelOtnDefaultsConnectionDirection FspR7Conn,
    deployProvTunnelOtnDefaultsFacilityType FspR7InterfaceType,
    deployProvTunnelOtnDefaultsProvisionedPaths SnmpAdminString,
    deployProvTunnelOtnDefaultsProtectionType FspR7CpProtectionType,
    deployProvTunnelOtnDefaultsPin FspR7CpPinning,
    deployProvTunnelOtnDefaultsRestorationType FspR7CpRestorationType,
    deployProvTunnelOtnDefaultsMonitorEntities FspR7EnableDisable,
    deployProvTunnelOtnDefaultsTunnelScope FspR7CpTunnelScope,
    deployProvTunnelOtnDefaultsLayer FspR7PacketsLayer,
    deployProvTunnelOtnDefaultsOifUni FspR7YesNo,
    deployProvTunnelOtnDefaultsFromAidString SnmpAdminString,
    deployProvTunnelOtnDefaultsToAidString SnmpAdminString,
    deployProvTunnelOtnDefaultsExcludedPaths SnmpAdminString,
    deployProvTunnelOtnDefaultsTerminationLevel OhTerminationLevel,
    deployProvTunnelOtnDefaultsFecType FspR7FecType,
    deployProvTunnelOtnDefaultsStuff FspR7Stuff,
    deployProvTunnelOtnDefaultsPreferPcs FspR7YesNo,
    deployProvTunnelOtnDefaultsEroScope SnmpAdminString,
    deployProvTunnelOtnDefaultsEroLifeCycle SnmpAdminString,
    deployProvTunnelOtnDefaultsXroScope SnmpAdminString,
    deployProvTunnelOtnDefaultsXroLifeCycle SnmpAdminString }

deployProvTunnelOtnDefaultsRowStatus OBJECT-TYPE
    SYNTAX      RowStatus
    MAX-ACCESS  read-only
    STATUS      current
    DESCRIPTION
        "RowStatus" 
    ::=  { deployProvTunnelOtnDefaultsEntry 1 }

deployProvTunnelOtnDefaultsTunnelId OBJECT-TYPE
    SYNTAX      SnmpAdminString
    MAX-ACCESS  read-only
    STATUS      current
    DESCRIPTION   ""
    ::=  { deployProvTunnelOtnDefaultsEntry 2 }

deployProvTunnelOtnDefaultsTunnelNo OBJECT-TYPE
    SYNTAX      Unsigned32
    MAX-ACCESS  read-only
    STATUS      current
    DESCRIPTION   ""
    ::=  { deployProvTunnelOtnDefaultsEntry 3 }

deployProvTunnelOtnDefaultsAlias OBJECT-TYPE
    SYNTAX      SnmpAdminString
    MAX-ACCESS  read-only
    STATUS      current
    DESCRIPTION   ""
    ::=  { deployProvTunnelOtnDefaultsEntry 4 }

deployProvTunnelOtnDefaultsTunnelType OBJECT-TYPE
    SYNTAX      FspR7CpTunnelType
    MAX-ACCESS  read-only
    STATUS      current
    DESCRIPTION   ""
    ::=  { deployProvTunnelOtnDefaultsEntry 5 }

deployProvTunnelOtnDefaultsToTid OBJECT-TYPE
    SYNTAX      SnmpAdminString
    MAX-ACCESS  read-only
    STATUS      current
    DESCRIPTION   ""
    ::=  { deployProvTunnelOtnDefaultsEntry 6 }

deployProvTunnelOtnDefaultsToNodeIp OBJECT-TYPE
    SYNTAX      IpAddress
    MAX-ACCESS  read-only
    STATUS      current
    DESCRIPTION   ""
    ::=  { deployProvTunnelOtnDefaultsEntry 7 }

deployProvTunnelOtnDefaultsFromAid OBJECT-TYPE
    SYNTAX      EntityIndex
    MAX-ACCESS  read-only
    STATUS      current
    DESCRIPTION   ""
    ::=  { deployProvTunnelOtnDefaultsEntry 8 }

deployProvTunnelOtnDefaultsToAid OBJECT-TYPE
    SYNTAX      EntityIndex
    MAX-ACCESS  read-only
    STATUS      current
    DESCRIPTION   ""
    ::=  { deployProvTunnelOtnDefaultsEntry 9 }

deployProvTunnelOtnDefaultsConnectionDirection OBJECT-TYPE
    SYNTAX      FspR7Conn
    MAX-ACCESS  read-only
    STATUS      current
    DESCRIPTION   ""
    ::=  { deployProvTunnelOtnDefaultsEntry 10 }

deployProvTunnelOtnDefaultsFacilityType OBJECT-TYPE
    SYNTAX      FspR7InterfaceType
    MAX-ACCESS  read-only
    STATUS      current
    DESCRIPTION   ""
    ::=  { deployProvTunnelOtnDefaultsEntry 11 }

deployProvTunnelOtnDefaultsProvisionedPaths OBJECT-TYPE
    SYNTAX      SnmpAdminString
    MAX-ACCESS  read-only
    STATUS      current
    DESCRIPTION   ""
    ::=  { deployProvTunnelOtnDefaultsEntry 12 }

deployProvTunnelOtnDefaultsProtectionType OBJECT-TYPE
    SYNTAX      FspR7CpProtectionType
    MAX-ACCESS  read-only
    STATUS      current
    DESCRIPTION   ""
    ::=  { deployProvTunnelOtnDefaultsEntry 13 }

deployProvTunnelOtnDefaultsPin OBJECT-TYPE
    SYNTAX      FspR7CpPinning
    MAX-ACCESS  read-only
    STATUS      current
    DESCRIPTION   ""
    ::=  { deployProvTunnelOtnDefaultsEntry 14 }

deployProvTunnelOtnDefaultsRestorationType OBJECT-TYPE
    SYNTAX      FspR7CpRestorationType
    MAX-ACCESS  read-only
    STATUS      current
    DESCRIPTION   ""
    ::=  { deployProvTunnelOtnDefaultsEntry 15 }

deployProvTunnelOtnDefaultsMonitorEntities OBJECT-TYPE
    SYNTAX      FspR7EnableDisable
    MAX-ACCESS  read-only
    STATUS      current
    DESCRIPTION   ""
    ::=  { deployProvTunnelOtnDefaultsEntry 16 }

deployProvTunnelOtnDefaultsTunnelScope OBJECT-TYPE
    SYNTAX      FspR7CpTunnelScope
    MAX-ACCESS  read-only
    STATUS      current
    DESCRIPTION
        "Service Scope extending over either Client or Network Ports of Modules or Links (UN or NR) for Connection Segements" 
    ::=  { deployProvTunnelOtnDefaultsEntry 17 }

deployProvTunnelOtnDefaultsLayer OBJECT-TYPE
    SYNTAX      FspR7PacketsLayer
    MAX-ACCESS  read-only
    STATUS      current
    DESCRIPTION
        "Notional Layer of Advertisement on Packets on the LIF" 
    ::=  { deployProvTunnelOtnDefaultsEntry 18 }

deployProvTunnelOtnDefaultsOifUni OBJECT-TYPE
    SYNTAX      FspR7YesNo
    MAX-ACCESS  read-only
    STATUS      current
    DESCRIPTION
        "OIF UNI Tunnel" 
    ::=  { deployProvTunnelOtnDefaultsEntry 19 }

deployProvTunnelOtnDefaultsFromAidString OBJECT-TYPE
    SYNTAX      SnmpAdminString
    MAX-ACCESS  read-only
    STATUS      current
    DESCRIPTION
        "" 
    ::=  { deployProvTunnelOtnDefaultsEntry 20 }

deployProvTunnelOtnDefaultsToAidString OBJECT-TYPE
    SYNTAX      SnmpAdminString
    MAX-ACCESS  read-only
    STATUS      current
    DESCRIPTION
        "" 
    ::=  { deployProvTunnelOtnDefaultsEntry 21 }

deployProvTunnelOtnDefaultsExcludedPaths OBJECT-TYPE
    SYNTAX      SnmpAdminString
    MAX-ACCESS  read-only
    STATUS      current
    DESCRIPTION
        "Lists of Path Elements to be excluded" 
    ::=  { deployProvTunnelOtnDefaultsEntry 22 }

deployProvTunnelOtnDefaultsTerminationLevel OBJECT-TYPE
    SYNTAX      OhTerminationLevel
    MAX-ACCESS  read-only
    STATUS      current
    DESCRIPTION
        "Highest signal level hardware removes then generates for transmission." 
    ::=  { deployProvTunnelOtnDefaultsEntry 23 }

deployProvTunnelOtnDefaultsFecType OBJECT-TYPE
    SYNTAX      FspR7FecType
    MAX-ACCESS  read-only
    STATUS      current
    DESCRIPTION
        "Forward Error Correction (Only relevant where TYPE = OTU#)" 
    ::=  { deployProvTunnelOtnDefaultsEntry 24 }

deployProvTunnelOtnDefaultsStuff OBJECT-TYPE
    SYNTAX      FspR7Stuff
    MAX-ACCESS  read-only
    STATUS      current
    DESCRIPTION
        "Indicates if bit/byte stuffing is used in the transport signal." 
    ::=  { deployProvTunnelOtnDefaultsEntry 25 }

deployProvTunnelOtnDefaultsPreferPcs OBJECT-TYPE
    SYNTAX      FspR7YesNo
    MAX-ACCESS  read-only
    STATUS      current
    DESCRIPTION
        "Preferred Path Computation Engine (Server)" 
    ::=  { deployProvTunnelOtnDefaultsEntry 26 }

deployProvTunnelOtnDefaultsEroScope OBJECT-TYPE
    SYNTAX      SnmpAdminString
    MAX-ACCESS  read-only
    STATUS      current
    DESCRIPTION
        "Inclusion Route - Scope" 
    ::=  { deployProvTunnelOtnDefaultsEntry 27 }

deployProvTunnelOtnDefaultsEroLifeCycle OBJECT-TYPE
    SYNTAX      SnmpAdminString
    MAX-ACCESS  read-only
    STATUS      current
    DESCRIPTION
        "Inclusion Route - Life Cycle" 
    ::=  { deployProvTunnelOtnDefaultsEntry 28 }

deployProvTunnelOtnDefaultsXroScope OBJECT-TYPE
    SYNTAX      SnmpAdminString
    MAX-ACCESS  read-only
    STATUS      current
    DESCRIPTION
        "Exclusion Path Elements - Scope" 
    ::=  { deployProvTunnelOtnDefaultsEntry 29 }

deployProvTunnelOtnDefaultsXroLifeCycle OBJECT-TYPE
    SYNTAX      SnmpAdminString
    MAX-ACCESS  read-only
    STATUS      current
    DESCRIPTION
        "Exclusion Path Elements - Life Cycle" 
    ::=  { deployProvTunnelOtnDefaultsEntry 30 }

deployProvPathOtnTable OBJECT-TYPE
    SYNTAX      SEQUENCE OF DeployProvPathOtnEntry
    MAX-ACCESS  not-accessible
    STATUS      current
    DESCRIPTION   ""
    ::=  { controlPlaneDeployProv 106 }

deployProvPathOtnEntry OBJECT-TYPE
    SYNTAX      DeployProvPathOtnEntry
    MAX-ACCESS  not-accessible
    STATUS      current
    DESCRIPTION   ""
    INDEX       {
                  controlPlaneOtnEntityIndex
                }
    ::=  { deployProvPathOtnTable 1 }

DeployProvPathOtnEntry ::=  SEQUENCE
  { deployProvPathOtnRowStatus RowStatus,
    deployProvPathOtnPathId SnmpAdminString }

deployProvPathOtnRowStatus OBJECT-TYPE
    SYNTAX      RowStatus
    MAX-ACCESS  read-write
    STATUS      current
    DESCRIPTION
        "RowStatus" 
    ::=  { deployProvPathOtnEntry 1 }

deployProvPathOtnPathId OBJECT-TYPE
    SYNTAX      SnmpAdminString
    MAX-ACCESS  read-write
    STATUS      current
    DESCRIPTION   ""
    ::=  { deployProvPathOtnEntry 2 }

deployProvPathOtnCapTable OBJECT-TYPE
    SYNTAX      SEQUENCE OF DeployProvPathOtnCapEntry
    MAX-ACCESS  not-accessible
    STATUS      current
    DESCRIPTION   ""
    ::=  { controlPlaneDeployProv 107  }

deployProvPathOtnCapEntry OBJECT-TYPE
    SYNTAX      DeployProvPathOtnCapEntry
    MAX-ACCESS  not-accessible
    STATUS      current
    DESCRIPTION   ""
    INDEX       { controlPlaneOtnEntityIndex }
    ::=  { deployProvPathOtnCapTable 1 }

DeployProvPathOtnCapEntry ::=  SEQUENCE
  { deployProvPathOtnCapRowStatus FspR7RowStatusCaps,
    deployProvPathOtnCapPathId Integer32 }

deployProvPathOtnCapRowStatus OBJECT-TYPE
    SYNTAX      FspR7RowStatusCaps
    MAX-ACCESS  read-only
    STATUS      current
    DESCRIPTION
        "RowStatus" 
    ::=  { deployProvPathOtnCapEntry 1 }

deployProvPathOtnCapPathId OBJECT-TYPE
    SYNTAX      Integer32
    MAX-ACCESS  read-only
    STATUS      current
    DESCRIPTION   ""
    ::=  { deployProvPathOtnCapEntry 2 }

deployProvPathOtnDefaultsTable  OBJECT-TYPE
    SYNTAX      SEQUENCE OF DeployProvPathOtnDefaultsEntry
    MAX-ACCESS  not-accessible
    STATUS      current
    DESCRIPTION   ""
    ::=  { controlPlaneDeployProv 108  }

deployProvPathOtnDefaultsEntry OBJECT-TYPE
    SYNTAX      DeployProvPathOtnDefaultsEntry
    MAX-ACCESS  not-accessible
    STATUS      current
    DESCRIPTION   ""
    INDEX       { controlPlaneOtnEntityIndex }
    ::=  { deployProvPathOtnDefaultsTable 1 }

DeployProvPathOtnDefaultsEntry ::=  SEQUENCE
  { deployProvPathOtnDefaultsRowStatus RowStatus,
    deployProvPathOtnDefaultsPathId SnmpAdminString }

deployProvPathOtnDefaultsRowStatus OBJECT-TYPE
    SYNTAX      RowStatus
    MAX-ACCESS  read-only
    STATUS      current
    DESCRIPTION
        "RowStatus" 
    ::=  { deployProvPathOtnDefaultsEntry 1 }

deployProvPathOtnDefaultsPathId OBJECT-TYPE
    SYNTAX      SnmpAdminString
    MAX-ACCESS  read-only
    STATUS      current
    DESCRIPTION   ""
    ::=  { deployProvPathOtnDefaultsEntry 2 }

deployProvPathElementOtnTable OBJECT-TYPE
    SYNTAX      SEQUENCE OF DeployProvPathElementOtnEntry
    MAX-ACCESS  not-accessible
    STATUS      current
    DESCRIPTION   ""
    ::=  { controlPlaneDeployProv 109 }

deployProvPathElementOtnEntry OBJECT-TYPE
    SYNTAX      DeployProvPathElementOtnEntry
    MAX-ACCESS  not-accessible
    STATUS      current
    DESCRIPTION   ""
    INDEX       {
                  controlPlaneOtnEntityIndex
                }
    ::=  { deployProvPathElementOtnTable 1 }

DeployProvPathElementOtnEntry ::=  SEQUENCE
  { deployProvPathElementOtnRowStatus RowStatus,
    deployProvPathElementOtnTrafficEngineeringType FspR7CpTEType,
    deployProvPathElementOtnLifIp IpAddress,
    deployProvPathElementOtnNodeIp IpAddress,
    deployProvPathElementOtnTid SnmpAdminString,
    deployProvPathElementOtnLogicalInterfaceId Unsigned32,
    deployProvPathElementOtnTie FspR7CpTie,
    deployProvPathElementOtnUpTributaryODTUType FspR7OdtuType,
    deployProvPathElementOtnDownTributaryODTUType FspR7OdtuType,
    deployProvPathElementOtnUpTributaryPort SnmpAdminString,
    deployProvPathElementOtnDownTributaryPort SnmpAdminString,
    deployProvPathElementOtnUpTributarySlot SnmpAdminString,
    deployProvPathElementOtnDownTributarySlot SnmpAdminString,
    deployProvPathElementOtnUpTributaryTSMethod FspR7ManualAuto,
    deployProvPathElementOtnDownTributaryTSMethod FspR7ManualAuto,
    deployProvPathElementOtnDownTribPortStage2 SnmpAdminString,
    deployProvPathElementOtnUpTribPortStage2 SnmpAdminString }

deployProvPathElementOtnRowStatus OBJECT-TYPE
    SYNTAX      RowStatus
    MAX-ACCESS  read-write
    STATUS      current
    DESCRIPTION
        "RowStatus" 
    ::=  { deployProvPathElementOtnEntry 1 }

deployProvPathElementOtnTrafficEngineeringType OBJECT-TYPE
    SYNTAX      FspR7CpTEType
    MAX-ACCESS  read-write
    STATUS      current
    DESCRIPTION   ""
    ::=  { deployProvPathElementOtnEntry 2 }

deployProvPathElementOtnLifIp OBJECT-TYPE
    SYNTAX      IpAddress
    MAX-ACCESS  read-write
    STATUS      current
    DESCRIPTION   ""
    ::=  { deployProvPathElementOtnEntry 3 }

deployProvPathElementOtnNodeIp OBJECT-TYPE
    SYNTAX      IpAddress
    MAX-ACCESS  read-write
    STATUS      current
    DESCRIPTION   ""
    ::=  { deployProvPathElementOtnEntry 4 }

deployProvPathElementOtnTid OBJECT-TYPE
    SYNTAX      SnmpAdminString
    MAX-ACCESS  read-write
    STATUS      current
    DESCRIPTION   ""
    ::=  { deployProvPathElementOtnEntry 5 }

deployProvPathElementOtnLogicalInterfaceId OBJECT-TYPE
    SYNTAX      Unsigned32
    MAX-ACCESS  read-write
    STATUS      current
    DESCRIPTION   ""
    ::=  { deployProvPathElementOtnEntry 6 }

deployProvPathElementOtnTie OBJECT-TYPE
    SYNTAX      FspR7CpTie
    MAX-ACCESS  read-write
    STATUS      current
    DESCRIPTION   ""
    ::=  { deployProvPathElementOtnEntry 7 }

deployProvPathElementOtnUpTributaryODTUType OBJECT-TYPE
    SYNTAX      FspR7OdtuType
    MAX-ACCESS  read-write
    STATUS      current
    DESCRIPTION   ""
    ::=  { deployProvPathElementOtnEntry 8 }

deployProvPathElementOtnDownTributaryODTUType OBJECT-TYPE
    SYNTAX      FspR7OdtuType
    MAX-ACCESS  read-write
    STATUS      current
    DESCRIPTION   ""
    ::=  { deployProvPathElementOtnEntry 9 }

deployProvPathElementOtnUpTributaryPort OBJECT-TYPE
    SYNTAX      SnmpAdminString
    MAX-ACCESS  read-write
    STATUS      current
    DESCRIPTION   ""
    ::=  { deployProvPathElementOtnEntry 10 }

deployProvPathElementOtnDownTributaryPort OBJECT-TYPE
    SYNTAX      SnmpAdminString
    MAX-ACCESS  read-write
    STATUS      current
    DESCRIPTION   ""
    ::=  { deployProvPathElementOtnEntry 11 }

deployProvPathElementOtnUpTributarySlot OBJECT-TYPE
    SYNTAX      SnmpAdminString
    MAX-ACCESS  read-write
    STATUS      current
    DESCRIPTION   ""
    ::=  { deployProvPathElementOtnEntry 12 }

deployProvPathElementOtnDownTributarySlot OBJECT-TYPE
    SYNTAX      SnmpAdminString
    MAX-ACCESS  read-write
    STATUS      current
    DESCRIPTION   ""
    ::=  { deployProvPathElementOtnEntry 13 }

deployProvPathElementOtnUpTributaryTSMethod OBJECT-TYPE
    SYNTAX      FspR7ManualAuto
    MAX-ACCESS  read-write
    STATUS      current
    DESCRIPTION   ""
    ::=  { deployProvPathElementOtnEntry 14 }

deployProvPathElementOtnDownTributaryTSMethod OBJECT-TYPE
    SYNTAX      FspR7ManualAuto
    MAX-ACCESS  read-write
    STATUS      current
    DESCRIPTION   ""
    ::=  { deployProvPathElementOtnEntry 15 }

deployProvPathElementOtnDownTribPortStage2 OBJECT-TYPE
    SYNTAX      SnmpAdminString
    MAX-ACCESS  read-write
    STATUS      current
    DESCRIPTION
        "Downstream Tributary Port (TRMT) - Stage2" 
    ::=  { deployProvPathElementOtnEntry 16 }

deployProvPathElementOtnUpTribPortStage2 OBJECT-TYPE
    SYNTAX      SnmpAdminString
    MAX-ACCESS  read-write
    STATUS      current
    DESCRIPTION
        "Upstream Tributary Port (RCV) - Stage2" 
    ::=  { deployProvPathElementOtnEntry 17 }

deployProvPathElementOtnCapTable OBJECT-TYPE
    SYNTAX      SEQUENCE OF DeployProvPathElementOtnCapEntry
    MAX-ACCESS  not-accessible
    STATUS      current
    DESCRIPTION   ""
    ::=  { controlPlaneDeployProv 110  }

deployProvPathElementOtnCapEntry OBJECT-TYPE
    SYNTAX      DeployProvPathElementOtnCapEntry
    MAX-ACCESS  not-accessible
    STATUS      current
    DESCRIPTION   ""
    INDEX       { controlPlaneOtnEntityIndex }
    ::=  { deployProvPathElementOtnCapTable 1 }

DeployProvPathElementOtnCapEntry ::=  SEQUENCE
  { deployProvPathElementOtnCapRowStatus FspR7RowStatusCaps,
    deployProvPathElementOtnCapTrafficEngineeringType FspR7CpTETypeCaps,
    deployProvPathElementOtnCapLifIp FspR7YesNo,
    deployProvPathElementOtnCapNodeIp FspR7YesNo,
    deployProvPathElementOtnCapTid Integer32,
    deployProvPathElementOtnCapLogicalInterfaceId FspR7Unsigned32Caps,
    deployProvPathElementOtnCapTie FspR7CpTieCaps,
    deployProvPathElementOtnCapUpTributaryODTUType FspR7OdtuTypeCaps,
    deployProvPathElementOtnCapDownTributaryODTUType FspR7OdtuTypeCaps,
    deployProvPathElementOtnCapUpTributaryPort SnmpAdminString,
    deployProvPathElementOtnCapDownTributaryPort SnmpAdminString,
    deployProvPathElementOtnCapUpTributarySlot SnmpAdminString,
    deployProvPathElementOtnCapDownTributarySlot SnmpAdminString,
    deployProvPathElementOtnCapUpTributaryTSMethod FspR7ManualAutoCaps,
    deployProvPathElementOtnCapDownTributaryTSMethod FspR7ManualAutoCaps,
    deployProvPathElementOtnCapDownTribPortStage2 SnmpAdminString,
    deployProvPathElementOtnCapUpTribPortStage2 SnmpAdminString }

deployProvPathElementOtnCapRowStatus OBJECT-TYPE
    SYNTAX      FspR7RowStatusCaps
    MAX-ACCESS  read-only
    STATUS      current
    DESCRIPTION
        "RowStatus" 
    ::=  { deployProvPathElementOtnCapEntry 1 }

deployProvPathElementOtnCapTrafficEngineeringType OBJECT-TYPE
    SYNTAX      FspR7CpTETypeCaps
    MAX-ACCESS  read-only
    STATUS      current
    DESCRIPTION   ""
    ::=  { deployProvPathElementOtnCapEntry 2 }

deployProvPathElementOtnCapLifIp OBJECT-TYPE
    SYNTAX      FspR7YesNo
    MAX-ACCESS  read-only
    STATUS      current
    DESCRIPTION   ""
    ::=  { deployProvPathElementOtnCapEntry 3 }

deployProvPathElementOtnCapNodeIp OBJECT-TYPE
    SYNTAX      FspR7YesNo
    MAX-ACCESS  read-only
    STATUS      current
    DESCRIPTION   ""
    ::=  { deployProvPathElementOtnCapEntry 4 }

deployProvPathElementOtnCapTid OBJECT-TYPE
    SYNTAX      Integer32
    MAX-ACCESS  read-only
    STATUS      current
    DESCRIPTION   ""
    ::=  { deployProvPathElementOtnCapEntry 5 }

deployProvPathElementOtnCapLogicalInterfaceId OBJECT-TYPE
    SYNTAX      FspR7Unsigned32Caps
    MAX-ACCESS  read-only
    STATUS      current
    DESCRIPTION   ""
    ::=  { deployProvPathElementOtnCapEntry 6 }

deployProvPathElementOtnCapTie OBJECT-TYPE
    SYNTAX      FspR7CpTieCaps
    MAX-ACCESS  read-only
    STATUS      current
    DESCRIPTION   ""
    ::=  { deployProvPathElementOtnCapEntry 7 }

deployProvPathElementOtnCapUpTributaryODTUType OBJECT-TYPE
    SYNTAX      FspR7OdtuTypeCaps
    MAX-ACCESS  read-only
    STATUS      current
    DESCRIPTION   ""
    ::=  { deployProvPathElementOtnCapEntry 8 }

deployProvPathElementOtnCapDownTributaryODTUType OBJECT-TYPE
    SYNTAX      FspR7OdtuTypeCaps
    MAX-ACCESS  read-only
    STATUS      current
    DESCRIPTION   ""
    ::=  { deployProvPathElementOtnCapEntry 9 }

deployProvPathElementOtnCapUpTributaryPort OBJECT-TYPE
    SYNTAX      SnmpAdminString
    MAX-ACCESS  read-only
    STATUS      current
    DESCRIPTION   ""
    ::=  { deployProvPathElementOtnCapEntry 10 }

deployProvPathElementOtnCapDownTributaryPort OBJECT-TYPE
    SYNTAX      SnmpAdminString
    MAX-ACCESS  read-only
    STATUS      current
    DESCRIPTION   ""
    ::=  { deployProvPathElementOtnCapEntry 11 }

deployProvPathElementOtnCapUpTributarySlot OBJECT-TYPE
    SYNTAX      SnmpAdminString
    MAX-ACCESS  read-only
    STATUS      current
    DESCRIPTION   ""
    ::=  { deployProvPathElementOtnCapEntry 12 }

deployProvPathElementOtnCapDownTributarySlot OBJECT-TYPE
    SYNTAX      SnmpAdminString
    MAX-ACCESS  read-only
    STATUS      current
    DESCRIPTION   ""
    ::=  { deployProvPathElementOtnCapEntry 13 }

deployProvPathElementOtnCapUpTributaryTSMethod OBJECT-TYPE
    SYNTAX      FspR7ManualAutoCaps
    MAX-ACCESS  read-only
    STATUS      current
    DESCRIPTION   ""
    ::=  { deployProvPathElementOtnCapEntry 14 }

deployProvPathElementOtnCapDownTributaryTSMethod OBJECT-TYPE
    SYNTAX      FspR7ManualAutoCaps
    MAX-ACCESS  read-only
    STATUS      current
    DESCRIPTION   ""
    ::=  { deployProvPathElementOtnCapEntry 15 }

deployProvPathElementOtnCapDownTribPortStage2 OBJECT-TYPE
    SYNTAX      SnmpAdminString
    MAX-ACCESS  read-only
    STATUS      current
    DESCRIPTION
        "Downstream Tributary Port (TRMT) - Stage2" 
    ::=  { deployProvPathElementOtnCapEntry 16 }

deployProvPathElementOtnCapUpTribPortStage2 OBJECT-TYPE
    SYNTAX      SnmpAdminString
    MAX-ACCESS  read-only
    STATUS      current
    DESCRIPTION
        "Upstream Tributary Port (RCV) - Stage2" 
    ::=  { deployProvPathElementOtnCapEntry 17 }

deployProvPathElementOtnDefaultsTable  OBJECT-TYPE
    SYNTAX      SEQUENCE OF DeployProvPathElementOtnDefaultsEntry
    MAX-ACCESS  not-accessible
    STATUS      current
    DESCRIPTION   ""
    ::=  { controlPlaneDeployProv 111  }

deployProvPathElementOtnDefaultsEntry OBJECT-TYPE
    SYNTAX      DeployProvPathElementOtnDefaultsEntry
    MAX-ACCESS  not-accessible
    STATUS      current
    DESCRIPTION   ""
    INDEX       { controlPlaneOtnEntityIndex }
    ::=  { deployProvPathElementOtnDefaultsTable 1 }

DeployProvPathElementOtnDefaultsEntry ::=  SEQUENCE
  { deployProvPathElementOtnDefaultsRowStatus RowStatus,
    deployProvPathElementOtnDefaultsTrafficEngineeringType FspR7CpTEType,
    deployProvPathElementOtnDefaultsLifIp IpAddress,
    deployProvPathElementOtnDefaultsNodeIp IpAddress,
    deployProvPathElementOtnDefaultsTid SnmpAdminString,
    deployProvPathElementOtnDefaultsLogicalInterfaceId Unsigned32,
    deployProvPathElementOtnDefaultsTie FspR7CpTie,
    deployProvPathElementOtnDefaultsUpTributaryODTUType FspR7OdtuType,
    deployProvPathElementOtnDefaultsDownTributaryODTUType FspR7OdtuType,
    deployProvPathElementOtnDefaultsUpTributaryPort SnmpAdminString,
    deployProvPathElementOtnDefaultsDownTributaryPort SnmpAdminString,
    deployProvPathElementOtnDefaultsUpTributarySlot SnmpAdminString,
    deployProvPathElementOtnDefaultsDownTributarySlot SnmpAdminString,
    deployProvPathElementOtnDefaultsUpTributaryTSMethod FspR7ManualAuto,
    deployProvPathElementOtnDefaultsDownTributaryTSMethod FspR7ManualAuto,
    deployProvPathElementOtnDefaultsDownTribPortStage2 SnmpAdminString,
    deployProvPathElementOtnDefaultsUpTribPortStage2 SnmpAdminString }

deployProvPathElementOtnDefaultsRowStatus OBJECT-TYPE
    SYNTAX      RowStatus
    MAX-ACCESS  read-only
    STATUS      current
    DESCRIPTION
        "RowStatus" 
    ::=  { deployProvPathElementOtnDefaultsEntry 1 }

deployProvPathElementOtnDefaultsTrafficEngineeringType OBJECT-TYPE
    SYNTAX      FspR7CpTEType
    MAX-ACCESS  read-only
    STATUS      current
    DESCRIPTION   ""
    ::=  { deployProvPathElementOtnDefaultsEntry 2 }

deployProvPathElementOtnDefaultsLifIp OBJECT-TYPE
    SYNTAX      IpAddress
    MAX-ACCESS  read-only
    STATUS      current
    DESCRIPTION   ""
    ::=  { deployProvPathElementOtnDefaultsEntry 3 }

deployProvPathElementOtnDefaultsNodeIp OBJECT-TYPE
    SYNTAX      IpAddress
    MAX-ACCESS  read-only
    STATUS      current
    DESCRIPTION   ""
    ::=  { deployProvPathElementOtnDefaultsEntry 4 }

deployProvPathElementOtnDefaultsTid OBJECT-TYPE
    SYNTAX      SnmpAdminString
    MAX-ACCESS  read-only
    STATUS      current
    DESCRIPTION   ""
    ::=  { deployProvPathElementOtnDefaultsEntry 5 }

deployProvPathElementOtnDefaultsLogicalInterfaceId OBJECT-TYPE
    SYNTAX      Unsigned32
    MAX-ACCESS  read-only
    STATUS      current
    DESCRIPTION   ""
    ::=  { deployProvPathElementOtnDefaultsEntry 6 }

deployProvPathElementOtnDefaultsTie OBJECT-TYPE
    SYNTAX      FspR7CpTie
    MAX-ACCESS  read-only
    STATUS      current
    DESCRIPTION   ""
    ::=  { deployProvPathElementOtnDefaultsEntry 7 }

deployProvPathElementOtnDefaultsUpTributaryODTUType OBJECT-TYPE
    SYNTAX      FspR7OdtuType
    MAX-ACCESS  read-only
    STATUS      current
    DESCRIPTION   ""
    ::=  { deployProvPathElementOtnDefaultsEntry 8 }

deployProvPathElementOtnDefaultsDownTributaryODTUType OBJECT-TYPE
    SYNTAX      FspR7OdtuType
    MAX-ACCESS  read-only
    STATUS      current
    DESCRIPTION   ""
    ::=  { deployProvPathElementOtnDefaultsEntry 9 }

deployProvPathElementOtnDefaultsUpTributaryPort OBJECT-TYPE
    SYNTAX      SnmpAdminString
    MAX-ACCESS  read-only
    STATUS      current
    DESCRIPTION   ""
    ::=  { deployProvPathElementOtnDefaultsEntry 10 }

deployProvPathElementOtnDefaultsDownTributaryPort OBJECT-TYPE
    SYNTAX      SnmpAdminString
    MAX-ACCESS  read-only
    STATUS      current
    DESCRIPTION   ""
    ::=  { deployProvPathElementOtnDefaultsEntry 11 }

deployProvPathElementOtnDefaultsUpTributarySlot OBJECT-TYPE
    SYNTAX      SnmpAdminString
    MAX-ACCESS  read-only
    STATUS      current
    DESCRIPTION   ""
    ::=  { deployProvPathElementOtnDefaultsEntry 12 }

deployProvPathElementOtnDefaultsDownTributarySlot OBJECT-TYPE
    SYNTAX      SnmpAdminString
    MAX-ACCESS  read-only
    STATUS      current
    DESCRIPTION   ""
    ::=  { deployProvPathElementOtnDefaultsEntry 13 }

deployProvPathElementOtnDefaultsUpTributaryTSMethod OBJECT-TYPE
    SYNTAX      FspR7ManualAuto
    MAX-ACCESS  read-only
    STATUS      current
    DESCRIPTION   ""
    ::=  { deployProvPathElementOtnDefaultsEntry 14 }

deployProvPathElementOtnDefaultsDownTributaryTSMethod OBJECT-TYPE
    SYNTAX      FspR7ManualAuto
    MAX-ACCESS  read-only
    STATUS      current
    DESCRIPTION   ""
    ::=  { deployProvPathElementOtnDefaultsEntry 15 }

deployProvPathElementOtnDefaultsDownTribPortStage2 OBJECT-TYPE
    SYNTAX      SnmpAdminString
    MAX-ACCESS  read-only
    STATUS      current
    DESCRIPTION
        "Downstream Tributary Port (TRMT) - Stage2" 
    ::=  { deployProvPathElementOtnDefaultsEntry 16 }

deployProvPathElementOtnDefaultsUpTribPortStage2 OBJECT-TYPE
    SYNTAX      SnmpAdminString
    MAX-ACCESS  read-only
    STATUS      current
    DESCRIPTION
        "Upstream Tributary Port (RCV) - Stage2" 
    ::=  { deployProvPathElementOtnDefaultsEntry 17 }

deployProvCopyPathOtnTable OBJECT-TYPE
    SYNTAX      SEQUENCE OF DeployProvCopyPathOtnEntry
    MAX-ACCESS  not-accessible
    STATUS      current
    DESCRIPTION   ""
    ::=  { controlPlaneDeployProv 112 }

deployProvCopyPathOtnEntry OBJECT-TYPE
    SYNTAX      DeployProvCopyPathOtnEntry
    MAX-ACCESS  not-accessible
    STATUS      current
    DESCRIPTION   ""
    INDEX       {
                  controlPlaneOtnEntityIndex
                }
    ::=  { deployProvCopyPathOtnTable 1 }

DeployProvCopyPathOtnEntry ::=  SEQUENCE
  { deployProvCopyPathOtnRowStatus RowStatus,
    deployProvCopyPathOtnSourcePathIndex EntityIndex,
    deployProvCopyPathOtnPathId SnmpAdminString }

deployProvCopyPathOtnRowStatus OBJECT-TYPE
    SYNTAX      RowStatus
    MAX-ACCESS  read-write
    STATUS      current
    DESCRIPTION
        "RowStatus" 
    ::=  { deployProvCopyPathOtnEntry 1 }

deployProvCopyPathOtnSourcePathIndex OBJECT-TYPE
    SYNTAX      EntityIndex
    MAX-ACCESS  read-write
    STATUS      current
    DESCRIPTION   ""
    ::=  { deployProvCopyPathOtnEntry 2 }

deployProvCopyPathOtnPathId OBJECT-TYPE
    SYNTAX      SnmpAdminString
    MAX-ACCESS  read-write
    STATUS      current
    DESCRIPTION   ""
    ::=  { deployProvCopyPathOtnEntry 3 }

deployProvCopyPathOtnCapTable OBJECT-TYPE
    SYNTAX      SEQUENCE OF DeployProvCopyPathOtnCapEntry
    MAX-ACCESS  not-accessible
    STATUS      current
    DESCRIPTION   ""
    ::=  { controlPlaneDeployProv 113  }

deployProvCopyPathOtnCapEntry OBJECT-TYPE
    SYNTAX      DeployProvCopyPathOtnCapEntry
    MAX-ACCESS  not-accessible
    STATUS      current
    DESCRIPTION   ""
    INDEX       { controlPlaneOtnEntityIndex }
    ::=  { deployProvCopyPathOtnCapTable 1 }

DeployProvCopyPathOtnCapEntry ::=  SEQUENCE
  { deployProvCopyPathOtnCapRowStatus FspR7RowStatusCaps,
    deployProvCopyPathOtnCapSourcePathIndex Integer32,
    deployProvCopyPathOtnCapPathId Integer32 }

deployProvCopyPathOtnCapRowStatus OBJECT-TYPE
    SYNTAX      FspR7RowStatusCaps
    MAX-ACCESS  read-only
    STATUS      current
    DESCRIPTION
        "RowStatus" 
    ::=  { deployProvCopyPathOtnCapEntry 1 }

deployProvCopyPathOtnCapSourcePathIndex OBJECT-TYPE
    SYNTAX      Integer32
    MAX-ACCESS  read-only
    STATUS      current
    DESCRIPTION   ""
    ::=  { deployProvCopyPathOtnCapEntry 2 }

deployProvCopyPathOtnCapPathId OBJECT-TYPE
    SYNTAX      Integer32
    MAX-ACCESS  read-only
    STATUS      current
    DESCRIPTION   ""
    ::=  { deployProvCopyPathOtnCapEntry 3 }

deployProvCopyPathOtnDefaultsTable  OBJECT-TYPE
    SYNTAX      SEQUENCE OF DeployProvCopyPathOtnDefaultsEntry
    MAX-ACCESS  not-accessible
    STATUS      current
    DESCRIPTION   ""
    ::=  { controlPlaneDeployProv 114  }

deployProvCopyPathOtnDefaultsEntry OBJECT-TYPE
    SYNTAX      DeployProvCopyPathOtnDefaultsEntry
    MAX-ACCESS  not-accessible
    STATUS      current
    DESCRIPTION   ""
    INDEX       { controlPlaneOtnEntityIndex }
    ::=  { deployProvCopyPathOtnDefaultsTable 1 }

DeployProvCopyPathOtnDefaultsEntry ::=  SEQUENCE
  { deployProvCopyPathOtnDefaultsRowStatus RowStatus,
    deployProvCopyPathOtnDefaultsSourcePathIndex EntityIndex,
    deployProvCopyPathOtnDefaultsPathId SnmpAdminString }

deployProvCopyPathOtnDefaultsRowStatus OBJECT-TYPE
    SYNTAX      RowStatus
    MAX-ACCESS  read-only
    STATUS      current
    DESCRIPTION
        "RowStatus" 
    ::=  { deployProvCopyPathOtnDefaultsEntry 1 }

deployProvCopyPathOtnDefaultsSourcePathIndex OBJECT-TYPE
    SYNTAX      EntityIndex
    MAX-ACCESS  read-only
    STATUS      current
    DESCRIPTION   ""
    ::=  { deployProvCopyPathOtnDefaultsEntry 2 }

deployProvCopyPathOtnDefaultsPathId OBJECT-TYPE
    SYNTAX      SnmpAdminString
    MAX-ACCESS  read-only
    STATUS      current
    DESCRIPTION   ""
    ::=  { deployProvCopyPathOtnDefaultsEntry 3 }

unusedDiversity OBJECT-TYPE
    SYNTAX      Unsigned32
    MAX-ACCESS  read-only
    STATUS      current
    DESCRIPTION
        "This parameter is used to retrieve unused Diversity index, needed
         to provision new entity. If 0 returned no free slots available for provisioning.
        "
    ::=  { controlPlaneDeployProv 115 }

deployProvDiversityPathTable OBJECT-TYPE
    SYNTAX      SEQUENCE OF DeployProvDiversityPathEntry
    MAX-ACCESS  not-accessible
    STATUS      current
    DESCRIPTION   ""
    ::=  { controlPlaneDeployProv 116 }

deployProvDiversityPathEntry OBJECT-TYPE
    SYNTAX      DeployProvDiversityPathEntry
    MAX-ACCESS  not-accessible
    STATUS      current
    DESCRIPTION   ""
    INDEX       {
                  deployProvDiversityPathIndex
                }
    ::=  { deployProvDiversityPathTable 1 }

DeployProvDiversityPathEntry ::=  SEQUENCE
  { deployProvDiversityPathIndex EntityIndex,
    deployProvDiversityPathRowStatus RowStatus,
    deployProvDiversityPathDvName SnmpAdminString,
    deployProvDiversityPathDvScope FspR7DvScope,
    deployProvDiversityPathTunnelName SnmpAdminString,
    deployProvDiversityPathTunnelNo Unsigned32,
    deployProvDiversityPathFromNodeIp IpAddress,
    deployProvDiversityPathToNodeIp IpAddress,
    deployProvDiversityPathDisjointedness FspR7Disjointedness,
    deployProvDiversityPathDiversifyPath FspR7DiversifyPath,
    deployProvDiversityPathReRoute FspR7NoYes,
    deployProvDiversityPathLifeCycle FspR7LifeCycle,
    deployProvDiversityPathTunnelAid SnmpAdminString }

deployProvDiversityPathIndex OBJECT-TYPE
    SYNTAX      EntityIndex
    MAX-ACCESS  accessible-for-notify
    STATUS      current
    DESCRIPTION   "Existing adress index"
    ::=  { deployProvDiversityPathEntry 1 }

deployProvDiversityPathRowStatus OBJECT-TYPE
    SYNTAX      RowStatus
    MAX-ACCESS  read-write
    STATUS      current
    DESCRIPTION
        "RowStatus" 
    ::=  { deployProvDiversityPathEntry 2 }

deployProvDiversityPathDvName OBJECT-TYPE
    SYNTAX      SnmpAdminString
    MAX-ACCESS  read-write
    STATUS      current
    DESCRIPTION
        "Diversity Name" 
    ::=  { deployProvDiversityPathEntry 3 }

deployProvDiversityPathDvScope OBJECT-TYPE
    SYNTAX      FspR7DvScope
    MAX-ACCESS  read-write
    STATUS      current
    DESCRIPTION
        "Diversity Scope" 
    ::=  { deployProvDiversityPathEntry 4 }

deployProvDiversityPathTunnelName OBJECT-TYPE
    SYNTAX      SnmpAdminString
    MAX-ACCESS  read-write
    STATUS      current
    DESCRIPTION
        "Tunnel Name" 
    ::=  { deployProvDiversityPathEntry 5 }

deployProvDiversityPathTunnelNo OBJECT-TYPE
    SYNTAX      Unsigned32
    MAX-ACCESS  read-write
    STATUS      current
    DESCRIPTION
        "Tunnel Number also called Service ID. This never changes while the tunnel is in service. (internal: serviceID.tunnelID)" 
    ::=  { deployProvDiversityPathEntry 6 }

deployProvDiversityPathFromNodeIp OBJECT-TYPE
    SYNTAX      IpAddress
    MAX-ACCESS  read-write
    STATUS      current
    DESCRIPTION
        "Source Node IP" 
    ::=  { deployProvDiversityPathEntry 7 }

deployProvDiversityPathToNodeIp OBJECT-TYPE
    SYNTAX      IpAddress
    MAX-ACCESS  read-write
    STATUS      current
    DESCRIPTION
        "Destination Node IP" 
    ::=  { deployProvDiversityPathEntry 8 }

deployProvDiversityPathDisjointedness OBJECT-TYPE
    SYNTAX      FspR7Disjointedness
    MAX-ACCESS  read-write
    STATUS      current
    DESCRIPTION
        "Defines how a tunnel must be separated from the reference tunnel." 
    ::=  { deployProvDiversityPathEntry 9 }

deployProvDiversityPathDiversifyPath OBJECT-TYPE
    SYNTAX      FspR7DiversifyPath
    MAX-ACCESS  read-write
    STATUS      current
    DESCRIPTION
        "Path Types Control Plane avoids in when specifing the diverse tunnels." 
    ::=  { deployProvDiversityPathEntry 10 }

deployProvDiversityPathReRoute OBJECT-TYPE
    SYNTAX      FspR7NoYes
    MAX-ACCESS  read-write
    STATUS      current
    DESCRIPTION
        "Reroute" 
    ::=  { deployProvDiversityPathEntry 11 }

deployProvDiversityPathLifeCycle OBJECT-TYPE
    SYNTAX      FspR7LifeCycle
    MAX-ACCESS  read-write
    STATUS      current
    DESCRIPTION
        "Defines time period where tunnels must be kept separate from the reference tunnel." 
    ::=  { deployProvDiversityPathEntry 12 }

deployProvDiversityPathTunnelAid OBJECT-TYPE
    SYNTAX      SnmpAdminString
    MAX-ACCESS  read-write
    STATUS      current
    DESCRIPTION
        "Supporting Tunnel" 
    ::=  { deployProvDiversityPathEntry 13 }

areaIdCapTable OBJECT-TYPE
    SYNTAX      SEQUENCE OF AreaIdCapEntry
    MAX-ACCESS  not-accessible
    STATUS      deprecated
    DESCRIPTION   "This table is used to get capabilities for AREAID parameter. Regular
         cap tables including AREAID show the length of output string.
         Enumerator YES/NO in regular cap tables shows if there are capabilities or value 0
         which means 'no capabilities'.
         The second index (n) is used to devide the output string to n string blocks.
         Each block has a maximum of 512 bytes. n = output string / 512."
    ::=  { parameterCapabilities 10 }

areaIdCapEntry OBJECT-TYPE
    SYNTAX      AreaIdCapEntry
    MAX-ACCESS  not-accessible
    STATUS      deprecated
    DESCRIPTION   ""
    INDEX       {
                  entityIndex,
                  areaIdCapIndexCap
                }
    ::=  { areaIdCapTable 1 }

AreaIdCapEntry ::=  SEQUENCE
  { areaIdCapIndexCap EntityIndex,
    areaIdCapStringCap SnmpAdminString }

areaIdCapIndexCap OBJECT-TYPE
    SYNTAX      EntityIndex
    MAX-ACCESS  accessible-for-notify
    STATUS      current
    DESCRIPTION   "Used to display capability value per index. The number of capabilities determines the number of indexes."
    ::=  { areaIdCapEntry 1 }

areaIdCapStringCap OBJECT-TYPE
    SYNTAX      SnmpAdminString
    MAX-ACCESS  read-only
    STATUS      current
    DESCRIPTION
        "" 
    ::=  { areaIdCapEntry 2 }

nendIpCapTable OBJECT-TYPE
    SYNTAX      SEQUENCE OF NendIpCapEntry
    MAX-ACCESS  not-accessible
    STATUS      current
    DESCRIPTION   "This table is used to get capabilities for NENDIP parameter.
         Enumerator YES/NO in regular cap tables shows if there are capabilities or no.
         No values for specific entity means 'no capabilities'.
         The second index (n) is used to devide the output string to n string blocks.
         Each block has a maximum of 255 bytes. n = output string / 255."
    ::=  { parameterCapabilities 11 }

nendIpCapEntry OBJECT-TYPE
    SYNTAX      NendIpCapEntry
    MAX-ACCESS  not-accessible
    STATUS      current
    DESCRIPTION   ""
    INDEX       {
                  entityIndex,
                  nendIpCapIndexCap
                }
    ::=  { nendIpCapTable 1 }

NendIpCapEntry ::=  SEQUENCE
  { nendIpCapIndexCap EntityIndex,
    nendIpCapStringCap SnmpAdminString }

nendIpCapIndexCap OBJECT-TYPE
    SYNTAX      EntityIndex
    MAX-ACCESS  accessible-for-notify
    STATUS      current
    DESCRIPTION   "Used to display capability value per index. The number of capabilities determines the number of indexes."
    ::=  { nendIpCapEntry 1 }

nendIpCapStringCap OBJECT-TYPE
    SYNTAX      SnmpAdminString
    MAX-ACCESS  read-only
    STATUS      current
    DESCRIPTION
        "" 
    ::=  { nendIpCapEntry 2 }

areaAidCapTable OBJECT-TYPE
    SYNTAX      SEQUENCE OF AreaAidCapEntry
    MAX-ACCESS  not-accessible
    STATUS      current
    DESCRIPTION   "This table is used to get capabilities for AREAAID parameter. Regular
         cap tables including AREAAID show the length of output string.
         Enumerator YES/NO in regular cap tables shows if there are capabilities or value 0
         which means 'no capabilities'.
         The second index (n) is used to devide the output string to n string blocks.
         Each block has a maximum of 255 bytes. n = output string / 255."
    ::=  { parameterCapabilities 12 }

areaAidCapEntry OBJECT-TYPE
    SYNTAX      AreaAidCapEntry
    MAX-ACCESS  not-accessible
    STATUS      current
    DESCRIPTION   ""
    INDEX       {
                  entityIndex,
                  areaIdCapIndexCap
                }
    ::=  { areaAidCapTable 1 }

AreaAidCapEntry ::=  SEQUENCE
  { areaAidCapIndexCap EntityIndex,
    areaAidCapStringCap SnmpAdminString }

areaAidCapIndexCap OBJECT-TYPE
    SYNTAX      EntityIndex
    MAX-ACCESS  accessible-for-notify
    STATUS      current
    DESCRIPTION   "Used to display capability value per index. The number of capabilities determines the number of indexes."
    ::=  { areaAidCapEntry 1 }

areaAidCapStringCap OBJECT-TYPE
    SYNTAX      SnmpAdminString
    MAX-ACCESS  read-only
    STATUS      current
    DESCRIPTION
        "" 
    ::=  { areaAidCapEntry 2 }

thresholdOtuTable OBJECT-TYPE
    SYNTAX      SEQUENCE OF ThresholdOtuEntry
    MAX-ACCESS  not-accessible
    STATUS      current
    DESCRIPTION   ""
    ::=  { performanceAdmin 1 }

thresholdOtuEntry OBJECT-TYPE
    SYNTAX      ThresholdOtuEntry
    MAX-ACCESS  not-accessible
    STATUS      current
    DESCRIPTION   ""
    INDEX       {
                  entityIndex
                }
    ::=  { thresholdOtuTable 1 }

ThresholdOtuEntry ::=  SEQUENCE
  { thresholdOtuESHighThres15min Unsigned32,
    thresholdOtuESHighThres1day Unsigned32,
    thresholdOtuSESHighThres15min Unsigned32,
    thresholdOtuSESHighThres1day Unsigned32,
    thresholdOtuBbeHighThres15min Counter64String,
    thresholdOtuBbeHighThres1day Counter64String,
    thresholdOtuUASHighThres15min Unsigned32,
    thresholdOtuUASHighThres1day Unsigned32 }

thresholdOtuESHighThres15min OBJECT-TYPE
    SYNTAX      Unsigned32 (0..900 | 4294967295)
    MAX-ACCESS  read-write
    STATUS      current
    DESCRIPTION
        "OTU Errored Seconds 15 Minute Threshold" 
    ::=  { thresholdOtuEntry 1 }

thresholdOtuESHighThres1day OBJECT-TYPE
    SYNTAX      Unsigned32 (0..86400 | 4294967295)
    MAX-ACCESS  read-write
    STATUS      current
    DESCRIPTION
        "OTU Errored Seconds 1 Day Threshold" 
    ::=  { thresholdOtuEntry 2 }

thresholdOtuSESHighThres15min OBJECT-TYPE
    SYNTAX      Unsigned32 (0..900 | 4294967295)
    MAX-ACCESS  read-write
    STATUS      current
    DESCRIPTION
        "OTU Severely Errored Seconds 15 Minute Threshold" 
    ::=  { thresholdOtuEntry 3 }

thresholdOtuSESHighThres1day OBJECT-TYPE
    SYNTAX      Unsigned32 (0..86400 | 4294967295)
    MAX-ACCESS  read-write
    STATUS      current
    DESCRIPTION
        "OTU Severely Errored Seconds 1 Day Threshold" 
    ::=  { thresholdOtuEntry 4 }

thresholdOtuBbeHighThres15min OBJECT-TYPE
    SYNTAX      Counter64String
    MAX-ACCESS  read-write
    STATUS      current
    DESCRIPTION
        "OTU Background Block Errors 15 Minute Threshold" 
    ::=  { thresholdOtuEntry 5 }

thresholdOtuBbeHighThres1day OBJECT-TYPE
    SYNTAX      Counter64String
    MAX-ACCESS  read-write
    STATUS      current
    DESCRIPTION
        "OTU Background Block Errors 1 Day Threshold" 
    ::=  { thresholdOtuEntry 6 }

thresholdOtuUASHighThres15min OBJECT-TYPE
    SYNTAX      Unsigned32 (0..900 | 4294967295)
    MAX-ACCESS  read-write
    STATUS      current
    DESCRIPTION
        "OTU Unavailable Seconds 15 Minute Threshold" 
    ::=  { thresholdOtuEntry 7 }

thresholdOtuUASHighThres1day OBJECT-TYPE
    SYNTAX      Unsigned32 (0..86400 | 4294967295)
    MAX-ACCESS  read-write
    STATUS      current
    DESCRIPTION
        "OTU Unavailable Seconds 1 Day Threshold" 
    ::=  { thresholdOtuEntry 8 }

thresholdOduTable OBJECT-TYPE
    SYNTAX      SEQUENCE OF ThresholdOduEntry
    MAX-ACCESS  not-accessible
    STATUS      current
    DESCRIPTION   ""
    ::=  { performanceAdmin 2 }

thresholdOduEntry OBJECT-TYPE
    SYNTAX      ThresholdOduEntry
    MAX-ACCESS  not-accessible
    STATUS      current
    DESCRIPTION   ""
    INDEX       {
                  entityIndex
                }
    ::=  { thresholdOduTable 1 }

ThresholdOduEntry ::=  SEQUENCE
  { thresholdOduESHighThres15min Unsigned32,
    thresholdOduESHighThres1day Unsigned32,
    thresholdOduSESHighThres15min Unsigned32,
    thresholdOduSESHighThres1day Unsigned32,
    thresholdOduBbeHighThres15min Counter64String,
    thresholdOduBbeHighThres1day Counter64String,
    thresholdOduUASHighThres15min Unsigned32,
    thresholdOduUASHighThres1day Unsigned32 }

thresholdOduESHighThres15min OBJECT-TYPE
    SYNTAX      Unsigned32 (0..900 | 4294967295)
    MAX-ACCESS  read-write
    STATUS      current
    DESCRIPTION
        "ODU Errored Seconds 15 Minute Threshold" 
    ::=  { thresholdOduEntry 1 }

thresholdOduESHighThres1day OBJECT-TYPE
    SYNTAX      Unsigned32 (0..86400 | 4294967295)
    MAX-ACCESS  read-write
    STATUS      current
    DESCRIPTION
        "ODU Errored Seconds 1 Day Threshold" 
    ::=  { thresholdOduEntry 2 }

thresholdOduSESHighThres15min OBJECT-TYPE
    SYNTAX      Unsigned32 (0..900 | 4294967295)
    MAX-ACCESS  read-write
    STATUS      current
    DESCRIPTION
        "ODU Severely Errored Seconds 15 Minute Threshold" 
    ::=  { thresholdOduEntry 3 }

thresholdOduSESHighThres1day OBJECT-TYPE
    SYNTAX      Unsigned32 (0..86400 | 4294967295)
    MAX-ACCESS  read-write
    STATUS      current
    DESCRIPTION
        "ODU Severely Errored Seconds 1 Day Threshold" 
    ::=  { thresholdOduEntry 4 }

thresholdOduBbeHighThres15min OBJECT-TYPE
    SYNTAX      Counter64String
    MAX-ACCESS  read-write
    STATUS      current
    DESCRIPTION
        "ODU Background Block Errors 15 Minute Threshold" 
    ::=  { thresholdOduEntry 5 }

thresholdOduBbeHighThres1day OBJECT-TYPE
    SYNTAX      Counter64String
    MAX-ACCESS  read-write
    STATUS      current
    DESCRIPTION
        "ODU Background Block Errors 1 Day Threshold" 
    ::=  { thresholdOduEntry 6 }

thresholdOduUASHighThres15min OBJECT-TYPE
    SYNTAX      Unsigned32 (0..900 | 4294967295)
    MAX-ACCESS  read-write
    STATUS      current
    DESCRIPTION
        "ODU Unavailable Seconds 15 Minute Threshold" 
    ::=  { thresholdOduEntry 7 }

thresholdOduUASHighThres1day OBJECT-TYPE
    SYNTAX      Unsigned32 (0..86400 | 4294967295)
    MAX-ACCESS  read-write
    STATUS      current
    DESCRIPTION
        "ODU Unavailable Seconds 1 Day Threshold" 
    ::=  { thresholdOduEntry 8 }

thresholdOduTcmATable OBJECT-TYPE
    SYNTAX      SEQUENCE OF ThresholdOduTcmAEntry
    MAX-ACCESS  not-accessible
    STATUS      current
    DESCRIPTION   ""
    ::=  { performanceAdmin 3 }

thresholdOduTcmAEntry OBJECT-TYPE
    SYNTAX      ThresholdOduTcmAEntry
    MAX-ACCESS  not-accessible
    STATUS      current
    DESCRIPTION   ""
    INDEX       {
                  entityIndex
                }
    ::=  { thresholdOduTcmATable 1 }

ThresholdOduTcmAEntry ::=  SEQUENCE
  { thresholdOduTcmAESHighThres15min Unsigned32,
    thresholdOduTcmAESHighThres1day Unsigned32,
    thresholdOduTcmASESHighThres15min Unsigned32,
    thresholdOduTcmASESHighThres1day Unsigned32,
    thresholdOduTcmABbeHighThres15min Counter64String,
    thresholdOduTcmABbeHighThres1day Counter64String,
    thresholdOduTcmAUASHighThres15min Unsigned32,
    thresholdOduTcmAUASHighThres1day Unsigned32 }

thresholdOduTcmAESHighThres15min OBJECT-TYPE
    SYNTAX      Unsigned32 (0..900 | 4294967295)
    MAX-ACCESS  read-write
    STATUS      current
    DESCRIPTION
        "ODU Tandem Connection Monitoring A Errored Seconds 15 Minute Threshold" 
    ::=  { thresholdOduTcmAEntry 1 }

thresholdOduTcmAESHighThres1day OBJECT-TYPE
    SYNTAX      Unsigned32 (0..86400 | 4294967295)
    MAX-ACCESS  read-write
    STATUS      current
    DESCRIPTION
        "ODU Tandem Connection Monitoring A Errored Seconds 1 Day Threshold" 
    ::=  { thresholdOduTcmAEntry 2 }

thresholdOduTcmASESHighThres15min OBJECT-TYPE
    SYNTAX      Unsigned32 (0..900 | 4294967295)
    MAX-ACCESS  read-write
    STATUS      current
    DESCRIPTION
        "Tandem Connection Monitor A Section Severely Errored Seconds 15 Minute Threshold" 
    ::=  { thresholdOduTcmAEntry 3 }

thresholdOduTcmASESHighThres1day OBJECT-TYPE
    SYNTAX      Unsigned32 (0..86400 | 4294967295)
    MAX-ACCESS  read-write
    STATUS      current
    DESCRIPTION
        "Tandem Connection Monitor A Section Severely Errored Seconds 1 Day Threshold" 
    ::=  { thresholdOduTcmAEntry 4 }

thresholdOduTcmABbeHighThres15min OBJECT-TYPE
    SYNTAX      Counter64String
    MAX-ACCESS  read-write
    STATUS      current
    DESCRIPTION
        "ODU Tandem Connection A Background Block Errors 15 Minute Threshold" 
    ::=  { thresholdOduTcmAEntry 5 }

thresholdOduTcmABbeHighThres1day OBJECT-TYPE
    SYNTAX      Counter64String
    MAX-ACCESS  read-write
    STATUS      current
    DESCRIPTION
        "ODU Tandem Connection A Background Block Errors 1 Day Minute Threshold" 
    ::=  { thresholdOduTcmAEntry 6 }

thresholdOduTcmAUASHighThres15min OBJECT-TYPE
    SYNTAX      Unsigned32 (0..900 | 4294967295)
    MAX-ACCESS  read-write
    STATUS      current
    DESCRIPTION
        "ODU Tandem Connection Monitoring A Unavailable Seconds 15 Minute Threshold" 
    ::=  { thresholdOduTcmAEntry 7 }

thresholdOduTcmAUASHighThres1day OBJECT-TYPE
    SYNTAX      Unsigned32 (0..86400 | 4294967295)
    MAX-ACCESS  read-write
    STATUS      current
    DESCRIPTION
        "ODU Tandem Connection Monitoring A Unavailable Seconds 1 Day Threshold" 
    ::=  { thresholdOduTcmAEntry 8 }

thresholdOduTcmBTable OBJECT-TYPE
    SYNTAX      SEQUENCE OF ThresholdOduTcmBEntry
    MAX-ACCESS  not-accessible
    STATUS      current
    DESCRIPTION   ""
    ::=  { performanceAdmin 4 }

thresholdOduTcmBEntry OBJECT-TYPE
    SYNTAX      ThresholdOduTcmBEntry
    MAX-ACCESS  not-accessible
    STATUS      current
    DESCRIPTION   ""
    INDEX       {
                  entityIndex
                }
    ::=  { thresholdOduTcmBTable 1 }

ThresholdOduTcmBEntry ::=  SEQUENCE
  { thresholdOduTcmBBESHighThres15min Unsigned32,
    thresholdOduTcmBESHighThres1day Unsigned32,
    thresholdOduTcmBSESHighThres15min Unsigned32,
    thresholdOduTcmBSESHighThres1day Unsigned32,
    thresholdOduTcmBOduTcmBBbeHighThres15min Counter64String,
    thresholdOduTcmBOduTcmBBbeHighThres1day Counter64String,
    thresholdOduTcmBUASHighThres15min Unsigned32,
    thresholdOduTcmBUASHighThres1day Unsigned32 }

thresholdOduTcmBBESHighThres15min OBJECT-TYPE
    SYNTAX      Unsigned32 (0..900 | 4294967295)
    MAX-ACCESS  read-write
    STATUS      current
    DESCRIPTION
        "ODU Tandem Connection Monitoring B Errored Seconds 15 Minute Threshold" 
    ::=  { thresholdOduTcmBEntry 1 }

thresholdOduTcmBESHighThres1day OBJECT-TYPE
    SYNTAX      Unsigned32 (0..86400 | 4294967295)
    MAX-ACCESS  read-write
    STATUS      current
    DESCRIPTION
        "ODU Tandem Connection Monitoring B Errored Seconds 1 Day Threshold" 
    ::=  { thresholdOduTcmBEntry 2 }

thresholdOduTcmBSESHighThres15min OBJECT-TYPE
    SYNTAX      Unsigned32 (0..900 | 4294967295)
    MAX-ACCESS  read-write
    STATUS      current
    DESCRIPTION
        "Tandem Connection Monitor B Section Severely Errored Seconds 15 Minute Threshold" 
    ::=  { thresholdOduTcmBEntry 3 }

thresholdOduTcmBSESHighThres1day OBJECT-TYPE
    SYNTAX      Unsigned32 (0..86400 | 4294967295)
    MAX-ACCESS  read-write
    STATUS      current
    DESCRIPTION
        "Tandem Connection Monitor B Section Severely Errored Seconds 1 Day Threshold" 
    ::=  { thresholdOduTcmBEntry 4 }

thresholdOduTcmBOduTcmBBbeHighThres15min OBJECT-TYPE
    SYNTAX      Counter64String
    MAX-ACCESS  read-write
    STATUS      current
    DESCRIPTION
        "ODU Tandem Connection B Background Block Errors 15 Minute Threshold" 
    ::=  { thresholdOduTcmBEntry 5 }

thresholdOduTcmBOduTcmBBbeHighThres1day OBJECT-TYPE
    SYNTAX      Counter64String
    MAX-ACCESS  read-write
    STATUS      current
    DESCRIPTION
        "ODU Tandem Connection B Background Block Errors 1 Day Threshold" 
    ::=  { thresholdOduTcmBEntry 6 }

thresholdOduTcmBUASHighThres15min OBJECT-TYPE
    SYNTAX      Unsigned32 (0..900 | 4294967295)
    MAX-ACCESS  read-write
    STATUS      current
    DESCRIPTION
        "ODU Tandem Connection Monitoring B Unavailable Seconds 15 Minute Threshold" 
    ::=  { thresholdOduTcmBEntry 7 }

thresholdOduTcmBUASHighThres1day OBJECT-TYPE
    SYNTAX      Unsigned32 (0..86400 | 4294967295)
    MAX-ACCESS  read-write
    STATUS      current
    DESCRIPTION
        "ODU Tandem Connection Monitoring B Unavailable Seconds 1 Day Threshold" 
    ::=  { thresholdOduTcmBEntry 8 }

thresholdSonetSectTable OBJECT-TYPE
    SYNTAX      SEQUENCE OF ThresholdSonetSectEntry
    MAX-ACCESS  not-accessible
    STATUS      current
    DESCRIPTION   ""
    ::=  { performanceAdmin 5 }

thresholdSonetSectEntry OBJECT-TYPE
    SYNTAX      ThresholdSonetSectEntry
    MAX-ACCESS  not-accessible
    STATUS      current
    DESCRIPTION   ""
    INDEX       {
                  entityIndex
                }
    ::=  { thresholdSonetSectTable 1 }

ThresholdSonetSectEntry ::=  SEQUENCE
  { thresholdSonetSectESHighThres15min Unsigned32,
    thresholdSonetSectESHighThres1day Unsigned32,
    thresholdSonetSectSESHighThres15min Unsigned32,
    thresholdSonetSectSESHighThres1day Unsigned32,
    thresholdSonetSectSEFSHighThres15min Unsigned32,
    thresholdSonetSectSEFSHighThres1day Unsigned32,
    thresholdSonetSectCVHighThres15min Counter64String,
    thresholdSonetSectCVHighThres1day Counter64String }

thresholdSonetSectESHighThres15min OBJECT-TYPE
    SYNTAX      Unsigned32 (0..900 | 4294967295)
    MAX-ACCESS  read-write
    STATUS      current
    DESCRIPTION
        "Section / Regeneration Section Errored Seconds 15 Minute Threshold" 
    ::=  { thresholdSonetSectEntry 1 }

thresholdSonetSectESHighThres1day OBJECT-TYPE
    SYNTAX      Unsigned32 (0..86400 | 4294967295)
    MAX-ACCESS  read-write
    STATUS      current
    DESCRIPTION
        "Section / Regeneration Section Errored Seconds 1 Day Threshold" 
    ::=  { thresholdSonetSectEntry 2 }

thresholdSonetSectSESHighThres15min OBJECT-TYPE
    SYNTAX      Unsigned32 (0..900 | 4294967295)
    MAX-ACCESS  read-write
    STATUS      current
    DESCRIPTION
        "Section / Regenerator Section Severely Errored Seconds 15 Minute Threshold" 
    ::=  { thresholdSonetSectEntry 3 }

thresholdSonetSectSESHighThres1day OBJECT-TYPE
    SYNTAX      Unsigned32 (0..86400 | 4294967295)
    MAX-ACCESS  read-write
    STATUS      current
    DESCRIPTION
        "Section / Regenerator Section Severely Errored Seconds 1 Day Threshold" 
    ::=  { thresholdSonetSectEntry 4 }

thresholdSonetSectSEFSHighThres15min OBJECT-TYPE
    SYNTAX      Unsigned32 (0..900 | 4294967295)
    MAX-ACCESS  read-write
    STATUS      current
    DESCRIPTION
        "Section Severely Errored Frame Seconds 15 Minute Threshold" 
    ::=  { thresholdSonetSectEntry 5 }

thresholdSonetSectSEFSHighThres1day OBJECT-TYPE
    SYNTAX      Unsigned32 (0..86400 | 4294967295)
    MAX-ACCESS  read-write
    STATUS      current
    DESCRIPTION
        "Section Severely Errored Frame Seconds 1 Day Threshold" 
    ::=  { thresholdSonetSectEntry 6 }

thresholdSonetSectCVHighThres15min OBJECT-TYPE
    SYNTAX      Counter64String
    MAX-ACCESS  read-write
    STATUS      current
    DESCRIPTION
        "Section / Regenerator Section Coding Violations 15 Minute Threshold" 
    ::=  { thresholdSonetSectEntry 7 }

thresholdSonetSectCVHighThres1day OBJECT-TYPE
    SYNTAX      Counter64String
    MAX-ACCESS  read-write
    STATUS      current
    DESCRIPTION
        "Section / Regenerator Section Coding Violations 1 Day Threshold" 
    ::=  { thresholdSonetSectEntry 8 }

thresholdSonetLineTable OBJECT-TYPE
    SYNTAX      SEQUENCE OF ThresholdSonetLineEntry
    MAX-ACCESS  not-accessible
    STATUS      deprecated
    DESCRIPTION   ""
    ::=  { performanceAdmin 6 }

thresholdSonetLineEntry OBJECT-TYPE
    SYNTAX      ThresholdSonetLineEntry
    MAX-ACCESS  not-accessible
    STATUS      deprecated
    DESCRIPTION   ""
    INDEX       {
                  entityIndex
                }
    ::=  { thresholdSonetLineTable 1 }

ThresholdSonetLineEntry ::=  SEQUENCE
  { thresholdSonetLineESHighThres15min Unsigned32,
    thresholdSonetLineESHighThres1day Unsigned32,
    thresholdSonetLineSESHighThres15min Unsigned32,
    thresholdSonetLineSESHighThres1day Unsigned32,
    thresholdSonetLineUASHighThres15min Unsigned32,
    thresholdSonetLineUASSHighThres1day Unsigned32,
    thresholdSonetLineCVHighThres15min Unsigned32,
    thresholdSonetLineCVSHighThres1day Counter64String,
    thresholdSonetLineCViolHighThres15min Counter64String }

thresholdSonetLineESHighThres15min OBJECT-TYPE
    SYNTAX      Unsigned32 (0..900 | 4294967295)
    MAX-ACCESS  read-write
    STATUS      deprecated
    DESCRIPTION
        "Line / Multiplex Section Errored Seconds 15 Minute Threshold" 
    ::=  { thresholdSonetLineEntry 1 }

thresholdSonetLineESHighThres1day OBJECT-TYPE
    SYNTAX      Unsigned32 (0..86400 | 4294967295)
    MAX-ACCESS  read-write
    STATUS      deprecated
    DESCRIPTION
        "Line / Multiplex Section Errored Seconds 1 Day Threshold" 
    ::=  { thresholdSonetLineEntry 2 }

thresholdSonetLineSESHighThres15min OBJECT-TYPE
    SYNTAX      Unsigned32 (0..900 | 4294967295)
    MAX-ACCESS  read-write
    STATUS      deprecated
    DESCRIPTION
        "Line / Multiplex Section Severely Errored Seconds 15 Minute Threshold" 
    ::=  { thresholdSonetLineEntry 3 }

thresholdSonetLineSESHighThres1day OBJECT-TYPE
    SYNTAX      Unsigned32 (0..86400 | 4294967295)
    MAX-ACCESS  read-write
    STATUS      deprecated
    DESCRIPTION
        "Line / Multiplex Section Severely Errored Seconds 1 Day Threshold" 
    ::=  { thresholdSonetLineEntry 4 }

thresholdSonetLineUASHighThres15min OBJECT-TYPE
    SYNTAX      Unsigned32 (0..900 | 4294967295)
    MAX-ACCESS  read-write
    STATUS      deprecated
    DESCRIPTION
        "Line / Multiplex Section Unavailable Seconds 15 Minute Threshold" 
    ::=  { thresholdSonetLineEntry 5 }

thresholdSonetLineUASSHighThres1day OBJECT-TYPE
    SYNTAX      Unsigned32 (0..86400 | 4294967295)
    MAX-ACCESS  read-write
    STATUS      deprecated
    DESCRIPTION
        "Line / Multiplex Section Unavailable Seconds 1 Day Threshold" 
    ::=  { thresholdSonetLineEntry 6 }

thresholdSonetLineCVHighThres15min OBJECT-TYPE
    SYNTAX      Unsigned32
    MAX-ACCESS  read-write
    STATUS      deprecated
    DESCRIPTION
        "Threshold 15 Min: Coding Violations Line / Multiplex Section" 
    ::=  { thresholdSonetLineEntry 7 }

thresholdSonetLineCVSHighThres1day OBJECT-TYPE
    SYNTAX      Counter64String
    MAX-ACCESS  read-write
    STATUS      deprecated
    DESCRIPTION
        "Line / Multiplex Section Coding Violations 1 Day Threshold" 
    ::=  { thresholdSonetLineEntry 8 }

thresholdSonetLineCViolHighThres15min OBJECT-TYPE
    SYNTAX      Counter64String
    MAX-ACCESS  read-write
    STATUS      deprecated
    DESCRIPTION
        "Line / Multiplex Section Coding Violations 15 Minute Threshold" 
    ::=  { thresholdSonetLineEntry 9 }

thresholdSonetHoPathTable OBJECT-TYPE
    SYNTAX      SEQUENCE OF ThresholdSonetHoPathEntry
    MAX-ACCESS  not-accessible
    STATUS      current
    DESCRIPTION   ""
    ::=  { performanceAdmin 7 }

thresholdSonetHoPathEntry OBJECT-TYPE
    SYNTAX      ThresholdSonetHoPathEntry
    MAX-ACCESS  not-accessible
    STATUS      current
    DESCRIPTION   ""
    INDEX       {
                  entityIndex
                }
    ::=  { thresholdSonetHoPathTable 1 }

ThresholdSonetHoPathEntry ::=  SEQUENCE
  { thresholdSonetHoPathESHighThres15min Unsigned32,
    thresholdSonetHoPathESHighThres1day Unsigned32,
    thresholdSonetHoPathSESHighThres15min Unsigned32,
    thresholdSonetHoPathSESHighThres1day Unsigned32,
    thresholdSonetHoPathUASHighThres15min Unsigned32,
    thresholdSonetHoPathUASHighThres1day Unsigned32,
    thresholdSonetHoPathCVHighThres15min Counter64String,
    thresholdSonetHoPathCVHighThres1day Counter64String }

thresholdSonetHoPathESHighThres15min OBJECT-TYPE
    SYNTAX      Unsigned32 (0..900 | 4294967295)
    MAX-ACCESS  read-write
    STATUS      current
    DESCRIPTION
        "Path Errored Seconds 15 Minute Threshold" 
    ::=  { thresholdSonetHoPathEntry 1 }

thresholdSonetHoPathESHighThres1day OBJECT-TYPE
    SYNTAX      Unsigned32 (0..86400 | 4294967295)
    MAX-ACCESS  read-write
    STATUS      current
    DESCRIPTION
        "Path Errored Seconds 1 Day Threshold" 
    ::=  { thresholdSonetHoPathEntry 2 }

thresholdSonetHoPathSESHighThres15min OBJECT-TYPE
    SYNTAX      Unsigned32 (0..900 | 4294967295)
    MAX-ACCESS  read-write
    STATUS      current
    DESCRIPTION
        "Path Severely Errored Seconds 15 Minute Threshold" 
    ::=  { thresholdSonetHoPathEntry 3 }

thresholdSonetHoPathSESHighThres1day OBJECT-TYPE
    SYNTAX      Unsigned32 (0..86400 | 4294967295)
    MAX-ACCESS  read-write
    STATUS      current
    DESCRIPTION
        "Path Severely Errored Seconds 1 Day Threshold" 
    ::=  { thresholdSonetHoPathEntry 4 }

thresholdSonetHoPathUASHighThres15min OBJECT-TYPE
    SYNTAX      Unsigned32 (0..900 | 4294967295)
    MAX-ACCESS  read-write
    STATUS      current
    DESCRIPTION
        "Path Unavailable Seconds 15 Minute Threshold" 
    ::=  { thresholdSonetHoPathEntry 5 }

thresholdSonetHoPathUASHighThres1day OBJECT-TYPE
    SYNTAX      Unsigned32 (0..86400 | 4294967295)
    MAX-ACCESS  read-write
    STATUS      current
    DESCRIPTION
        "Path Unavailable Seconds 1 Day Threshold" 
    ::=  { thresholdSonetHoPathEntry 6 }

thresholdSonetHoPathCVHighThres15min OBJECT-TYPE
    SYNTAX      Counter64String
    MAX-ACCESS  read-write
    STATUS      current
    DESCRIPTION
        "Path Coding Violations 15 Minute Threshold" 
    ::=  { thresholdSonetHoPathEntry 7 }

thresholdSonetHoPathCVHighThres1day OBJECT-TYPE
    SYNTAX      Counter64String
    MAX-ACCESS  read-write
    STATUS      current
    DESCRIPTION
        "Path Coding Violations 1 Day Threshold" 
    ::=  { thresholdSonetHoPathEntry 8 }

thresholdSonetLoPathTable OBJECT-TYPE
    SYNTAX      SEQUENCE OF ThresholdSonetLoPathEntry
    MAX-ACCESS  not-accessible
    STATUS      current
    DESCRIPTION   ""
    ::=  { performanceAdmin 8 }

thresholdSonetLoPathEntry OBJECT-TYPE
    SYNTAX      ThresholdSonetLoPathEntry
    MAX-ACCESS  not-accessible
    STATUS      current
    DESCRIPTION   ""
    INDEX       {
                  entityIndex
                }
    ::=  { thresholdSonetLoPathTable 1 }

ThresholdSonetLoPathEntry ::=  SEQUENCE
  { thresholdSonetLoPathESHighThres15min Unsigned32,
    thresholdSonetLoPathESHighThres1day Unsigned32,
    thresholdSonetLoPathSESHighThres15min Unsigned32,
    thresholdSonetLoPathSESHighThres1day Unsigned32,
    thresholdSonetLoPathUASHighThres15min Unsigned32,
    thresholdSonetLoPathUASHighThres1day Unsigned32,
    thresholdSonetLoPathCVHighThres15min Counter64String,
    thresholdSonetLoPathCVHighThres1day Counter64String }

thresholdSonetLoPathESHighThres15min OBJECT-TYPE
    SYNTAX      Unsigned32 (0..900 | 4294967295)
    MAX-ACCESS  read-write
    STATUS      current
    DESCRIPTION
        "Path Low Order Errored Seconds 15 Minute Threshold" 
    ::=  { thresholdSonetLoPathEntry 1 }

thresholdSonetLoPathESHighThres1day OBJECT-TYPE
    SYNTAX      Unsigned32 (0..86400 | 4294967295)
    MAX-ACCESS  read-write
    STATUS      current
    DESCRIPTION
        "Path Low Order Errored Seconds 1 Day Threshold" 
    ::=  { thresholdSonetLoPathEntry 2 }

thresholdSonetLoPathSESHighThres15min OBJECT-TYPE
    SYNTAX      Unsigned32 (0..900 | 4294967295)
    MAX-ACCESS  read-write
    STATUS      current
    DESCRIPTION
        "Path Low Order Severely Errored Seconds 15 Minute Threshold" 
    ::=  { thresholdSonetLoPathEntry 3 }

thresholdSonetLoPathSESHighThres1day OBJECT-TYPE
    SYNTAX      Unsigned32 (0..86400 | 4294967295)
    MAX-ACCESS  read-write
    STATUS      current
    DESCRIPTION
        "Path Low Order Severely Errored Seconds 1 Day Threshold" 
    ::=  { thresholdSonetLoPathEntry 4 }

thresholdSonetLoPathUASHighThres15min OBJECT-TYPE
    SYNTAX      Unsigned32 (0..900 | 4294967295)
    MAX-ACCESS  read-write
    STATUS      current
    DESCRIPTION
        "Path Low Order Unavailable Seconds 15 Minute Threshold" 
    ::=  { thresholdSonetLoPathEntry 5 }

thresholdSonetLoPathUASHighThres1day OBJECT-TYPE
    SYNTAX      Unsigned32 (0..86400 | 4294967295)
    MAX-ACCESS  read-write
    STATUS      current
    DESCRIPTION
        "Path Low Order Unavailable Seconds 1 Day Threshold" 
    ::=  { thresholdSonetLoPathEntry 6 }

thresholdSonetLoPathCVHighThres15min OBJECT-TYPE
    SYNTAX      Counter64String
    MAX-ACCESS  read-write
    STATUS      current
    DESCRIPTION
        "Path Low Order Coding Violations 15 Minute Threshold" 
    ::=  { thresholdSonetLoPathEntry 7 }

thresholdSonetLoPathCVHighThres1day OBJECT-TYPE
    SYNTAX      Counter64String
    MAX-ACCESS  read-write
    STATUS      current
    DESCRIPTION
        "Path Low Order Coding Violations 1 Day Threshold" 
    ::=  { thresholdSonetLoPathEntry 8 }

thresholdPhysPerfTable OBJECT-TYPE
    SYNTAX      SEQUENCE OF ThresholdPhysPerfEntry
    MAX-ACCESS  not-accessible
    STATUS      current
    DESCRIPTION   ""
    ::=  { performanceAdmin 9 }

thresholdPhysPerfEntry OBJECT-TYPE
    SYNTAX      ThresholdPhysPerfEntry
    MAX-ACCESS  not-accessible
    STATUS      current
    DESCRIPTION   ""
    INDEX       {
                  entityIndex
                }
    ::=  { thresholdPhysPerfTable 1 }

ThresholdPhysPerfEntry ::=  SEQUENCE
  { thresholdPhysPerfOpticalInputPwrLow Integer32,
    thresholdPhysPerfOpticalInputPwrHigh Integer32,
    thresholdPhysPerfOpticalOutputPwrLow Integer32,
    thresholdPhysPerfOpticalOutputPwrHigh Integer32,
    thresholdPhysPerfLaserBiasCurrentNormalized Unsigned32,
    thresholdPhysPerfAttRxLow Integer32,
    thresholdPhysPerfAttRxHigh Integer32,
    thresholdPhysPerfAttTxLow Integer32,
    thresholdPhysPerfAttTxHigh Integer32,
    thresholdPhysPerfLaserTempLowThres Integer32,
    thresholdPhysPerfLaserTempHighThres Integer32,
    thresholdPhysPerfPumpLaser1TempHighThres Integer32,
    thresholdPhysPerfPumpLaser1TempLowThres Integer32,
    thresholdPhysPerfPumpLaser2TempHighThres Integer32,
    thresholdPhysPerfPumpLaser2TempLowThres Integer32,
    thresholdPhysPerfOscPwrRcvHighThres Integer32,
    thresholdPhysPerfOscPwrRcvLowThres Integer32,
    thresholdPhysPerfRamanPumpPwrHighThres Integer32,
    thresholdPhysPerfRamanPumpPwrLowThres Integer32,
    thresholdPhysPerfConfigurableOpticalOutputPwrLow Integer32,
    thresholdPhysPerfConfigurableOpticalOutputPwrHigh Integer32,
    thresholdPhysPerfBrPwrReceivedHighThres Integer32,
    thresholdPhysPerfDispersionCompensationLowThres Integer32,
    thresholdPhysPerfDispersionCompensationHighThres Integer32,
    thresholdPhysPerfLowerAtlinkThres Integer32,
    thresholdPhysPerfUpperAtlinkThres Integer32,
    thresholdPhysPerfPumpLaser3TempHighThres Integer32,
    thresholdPhysPerfPumpLaser3TempLowThres Integer32,
    thresholdPhysPerfLatencyHighThres Integer32,
    thresholdPhysPerfLatencyLowThres Integer32,
    thresholdPhysPerfRoundTripDelayHighThres Integer32,
    thresholdPhysPerfRoundTripDelayLowThres Integer32,
    thresholdPhysPerfPumpLaser4TempHighThres Integer32,
    thresholdPhysPerfPumpLaser4TempLowThres Integer32,
    thresholdPhysPerfLocalOscTempLowThres Integer32,
    thresholdPhysPerfLocalOscTempHighThres Integer32,
    thresholdPhysPerfDifferentialGroupDelayHigh Integer32,
    thresholdPhysPerfChromaticDispersionLow Integer32,
    thresholdPhysPerfChromaticDispersionHigh Integer32,
    thresholdPhysPerfSignalToNoiseRatioLow Integer32,
    thresholdPhysPerfCarrierFreqOffsetLow Integer32,
    thresholdPhysPerfCarrierFreqOffsetHigh Integer32,
    thresholdPhysPerfLogicalLanesSkewHigh Integer32 }

thresholdPhysPerfOpticalInputPwrLow OBJECT-TYPE
    SYNTAX      Integer32 (-450..260 | -2147483648) 
    UNITS       "0.1 dBm"
    MAX-ACCESS  read-write
    STATUS      current
    DESCRIPTION
        "Optical Input Power Received" 
    ::=  { thresholdPhysPerfEntry 1 }

thresholdPhysPerfOpticalInputPwrHigh OBJECT-TYPE
    SYNTAX      Integer32 (-450..270 | -2147483648) 
    UNITS       "0.1 dBm"
    MAX-ACCESS  read-write
    STATUS      current
    DESCRIPTION
        "Optical Input Power Received" 
    ::=  { thresholdPhysPerfEntry 2 }

thresholdPhysPerfOpticalOutputPwrLow OBJECT-TYPE
    SYNTAX      Integer32 
    UNITS       "0.1 dBm"
    MAX-ACCESS  read-write
    STATUS      current
    DESCRIPTION
        "Low fixed threshold of the Optical Power Transmitted (output)" 
    ::=  { thresholdPhysPerfEntry 3 }

thresholdPhysPerfOpticalOutputPwrHigh OBJECT-TYPE
    SYNTAX      Integer32 
    UNITS       "0.1 dBm"
    MAX-ACCESS  read-write
    STATUS      current
    DESCRIPTION
        "High fixed threshold of the Optical Power Transmitted (output)" 
    ::=  { thresholdPhysPerfEntry 4 }

thresholdPhysPerfLaserBiasCurrentNormalized OBJECT-TYPE
    SYNTAX      Unsigned32 
    UNITS       "%"
    MAX-ACCESS  read-write
    STATUS      current
    DESCRIPTION
        "Laser Bias Current Normalized Fixed High Threshold." 
    ::=  { thresholdPhysPerfEntry 5 }

thresholdPhysPerfAttRxLow OBJECT-TYPE
    SYNTAX      Integer32 
    UNITS       "0.1 dB"
    MAX-ACCESS  read-write
    STATUS      current
    DESCRIPTION
        "Low Threshold for Attenuation on Receive Fiber." 
    ::=  { thresholdPhysPerfEntry 6 }

thresholdPhysPerfAttRxHigh OBJECT-TYPE
    SYNTAX      Integer32 
    UNITS       "0.1 dB"
    MAX-ACCESS  read-write
    STATUS      current
    DESCRIPTION
        "High Threshold for Attenuation on Receive Fiber" 
    ::=  { thresholdPhysPerfEntry 7 }

thresholdPhysPerfAttTxLow OBJECT-TYPE
    SYNTAX      Integer32 
    UNITS       "0.1 dB"
    MAX-ACCESS  read-write
    STATUS      current
    DESCRIPTION
        "Low Threshold Attenuation on Transmit Fiber" 
    ::=  { thresholdPhysPerfEntry 8 }

thresholdPhysPerfAttTxHigh OBJECT-TYPE
    SYNTAX      Integer32 
    UNITS       "0.1 dB"
    MAX-ACCESS  read-write
    STATUS      current
    DESCRIPTION
        "High Threshold of Attenuation on Transmit Fiber" 
    ::=  { thresholdPhysPerfEntry 9 }

thresholdPhysPerfLaserTempLowThres OBJECT-TYPE
    SYNTAX      Integer32 
    UNITS       "0.1 degree Celsius"
    MAX-ACCESS  read-write
    STATUS      current
    DESCRIPTION
        "Laser temperature fixed low threshold." 
    ::=  { thresholdPhysPerfEntry 10 }

thresholdPhysPerfLaserTempHighThres OBJECT-TYPE
    SYNTAX      Integer32 
    UNITS       "0.1 degree Celsius"
    MAX-ACCESS  read-write
    STATUS      current
    DESCRIPTION
        "Laser temperature fixed high threshold." 
    ::=  { thresholdPhysPerfEntry 11 }

thresholdPhysPerfPumpLaser1TempHighThres OBJECT-TYPE
    SYNTAX      Integer32 
    UNITS       "0.1 degree Celsius"
    MAX-ACCESS  read-write
    STATUS      current
    DESCRIPTION
        "Laser 1 temperature fixed high threshold." 
    ::=  { thresholdPhysPerfEntry 12 }

thresholdPhysPerfPumpLaser1TempLowThres OBJECT-TYPE
    SYNTAX      Integer32 
    UNITS       "0.1 degree Celsius"
    MAX-ACCESS  read-write
    STATUS      current
    DESCRIPTION
        "Laser 1 temperature fixed low threshold." 
    ::=  { thresholdPhysPerfEntry 13 }

thresholdPhysPerfPumpLaser2TempHighThres OBJECT-TYPE
    SYNTAX      Integer32 
    UNITS       "0.1 degree Celsius"
    MAX-ACCESS  read-write
    STATUS      current
    DESCRIPTION
        "Laser 2 temperature fixed high threshold." 
    ::=  { thresholdPhysPerfEntry 14 }

thresholdPhysPerfPumpLaser2TempLowThres OBJECT-TYPE
    SYNTAX      Integer32 
    UNITS       "0.1 degree Celsius"
    MAX-ACCESS  read-write
    STATUS      current
    DESCRIPTION
        "Laser 2 temperature fixed low threshold" 
    ::=  { thresholdPhysPerfEntry 15 }

thresholdPhysPerfOscPwrRcvHighThres OBJECT-TYPE
    SYNTAX      Integer32 (-470..-50 | -2147483648) 
    UNITS       "0.1 dBm"
    MAX-ACCESS  read-write
    STATUS      current
    DESCRIPTION
        "Optical Supervisory Channel Input Power Received High Threshold" 
    ::=  { thresholdPhysPerfEntry 16 }

thresholdPhysPerfOscPwrRcvLowThres OBJECT-TYPE
    SYNTAX      Integer32 (-470..-50 | -2147483648) 
    UNITS       "0.1 dBm"
    MAX-ACCESS  read-write
    STATUS      current
    DESCRIPTION
        "Optical Supervisory Channel Input Power Received Low Threshold" 
    ::=  { thresholdPhysPerfEntry 17 }

thresholdPhysPerfRamanPumpPwrHighThres OBJECT-TYPE
    SYNTAX      Integer32 
    UNITS       "0.1 dBm"
    MAX-ACCESS  read-write
    STATUS      current
    DESCRIPTION
        "Raman Pump Power High threshold" 
    ::=  { thresholdPhysPerfEntry 18 }

thresholdPhysPerfRamanPumpPwrLowThres OBJECT-TYPE
    SYNTAX      Integer32 
    UNITS       "0.1 dBm"
    MAX-ACCESS  read-write
    STATUS      current
    DESCRIPTION
        "Raman Pump Power Low threshold" 
    ::=  { thresholdPhysPerfEntry 19 }

thresholdPhysPerfConfigurableOpticalOutputPwrLow OBJECT-TYPE
    SYNTAX      Integer32 (-500..300 | -2147483648) 
    UNITS       "0.1 dBm"
    MAX-ACCESS  read-write
    STATUS      current
    DESCRIPTION
        "Configurable threshold of the Optical Power Transmitted (output)" 
    ::=  { thresholdPhysPerfEntry 20 }

thresholdPhysPerfConfigurableOpticalOutputPwrHigh OBJECT-TYPE
    SYNTAX      Integer32 (-500..300 | -2147483648) 
    UNITS       "0.1 dBm"
    MAX-ACCESS  read-write
    STATUS      current
    DESCRIPTION
        "Configurable high threshold of the Optical Power Transmitted (output)" 
    ::=  { thresholdPhysPerfEntry 21 }

thresholdPhysPerfBrPwrReceivedHighThres OBJECT-TYPE
    SYNTAX      Integer32 (-300..-180 | -2147483648) 
    UNITS       "0.1 dB"
    MAX-ACCESS  read-write
    STATUS      current
    DESCRIPTION
        "Backreflection Input Received High Threshold" 
    ::=  { thresholdPhysPerfEntry 22 }

thresholdPhysPerfDispersionCompensationLowThres OBJECT-TYPE
    SYNTAX      Integer32 (-50000..50000 | -2147483648) 
    UNITS       "ps/nm"
    MAX-ACCESS  read-write
    STATUS      current
    DESCRIPTION
        "Chromatic Dispersion Compensation Low Threshold" 
    ::=  { thresholdPhysPerfEntry 23 }

thresholdPhysPerfDispersionCompensationHighThres OBJECT-TYPE
    SYNTAX      Integer32 (-50000..50000 | -2147483648) 
    UNITS       "ps/nm"
    MAX-ACCESS  read-write
    STATUS      current
    DESCRIPTION
        "Chromatic Dispersion Compensation High Threshold" 
    ::=  { thresholdPhysPerfEntry 24 }

thresholdPhysPerfLowerAtlinkThres OBJECT-TYPE
    SYNTAX      Integer32 (0..500 | -2147483648) 
    UNITS       "0.1 dB"
    MAX-ACCESS  read-write
    STATUS      current
    DESCRIPTION
        "Configurable low threshold for link attenuation" 
    ::=  { thresholdPhysPerfEntry 25 }

thresholdPhysPerfUpperAtlinkThres OBJECT-TYPE
    SYNTAX      Integer32 (0..500 | -2147483648) 
    UNITS       "0.1 dB"
    MAX-ACCESS  read-write
    STATUS      current
    DESCRIPTION
        "Configurable high threshold for link attenuation" 
    ::=  { thresholdPhysPerfEntry 26 }

thresholdPhysPerfPumpLaser3TempHighThres OBJECT-TYPE
    SYNTAX      Integer32 
    UNITS       "0.1 degree Celsius"
    MAX-ACCESS  read-write
    STATUS      current
    DESCRIPTION
        "Laser 3 temperature fixed high threshold" 
    ::=  { thresholdPhysPerfEntry 27 }

thresholdPhysPerfPumpLaser3TempLowThres OBJECT-TYPE
    SYNTAX      Integer32 
    UNITS       "0.1 degree Celsius"
    MAX-ACCESS  read-write
    STATUS      current
    DESCRIPTION
        "Laser 3 temperature fixed low threshold" 
    ::=  { thresholdPhysPerfEntry 28 }

thresholdPhysPerfLatencyHighThres OBJECT-TYPE
    SYNTAX      Integer32 (1..300000 | -2147483648) 
    UNITS       "0.1 us"
    MAX-ACCESS  read-write
    STATUS      current
    DESCRIPTION
        "Configurable high threshold for round trip delay" 
    ::=  { thresholdPhysPerfEntry 29 }

thresholdPhysPerfLatencyLowThres OBJECT-TYPE
    SYNTAX      Integer32 (0..300000 | -2147483648) 
    UNITS       "0.1 us"
    MAX-ACCESS  read-write
    STATUS      current
    DESCRIPTION
        "Configurable low threshold round trip delay" 
    ::=  { thresholdPhysPerfEntry 30 }

thresholdPhysPerfRoundTripDelayHighThres OBJECT-TYPE
    SYNTAX      Integer32 (1..30000000 | -2147483648) 
    UNITS       "ns"
    MAX-ACCESS  read-write
    STATUS      current
    DESCRIPTION
        "Configurable high threshold for round trip delay" 
    ::=  { thresholdPhysPerfEntry 31 }

thresholdPhysPerfRoundTripDelayLowThres OBJECT-TYPE
    SYNTAX      Integer32 (0..30000000 | -2147483648) 
    UNITS       "ns"
    MAX-ACCESS  read-write
    STATUS      current
    DESCRIPTION
        "Configurable low threshold for round trip delay" 
    ::=  { thresholdPhysPerfEntry 32 }

thresholdPhysPerfPumpLaser4TempHighThres OBJECT-TYPE
    SYNTAX      Integer32 
    UNITS       "0.1 degree Celsius"
    MAX-ACCESS  read-write
    STATUS      current
    DESCRIPTION
        "Laser 4 temperature fixed high threshold" 
    ::=  { thresholdPhysPerfEntry 33 }

thresholdPhysPerfPumpLaser4TempLowThres OBJECT-TYPE
    SYNTAX      Integer32 
    UNITS       "0.1 degree Celsius"
    MAX-ACCESS  read-write
    STATUS      current
    DESCRIPTION
        "Laser 4 temperature fixed low threshold" 
    ::=  { thresholdPhysPerfEntry 34 }

thresholdPhysPerfLocalOscTempLowThres OBJECT-TYPE
    SYNTAX      Integer32 
    UNITS       "0.1 degree Celsius"
    MAX-ACCESS  read-write
    STATUS      current
    DESCRIPTION
        "Rx Laser unsed for Local Oscillator Temperature Fixed Low Threshold" 
    ::=  { thresholdPhysPerfEntry 35 }

thresholdPhysPerfLocalOscTempHighThres OBJECT-TYPE
    SYNTAX      Integer32 
    UNITS       "0.1 degree Celsius"
    MAX-ACCESS  read-write
    STATUS      current
    DESCRIPTION
        "Rx Laser used for Local Oscillator Temperature Fixed High Threshold" 
    ::=  { thresholdPhysPerfEntry 36 }

thresholdPhysPerfDifferentialGroupDelayHigh OBJECT-TYPE
    SYNTAX      Integer32 (0..100 | -2147483648) 
    UNITS       "ps"
    MAX-ACCESS  read-write
    STATUS      current
    DESCRIPTION
        "Differential Group Delay High TH" 
    ::=  { thresholdPhysPerfEntry 37 }

thresholdPhysPerfChromaticDispersionLow OBJECT-TYPE
    SYNTAX      Integer32 (-100000..100000 | -2147483648) 
    UNITS       "ps/nm"
    MAX-ACCESS  read-write
    STATUS      current
    DESCRIPTION
        "Chromatic Dispersion Compensation Low Threshold" 
    ::=  { thresholdPhysPerfEntry 38 }

thresholdPhysPerfChromaticDispersionHigh OBJECT-TYPE
    SYNTAX      Integer32 (-100000..100000 | -2147483648) 
    UNITS       "ps/nm"
    MAX-ACCESS  read-write
    STATUS      current
    DESCRIPTION
        "Chromatic Dispersion Compensation High Threshold" 
    ::=  { thresholdPhysPerfEntry 39 }

thresholdPhysPerfSignalToNoiseRatioLow OBJECT-TYPE
    SYNTAX      Integer32 (80..240 | -2147483648) 
    UNITS       "0.1 dB"
    MAX-ACCESS  read-write
    STATUS      current
    DESCRIPTION
        "Signal-to-Noise Ratio Low TH" 
    ::=  { thresholdPhysPerfEntry 40 }

thresholdPhysPerfCarrierFreqOffsetLow OBJECT-TYPE
    SYNTAX      Integer32 (-32000..32000 | -2147483648) 
    UNITS       "0.001 GHz"
    MAX-ACCESS  read-write
    STATUS      current
    DESCRIPTION
        "Carrier Frequency Offset Low TH" 
    ::=  { thresholdPhysPerfEntry 41 }

thresholdPhysPerfCarrierFreqOffsetHigh OBJECT-TYPE
    SYNTAX      Integer32 (-32000..32000 | -2147483648) 
    UNITS       "0.001 GHz"
    MAX-ACCESS  read-write
    STATUS      current
    DESCRIPTION
        "Carrier Frequency Offset High TH" 
    ::=  { thresholdPhysPerfEntry 42 }

thresholdPhysPerfLogicalLanesSkewHigh OBJECT-TYPE
    SYNTAX      Integer32 (0..1000 | -2147483648) 
    UNITS       "ns"
    MAX-ACCESS  read-write
    STATUS      current
    DESCRIPTION
        "Skew between logical lanes farthest apart high threshold" 
    ::=  { thresholdPhysPerfEntry 43 }

thresholdPhysConvTable OBJECT-TYPE
    SYNTAX      SEQUENCE OF ThresholdPhysConvEntry
    MAX-ACCESS  not-accessible
    STATUS      current
    DESCRIPTION   ""
    ::=  { performanceAdmin 10 }

thresholdPhysConvEntry OBJECT-TYPE
    SYNTAX      ThresholdPhysConvEntry
    MAX-ACCESS  not-accessible
    STATUS      current
    DESCRIPTION   ""
    INDEX       {
                  entityIndex
                }
    ::=  { thresholdPhysConvTable 1 }

ThresholdPhysConvEntry ::=  SEQUENCE
  { thresholdPhysConvESHighThres15min Unsigned32,
    thresholdPhysConvESHighThres1day Unsigned32,
    thresholdPhysConvDEHighThres15min Unsigned32,
    thresholdPhysConvDEHighThres1day Unsigned32,
    thresholdPhysConvCVHighThres15min Counter64String,
    thresholdPhysConvCVHighThres1day Counter64String }

thresholdPhysConvESHighThres15min OBJECT-TYPE
    SYNTAX      Unsigned32 (0..900 | 4294967295)
    MAX-ACCESS  read-write
    STATUS      current
    DESCRIPTION
        "Physical Coding Layer Errored Seconds 15 Minute Threshold" 
    ::=  { thresholdPhysConvEntry 1 }

thresholdPhysConvESHighThres1day OBJECT-TYPE
    SYNTAX      Unsigned32 (0..89400 | 4294967295)
    MAX-ACCESS  read-write
    STATUS      current
    DESCRIPTION
        "Physical Coding Layer Errored Seconds 1 Day Threshold" 
    ::=  { thresholdPhysConvEntry 2 }

thresholdPhysConvDEHighThres15min OBJECT-TYPE
    SYNTAX      Unsigned32
    MAX-ACCESS  read-write
    STATUS      current
    DESCRIPTION
        "Physical Coding Layer Disparity Errors 15 Minute Threshold" 
    ::=  { thresholdPhysConvEntry 3 }

thresholdPhysConvDEHighThres1day OBJECT-TYPE
    SYNTAX      Unsigned32
    MAX-ACCESS  read-write
    STATUS      current
    DESCRIPTION
        "Physical Coding Layer Disparity Errors 1 Day Threshold" 
    ::=  { thresholdPhysConvEntry 4 }

thresholdPhysConvCVHighThres15min OBJECT-TYPE
    SYNTAX      Counter64String
    MAX-ACCESS  read-write
    STATUS      current
    DESCRIPTION
        "Physical Coding Layer 15 Minute Threshold" 
    ::=  { thresholdPhysConvEntry 5 }

thresholdPhysConvCVHighThres1day OBJECT-TYPE
    SYNTAX      Counter64String
    MAX-ACCESS  read-write
    STATUS      current
    DESCRIPTION
        "Physical Coding Layer Coding Violations 1 Day Threshold" 
    ::=  { thresholdPhysConvEntry 6 }

thresholdEthRxTable OBJECT-TYPE
    SYNTAX      SEQUENCE OF ThresholdEthRxEntry
    MAX-ACCESS  not-accessible
    STATUS      current
    DESCRIPTION   ""
    ::=  { performanceAdmin 11 }

thresholdEthRxEntry OBJECT-TYPE
    SYNTAX      ThresholdEthRxEntry
    MAX-ACCESS  not-accessible
    STATUS      current
    DESCRIPTION   ""
    INDEX       {
                  entityIndex
                }
    ::=  { thresholdEthRxTable 1 }

ThresholdEthRxEntry ::=  SEQUENCE
  { thresholdEthRxPauseFramesHighThres15Min Unsigned32,
    thresholdEthRxPauseFramesHighThres1Day Unsigned32,
    thresholdEthRxCrcFramesHighThres15Min Unsigned32,
    thresholdEthRxCrcFramesHighThres1Day Unsigned32,
    thresholdEthRxDiscardedFramesHighThres15Min Unsigned32,
    thresholdEthRxDiscardedFramesHighThres1Day Unsigned32 }

thresholdEthRxPauseFramesHighThres15Min OBJECT-TYPE
    SYNTAX      Unsigned32 (0..900 | 4294967295)
    MAX-ACCESS  read-write
    STATUS      current
    DESCRIPTION
        "Pause Frames Received 15 Minute Threshold" 
    ::=  { thresholdEthRxEntry 1 }

thresholdEthRxPauseFramesHighThres1Day OBJECT-TYPE
    SYNTAX      Unsigned32 (0..86400 | 4294967295)
    MAX-ACCESS  read-write
    STATUS      current
    DESCRIPTION
        "Pause Frames Received 1 Day Threshold" 
    ::=  { thresholdEthRxEntry 2 }

thresholdEthRxCrcFramesHighThres15Min OBJECT-TYPE
    SYNTAX      Unsigned32 (0..900 | 4294967295)
    MAX-ACCESS  read-write
    STATUS      current
    DESCRIPTION
        "Received CRC Errors 15 Minute Threshold" 
    ::=  { thresholdEthRxEntry 3 }

thresholdEthRxCrcFramesHighThres1Day OBJECT-TYPE
    SYNTAX      Unsigned32 (0..86400 | 4294967295)
    MAX-ACCESS  read-write
    STATUS      current
    DESCRIPTION
        "Received CRC Errors 1 Day Threshold" 
    ::=  { thresholdEthRxEntry 4 }

thresholdEthRxDiscardedFramesHighThres15Min OBJECT-TYPE
    SYNTAX      Unsigned32 (0..900 | 4294967295)
    MAX-ACCESS  read-write
    STATUS      current
    DESCRIPTION
        "Received Frames Discarded 15 Minute Threshold" 
    ::=  { thresholdEthRxEntry 5 }

thresholdEthRxDiscardedFramesHighThres1Day OBJECT-TYPE
    SYNTAX      Unsigned32 (0..86400 | 4294967295)
    MAX-ACCESS  read-write
    STATUS      current
    DESCRIPTION
        "Received Frames Discarded 1 Day Threshold" 
    ::=  { thresholdEthRxEntry 6 }

thresholdEthTxTable OBJECT-TYPE
    SYNTAX      SEQUENCE OF ThresholdEthTxEntry
    MAX-ACCESS  not-accessible
    STATUS      current
    DESCRIPTION   ""
    ::=  { performanceAdmin 12 }

thresholdEthTxEntry OBJECT-TYPE
    SYNTAX      ThresholdEthTxEntry
    MAX-ACCESS  not-accessible
    STATUS      current
    DESCRIPTION   ""
    INDEX       {
                  entityIndex
                }
    ::=  { thresholdEthTxTable 1 }

ThresholdEthTxEntry ::=  SEQUENCE
  { thresholdEthTxPauseFramesHighThres15Min Unsigned32,
    thresholdEthTxPauseFramesHighThres1Day Unsigned32,
    thresholdEthTxCrcFramesEgressHighThres15Min Unsigned32,
    thresholdEthTxCrcFramesEgressHighThres1Day Unsigned32 }

thresholdEthTxPauseFramesHighThres15Min OBJECT-TYPE
    SYNTAX      Unsigned32 (0..900 | 4294967295)
    MAX-ACCESS  read-write
    STATUS      current
    DESCRIPTION
        "Pause Frames Transmitted 15 Minute Threshold" 
    ::=  { thresholdEthTxEntry 1 }

thresholdEthTxPauseFramesHighThres1Day OBJECT-TYPE
    SYNTAX      Unsigned32 (0..86400 | 4294967295)
    MAX-ACCESS  read-write
    STATUS      current
    DESCRIPTION
        "Pause Frames Transmitted 1 Day Threshold" 
    ::=  { thresholdEthTxEntry 2 }

thresholdEthTxCrcFramesEgressHighThres15Min OBJECT-TYPE
    SYNTAX      Unsigned32 (0..900 | 4294967295)
    MAX-ACCESS  read-write
    STATUS      current
    DESCRIPTION
        "Egress CRC Errored Frames Received 15 Minute Threshold" 
    ::=  { thresholdEthTxEntry 3 }

thresholdEthTxCrcFramesEgressHighThres1Day OBJECT-TYPE
    SYNTAX      Unsigned32 (0..86400 | 4294967295)
    MAX-ACCESS  read-write
    STATUS      current
    DESCRIPTION
        "Egress CRC Errored Frames Received 1 Day Threshold" 
    ::=  { thresholdEthTxEntry 4 }

thresholdGfpTable OBJECT-TYPE
    SYNTAX      SEQUENCE OF ThresholdGfpEntry
    MAX-ACCESS  not-accessible
    STATUS      deprecated
    DESCRIPTION   ""
    ::=  { performanceAdmin 13 }

thresholdGfpEntry OBJECT-TYPE
    SYNTAX      ThresholdGfpEntry
    MAX-ACCESS  not-accessible
    STATUS      deprecated
    DESCRIPTION   ""
    INDEX       {
                  entityIndex
                }
    ::=  { thresholdGfpTable 1 }

ThresholdGfpEntry ::=  SEQUENCE
  { thresholdGfpCoreHecCorrectedFramesHighThres15Min Unsigned32,
    thresholdGfpCoreHecCorrectedFramesHighThres1Day Unsigned32,
    thresholdGfpTypeHecCorrectedFramesHighThres15Min Unsigned32,
    thresholdGfpTypeHecCorrectedFramesHighThres15Day Unsigned32,
    thresholdGfpTypeHecDiscardedFramesHighThres15Min Unsigned32,
    thresholdGfpTypeHecDiscardedFramesHighThres1Day Unsigned32,
    thresholdGfpTHecDiscardedFramesHighThres1Day Counter64String }

thresholdGfpCoreHecCorrectedFramesHighThres15Min OBJECT-TYPE
    SYNTAX      Unsigned32 (0..900 | 4294967295)
    MAX-ACCESS  read-write
    STATUS      deprecated
    DESCRIPTION
        "Core HEC Corrected Frames 15 Minute Threshold" 
    ::=  { thresholdGfpEntry 1 }

thresholdGfpCoreHecCorrectedFramesHighThres1Day OBJECT-TYPE
    SYNTAX      Unsigned32 (0..86400 | 4294967295)
    MAX-ACCESS  read-write
    STATUS      deprecated
    DESCRIPTION
        "Core HEC Corrected Frames 1 Day Threshold" 
    ::=  { thresholdGfpEntry 2 }

thresholdGfpTypeHecCorrectedFramesHighThres15Min OBJECT-TYPE
    SYNTAX      Unsigned32 (0..900 | 4294967295)
    MAX-ACCESS  read-write
    STATUS      deprecated
    DESCRIPTION
        "Type Field HEC Corrected Frames 15 Minute Threshold" 
    ::=  { thresholdGfpEntry 3 }

thresholdGfpTypeHecCorrectedFramesHighThres15Day OBJECT-TYPE
    SYNTAX      Unsigned32 (0..86400 | 4294967295)
    MAX-ACCESS  read-write
    STATUS      deprecated
    DESCRIPTION
        "Type Field HEC Corrected Frames Day Threshold" 
    ::=  { thresholdGfpEntry 4 }

thresholdGfpTypeHecDiscardedFramesHighThres15Min OBJECT-TYPE
    SYNTAX      Unsigned32 (0..900 | 4294967295)
    MAX-ACCESS  read-write
    STATUS      deprecated
    DESCRIPTION
        "Type Field HEC Discarded Frames 15 Minute Threshold" 
    ::=  { thresholdGfpEntry 5 }

thresholdGfpTypeHecDiscardedFramesHighThres1Day OBJECT-TYPE
    SYNTAX      Unsigned32
    MAX-ACCESS  read-write
    STATUS      deprecated
    DESCRIPTION
        "Type Field HEC Discarded Frames High Threshold" 
    ::=  { thresholdGfpEntry 6 }

thresholdGfpTHecDiscardedFramesHighThres1Day OBJECT-TYPE
    SYNTAX      Counter64String
    MAX-ACCESS  read-write
    STATUS      deprecated
    DESCRIPTION
        "Type Field HEC Discarded Frames 1 Day Threshold" 
    ::=  { thresholdGfpEntry 7 }

thresholdIntrusionTable OBJECT-TYPE
    SYNTAX      SEQUENCE OF ThresholdIntrusionEntry
    MAX-ACCESS  not-accessible
    STATUS      current
    DESCRIPTION   ""
    ::=  { performanceAdmin 15 }

thresholdIntrusionEntry OBJECT-TYPE
    SYNTAX      ThresholdIntrusionEntry
    MAX-ACCESS  not-accessible
    STATUS      current
    DESCRIPTION   ""
    INDEX       {
                  entityIndex
                }
    ::=  { thresholdIntrusionTable 1 }

ThresholdIntrusionEntry ::=  SEQUENCE
  { thresholdIntrusionGradient Unsigned32 }

thresholdIntrusionGradient OBJECT-TYPE
    SYNTAX      Unsigned32 (5..990 | 4294967295) 
    UNITS       "0.1 dB/min"
    MAX-ACCESS  read-write
    STATUS      current
    DESCRIPTION   "Attenuation Gradient Threshold on Receive Fiber. Applies to both
         TRMT and RCV directions; but threshold violation is reported for
         each direction separately by the 'tapping' alarms: INTRUDE-RCV
         and INTRUDE-TRMT."
    ::=  { thresholdIntrusionEntry 1 }

thresholdOtuFecTable OBJECT-TYPE
    SYNTAX      SEQUENCE OF ThresholdOtuFecEntry
    MAX-ACCESS  not-accessible
    STATUS      deprecated
    DESCRIPTION   ""
    ::=  { performanceAdmin 16 }

thresholdOtuFecEntry OBJECT-TYPE
    SYNTAX      ThresholdOtuFecEntry
    MAX-ACCESS  not-accessible
    STATUS      deprecated
    DESCRIPTION   ""
    INDEX       {
                  entityIndex
                }
    ::=  { thresholdOtuFecTable 1 }

ThresholdOtuFecEntry ::=  SEQUENCE
  { thresholdOtuFecESHighThres15min Unsigned32,
    thresholdOtuFecESHighThres1day Unsigned32,
    thresholdOtuFecSESHighThres15min Unsigned32,
    thresholdOtuFecSESHighThres1day Unsigned32,
    thresholdOtuFecCEHighThres15min Unsigned32,
    thresholdOtuFecCEHighThres1day Unsigned32,
    thresholdOtuFecUBEHighThres15min Counter64String,
    thresholdOtuFecUBEHighThres1day Counter64String,
    thresholdOtuFecCErrHighThres15min Counter64String,
    thresholdOtuFecCErrHighThres1day Counter64String }

thresholdOtuFecESHighThres15min OBJECT-TYPE
    SYNTAX      Unsigned32 (0..900 | 4294967295)
    MAX-ACCESS  read-write
    STATUS      deprecated
    DESCRIPTION
        "OTU FEC Errored Seconds 15 Minute Threshold" 
    ::=  { thresholdOtuFecEntry 1 }

thresholdOtuFecESHighThres1day OBJECT-TYPE
    SYNTAX      Unsigned32 (0..86400 | 4294967295)
    MAX-ACCESS  read-write
    STATUS      deprecated
    DESCRIPTION
        "OTU FEC Errored Seconds Day Threshold" 
    ::=  { thresholdOtuFecEntry 2 }

thresholdOtuFecSESHighThres15min OBJECT-TYPE
    SYNTAX      Unsigned32 (0..900 | 4294967295)
    MAX-ACCESS  read-write
    STATUS      deprecated
    DESCRIPTION
        "OTU FEC Severely Errored Seconds 15 Minute Threshold" 
    ::=  { thresholdOtuFecEntry 3 }

thresholdOtuFecSESHighThres1day OBJECT-TYPE
    SYNTAX      Unsigned32 (0..86400 | 4294967295)
    MAX-ACCESS  read-write
    STATUS      deprecated
    DESCRIPTION
        "OTU FEC Severely Errored Seconds 1 Day Threshold" 
    ::=  { thresholdOtuFecEntry 4 }

thresholdOtuFecCEHighThres15min OBJECT-TYPE
    SYNTAX      Unsigned32
    MAX-ACCESS  read-write
    STATUS      deprecated
    DESCRIPTION
        "FEC Corrected Errors 15 Min Threshold" 
    ::=  { thresholdOtuFecEntry 5 }

thresholdOtuFecCEHighThres1day OBJECT-TYPE
    SYNTAX      Unsigned32
    MAX-ACCESS  read-write
    STATUS      deprecated
    DESCRIPTION
        "FEC Corrected Errors 1Day Threshold" 
    ::=  { thresholdOtuFecEntry 6 }

thresholdOtuFecUBEHighThres15min OBJECT-TYPE
    SYNTAX      Counter64String
    MAX-ACCESS  read-write
    STATUS      deprecated
    DESCRIPTION
        "Uncorrected Block Errors 15 Minute Threshold" 
    ::=  { thresholdOtuFecEntry 7 }

thresholdOtuFecUBEHighThres1day OBJECT-TYPE
    SYNTAX      Counter64String
    MAX-ACCESS  read-write
    STATUS      deprecated
    DESCRIPTION
        "Uncorrected Block Errors 1 Day Threshold" 
    ::=  { thresholdOtuFecEntry 8 }

thresholdOtuFecCErrHighThres15min OBJECT-TYPE
    SYNTAX      Counter64String
    MAX-ACCESS  read-write
    STATUS      deprecated
    DESCRIPTION
        "FEC Corrected Errors 15 Minute Threshold" 
    ::=  { thresholdOtuFecEntry 9 }

thresholdOtuFecCErrHighThres1day OBJECT-TYPE
    SYNTAX      Counter64String
    MAX-ACCESS  read-write
    STATUS      deprecated
    DESCRIPTION
        "FEC Corrected Errors 1 Day Threshold" 
    ::=  { thresholdOtuFecEntry 10 }

thresholdGfptTable OBJECT-TYPE
    SYNTAX      SEQUENCE OF ThresholdGfptEntry
    MAX-ACCESS  not-accessible
    STATUS      current
    DESCRIPTION   ""
    ::=  { performanceAdmin 17 }

thresholdGfptEntry OBJECT-TYPE
    SYNTAX      ThresholdGfptEntry
    MAX-ACCESS  not-accessible
    STATUS      current
    DESCRIPTION   ""
    INDEX       {
                  entityIndex
                }
    ::=  { thresholdGfptTable 1 }

ThresholdGfptEntry ::=  SEQUENCE
  { thresholdGfptDiscardedSuperblocksHighThres15Min Unsigned32,
    thresholdGfptDiscardedSuperblocksHighThres1Day Unsigned32 }

thresholdGfptDiscardedSuperblocksHighThres15Min OBJECT-TYPE
    SYNTAX      Unsigned32 (0..900 | 4294967295)
    MAX-ACCESS  read-write
    STATUS      current
    DESCRIPTION
        "Discarded Super Blocks 15 Minute Threshold" 
    ::=  { thresholdGfptEntry 1 }

thresholdGfptDiscardedSuperblocksHighThres1Day OBJECT-TYPE
    SYNTAX      Unsigned32 (0..86400 | 4294967295)
    MAX-ACCESS  read-write
    STATUS      current
    DESCRIPTION
        "Discarded Super Blocks 1 Day Threshold" 
    ::=  { thresholdGfptEntry 2 }

thresholdSubAggregateTable OBJECT-TYPE
    SYNTAX      SEQUENCE OF ThresholdSubAggregateEntry
    MAX-ACCESS  not-accessible
    STATUS      current
    DESCRIPTION   ""
    ::=  { performanceAdmin 18 }

thresholdSubAggregateEntry OBJECT-TYPE
    SYNTAX      ThresholdSubAggregateEntry
    MAX-ACCESS  not-accessible
    STATUS      current
    DESCRIPTION   ""
    INDEX       {
                  entityIndex
                }
    ::=  { thresholdSubAggregateTable 1 }

ThresholdSubAggregateEntry ::=  SEQUENCE
  { thresholdSubAggregateESHighThres15min Unsigned32,
    thresholdSubAggregateESHighThres1day Unsigned32,
    thresholdSubAggregateSESHighThres15min Unsigned32,
    thresholdSubAggregateSESHighThres1day Unsigned32 }

thresholdSubAggregateESHighThres15min OBJECT-TYPE
    SYNTAX      Unsigned32 (0..900 | 4294967295)
    MAX-ACCESS  read-write
    STATUS      current
    DESCRIPTION
        "Multiplexer Errored Seconds 15 Minute Threshold" 
    ::=  { thresholdSubAggregateEntry 1 }

thresholdSubAggregateESHighThres1day OBJECT-TYPE
    SYNTAX      Unsigned32 (0..86400 | 4294967295)
    MAX-ACCESS  read-write
    STATUS      current
    DESCRIPTION
        "Multiplexer Errored Seconds 1 Day Threshold" 
    ::=  { thresholdSubAggregateEntry 2 }

thresholdSubAggregateSESHighThres15min OBJECT-TYPE
    SYNTAX      Unsigned32 (0..900 | 4294967295)
    MAX-ACCESS  read-write
    STATUS      current
    DESCRIPTION
        "Multiplexer Severely Errored Seconds 15 Minute Threshold" 
    ::=  { thresholdSubAggregateEntry 3 }

thresholdSubAggregateSESHighThres1day OBJECT-TYPE
    SYNTAX      Unsigned32 (0..86400 | 4294967295)
    MAX-ACCESS  read-write
    STATUS      current
    DESCRIPTION
        "Multiplexer Severely Errored Seconds 1 Day Threshold" 
    ::=  { thresholdSubAggregateEntry 4 }

thresholdOduTcmCTable OBJECT-TYPE
    SYNTAX      SEQUENCE OF ThresholdOduTcmCEntry
    MAX-ACCESS  not-accessible
    STATUS      current
    DESCRIPTION   ""
    ::=  { performanceAdmin 19 }

thresholdOduTcmCEntry OBJECT-TYPE
    SYNTAX      ThresholdOduTcmCEntry
    MAX-ACCESS  not-accessible
    STATUS      current
    DESCRIPTION   ""
    INDEX       {
                  entityIndex
                }
    ::=  { thresholdOduTcmCTable 1 }

ThresholdOduTcmCEntry ::=  SEQUENCE
  { thresholdOduTcmCBESHighThres15min Unsigned32,
    thresholdOduTcmCESHighThres1day Unsigned32,
    thresholdOduTcmCSESHighThres15min Unsigned32,
    thresholdOduTcmCSESHighThres1day Unsigned32,
    thresholdOduTcmCOduTcmCBbeHighThres15min Counter64String,
    thresholdOduTcmCOduTcmCBbeHighThres1day Counter64String,
    thresholdOduTcmCUASHighThres15min Unsigned32,
    thresholdOduTcmCUASHighThres1day Unsigned32 }

thresholdOduTcmCBESHighThres15min OBJECT-TYPE
    SYNTAX      Unsigned32 (0..900 | 4294967295)
    MAX-ACCESS  read-write
    STATUS      current
    DESCRIPTION
        "ODU Tandem Connection Monitoring C Errored Seconds 15 Minute Threshold" 
    ::=  { thresholdOduTcmCEntry 1 }

thresholdOduTcmCESHighThres1day OBJECT-TYPE
    SYNTAX      Unsigned32 (0..86400 | 4294967295)
    MAX-ACCESS  read-write
    STATUS      current
    DESCRIPTION
        "ODU Tandem Connection Monitoring C Errored Seconds 1 Day Threshold" 
    ::=  { thresholdOduTcmCEntry 2 }

thresholdOduTcmCSESHighThres15min OBJECT-TYPE
    SYNTAX      Unsigned32 (0..900 | 4294967295)
    MAX-ACCESS  read-write
    STATUS      current
    DESCRIPTION
        "Tandem Connection Monitor C Section Severely Errored Seconds 15 Minute Threshold" 
    ::=  { thresholdOduTcmCEntry 3 }

thresholdOduTcmCSESHighThres1day OBJECT-TYPE
    SYNTAX      Unsigned32 (0..86400 | 4294967295)
    MAX-ACCESS  read-write
    STATUS      current
    DESCRIPTION
        "Tandem Connection Monitor C Section Severely Errored Seconds 1 Day Threshold" 
    ::=  { thresholdOduTcmCEntry 4 }

thresholdOduTcmCOduTcmCBbeHighThres15min OBJECT-TYPE
    SYNTAX      Counter64String
    MAX-ACCESS  read-write
    STATUS      current
    DESCRIPTION
        "ODU Tandem Connection C Background Block Errors 15 Minute Threshold" 
    ::=  { thresholdOduTcmCEntry 5 }

thresholdOduTcmCOduTcmCBbeHighThres1day OBJECT-TYPE
    SYNTAX      Counter64String
    MAX-ACCESS  read-write
    STATUS      current
    DESCRIPTION
        "ODU Tandem Connection C Background Block Errors 1 Day Threshold" 
    ::=  { thresholdOduTcmCEntry 6 }

thresholdOduTcmCUASHighThres15min OBJECT-TYPE
    SYNTAX      Unsigned32 (0..900 | 4294967295)
    MAX-ACCESS  read-write
    STATUS      current
    DESCRIPTION
        "ODU Tandem Connection Monitoring C Unavailable Seconds 15 Minute Threshold" 
    ::=  { thresholdOduTcmCEntry 7 }

thresholdOduTcmCUASHighThres1day OBJECT-TYPE
    SYNTAX      Unsigned32 (0..86400 | 4294967295)
    MAX-ACCESS  read-write
    STATUS      current
    DESCRIPTION
        "ODU Tandem Connection Monitoring C Unavailable Seconds 1 Day Threshold" 
    ::=  { thresholdOduTcmCEntry 8 }

thresholdPhysConvHighSpeedTable OBJECT-TYPE
    SYNTAX      SEQUENCE OF ThresholdPhysConvHighSpeedEntry
    MAX-ACCESS  not-accessible
    STATUS      current
    DESCRIPTION   ""
    ::=  { performanceAdmin 20 }

thresholdPhysConvHighSpeedEntry OBJECT-TYPE
    SYNTAX      ThresholdPhysConvHighSpeedEntry
    MAX-ACCESS  not-accessible
    STATUS      current
    DESCRIPTION   ""
    INDEX       {
                  entityIndex
                }
    ::=  { thresholdPhysConvHighSpeedTable 1 }

ThresholdPhysConvHighSpeedEntry ::=  SEQUENCE
  { thresholdPhysConvHighSpeedESHighThres15min Unsigned32,
    thresholdPhysConvHighSpeedESHighThres1day Unsigned32,
    thresholdPhysConvHighSpeedCVHighThres15min Counter64String,
    thresholdPhysConvHighSpeedCVHighThres1day Counter64String,
    thresholdPhysConvHighSpeedSEHighThres15min Unsigned32,
    thresholdPhysConvHighSpeedSEHighThres1day Unsigned32 }

thresholdPhysConvHighSpeedESHighThres15min OBJECT-TYPE
    SYNTAX      Unsigned32 (0..900 | 4294967295)
    MAX-ACCESS  read-write
    STATUS      current
    DESCRIPTION
        "Physical Coding Layer Errored Seconds 15 Minute Threshold" 
    ::=  { thresholdPhysConvHighSpeedEntry 1 }

thresholdPhysConvHighSpeedESHighThres1day OBJECT-TYPE
    SYNTAX      Unsigned32 (0..89400 | 4294967295)
    MAX-ACCESS  read-write
    STATUS      current
    DESCRIPTION
        "Physical Coding Layer Errored Seconds 1 Day Threshold" 
    ::=  { thresholdPhysConvHighSpeedEntry 2 }

thresholdPhysConvHighSpeedCVHighThres15min OBJECT-TYPE
    SYNTAX      Counter64String
    MAX-ACCESS  read-write
    STATUS      current
    DESCRIPTION
        "Physical Coding Layer 15 Minute Threshold" 
    ::=  { thresholdPhysConvHighSpeedEntry 3 }

thresholdPhysConvHighSpeedCVHighThres1day OBJECT-TYPE
    SYNTAX      Counter64String
    MAX-ACCESS  read-write
    STATUS      current
    DESCRIPTION
        "Physical Coding Layer Coding Violations 1 Day Threshold" 
    ::=  { thresholdPhysConvHighSpeedEntry 4 }

thresholdPhysConvHighSpeedSEHighThres15min OBJECT-TYPE
    SYNTAX      Unsigned32 (0..900 | 4294967295)
    MAX-ACCESS  read-write
    STATUS      current
    DESCRIPTION
        "Physical Coding Layer Sync Header Errors 15 Minute Threshold" 
    ::=  { thresholdPhysConvHighSpeedEntry 5 }

thresholdPhysConvHighSpeedSEHighThres1day OBJECT-TYPE
    SYNTAX      Unsigned32 (0..86400 | 4294967295)
    MAX-ACCESS  read-write
    STATUS      current
    DESCRIPTION
        "Physical Coding Layer Sync Header Errors 1 Day Threshold" 
    ::=  { thresholdPhysConvHighSpeedEntry 6 }

thresholdEthRxHighSpeedTable OBJECT-TYPE
    SYNTAX      SEQUENCE OF ThresholdEthRxHighSpeedEntry
    MAX-ACCESS  not-accessible
    STATUS      current
    DESCRIPTION   ""
    ::=  { performanceAdmin 21 }

thresholdEthRxHighSpeedEntry OBJECT-TYPE
    SYNTAX      ThresholdEthRxHighSpeedEntry
    MAX-ACCESS  not-accessible
    STATUS      current
    DESCRIPTION   ""
    INDEX       {
                  entityIndex
                }
    ::=  { thresholdEthRxHighSpeedTable 1 }

ThresholdEthRxHighSpeedEntry ::=  SEQUENCE
  { thresholdEthRxHighSpeedPauseFramesHighThres15Min Unsigned32,
    thresholdEthRxHighSpeedPauseFramesHighThres1Day Unsigned32,
    thresholdEthRxHighSpeedCrcFramesHighThres15Min Unsigned32,
    thresholdEthRxHighSpeedCrcFramesHighThres1Day Unsigned32 }

thresholdEthRxHighSpeedPauseFramesHighThres15Min OBJECT-TYPE
    SYNTAX      Unsigned32 (0..900 | 4294967295)
    MAX-ACCESS  read-write
    STATUS      current
    DESCRIPTION
        "Pause Frames Received 15 Minute Threshold" 
    ::=  { thresholdEthRxHighSpeedEntry 1 }

thresholdEthRxHighSpeedPauseFramesHighThres1Day OBJECT-TYPE
    SYNTAX      Unsigned32 (0..86400 | 4294967295)
    MAX-ACCESS  read-write
    STATUS      current
    DESCRIPTION
        "Pause Frames Received 1 Day Threshold" 
    ::=  { thresholdEthRxHighSpeedEntry 2 }

thresholdEthRxHighSpeedCrcFramesHighThres15Min OBJECT-TYPE
    SYNTAX      Unsigned32 (0..900 | 4294967295)
    MAX-ACCESS  read-write
    STATUS      current
    DESCRIPTION
        "Received CRC Errors 15 Minute Threshold" 
    ::=  { thresholdEthRxHighSpeedEntry 3 }

thresholdEthRxHighSpeedCrcFramesHighThres1Day OBJECT-TYPE
    SYNTAX      Unsigned32 (0..86400 | 4294967295)
    MAX-ACCESS  read-write
    STATUS      current
    DESCRIPTION
        "Received CRC Errors 1 Day Threshold" 
    ::=  { thresholdEthRxHighSpeedEntry 4 }

thresholdPhysPerfCapTable OBJECT-TYPE
    SYNTAX      SEQUENCE OF ThresholdPhysPerfCapEntry
    MAX-ACCESS  not-accessible
    STATUS      current
    DESCRIPTION   ""
    ::=  { performanceAdmin 22 }

thresholdPhysPerfCapEntry OBJECT-TYPE
    SYNTAX      ThresholdPhysPerfCapEntry
    MAX-ACCESS  not-accessible
    STATUS      current
    DESCRIPTION   ""
    INDEX       {
                  entityIndex
                }
    ::=  { thresholdPhysPerfCapTable 1 }

ThresholdPhysPerfCapEntry ::=  SEQUENCE
  { thresholdPhysPerfCapOpticalInputPwrLow FspR7Integer32Caps,
    thresholdPhysPerfCapOpticalInputPwrHigh FspR7Integer32Caps,
    thresholdPhysPerfCapAttRxLow FspR7Integer32Caps,
    thresholdPhysPerfCapAttRxHigh FspR7Integer32Caps,
    thresholdPhysPerfCapAttTxLow FspR7Integer32Caps,
    thresholdPhysPerfCapAttTxHigh FspR7Integer32Caps,
    thresholdPhysPerfCapOscPwrRcvHighThres FspR7Integer32Caps,
    thresholdPhysPerfCapOscPwrRcvLowThres FspR7Integer32Caps,
    thresholdPhysPerfCapConfigurableOpticalOutputPwrLow FspR7Integer32Caps,
    thresholdPhysPerfCapConfigurableOpticalOutputPwrHigh FspR7Integer32Caps,
    thresholdPhysPerfCapBrPwrReceivedHighThres FspR7Integer32Caps,
    thresholdPhysPerfCapDispersionCompensationLowThres FspR7Integer32Caps,
    thresholdPhysPerfCapDispersionCompensationHighThres FspR7Integer32Caps,
    thresholdPhysPerfCapLowerAtlinkThres FspR7Integer32Caps,
    thresholdPhysPerfCapUpperAtlinkThres FspR7Integer32Caps,
    thresholdPhysPerfCapLatencyLowThres FspR7Integer32Caps,
    thresholdPhysPerfCapLatencyHighThres FspR7Integer32Caps,
    thresholdPhysPerfCapRoundTripDelayHighThres FspR7Integer32Caps,
    thresholdPhysPerfCapRoundTripDelayLowThres FspR7Integer32Caps,
    thresholdPhysPerfCapDifferentialGroupDelayHigh FspR7Integer32Caps,
    thresholdPhysPerfCapChromaticDispersionLow FspR7Integer32Caps,
    thresholdPhysPerfCapChromaticDispersionHigh FspR7Integer32Caps,
    thresholdPhysPerfCapSignalToNoiseRatioLow FspR7Integer32Caps,
    thresholdPhysPerfCapCarrierFreqOffsetLow FspR7Integer32Caps,
    thresholdPhysPerfCapCarrierFreqOffsetHigh FspR7Integer32Caps,
    thresholdPhysPerfCapLogicalLanesSkewHigh FspR7Integer32Caps }

thresholdPhysPerfCapOpticalInputPwrLow OBJECT-TYPE
    SYNTAX      FspR7Integer32Caps
    UNITS       "0.1 dBm"
    MAX-ACCESS  read-only
    STATUS      current
    DESCRIPTION   "This object contains capabilities for ThresholdPhysPerfOpticalInputPwrLow object."
    ::=  { thresholdPhysPerfCapEntry 1 }

thresholdPhysPerfCapOpticalInputPwrHigh OBJECT-TYPE
    SYNTAX      FspR7Integer32Caps
    UNITS       "0.1 dBm"
    MAX-ACCESS  read-only
    STATUS      current
    DESCRIPTION   "This object contains capabilities for ThresholdPhysPerfOpticalInputPwrHigh object."
    ::=  { thresholdPhysPerfCapEntry 2 }

thresholdPhysPerfCapAttRxLow OBJECT-TYPE
    SYNTAX      FspR7Integer32Caps
    UNITS       "0.1 dB"
    MAX-ACCESS  read-only
    STATUS      current
    DESCRIPTION   "This object contains capabilities for ThresholdPhysPerfAttRxLow object."
    ::=  { thresholdPhysPerfCapEntry 3 }

thresholdPhysPerfCapAttRxHigh OBJECT-TYPE
    SYNTAX      FspR7Integer32Caps
    UNITS       "0.1 dB"
    MAX-ACCESS  read-only
    STATUS      current
    DESCRIPTION   "This object contains capabilities for ThresholdPhysPerfAttRxHigh object."
    ::=  { thresholdPhysPerfCapEntry 4 }

thresholdPhysPerfCapAttTxLow OBJECT-TYPE
    SYNTAX      FspR7Integer32Caps
    UNITS       "0.1 dB"
    MAX-ACCESS  read-only
    STATUS      current
    DESCRIPTION   "This object contains capabilities for ThresholdPhysPerfAttTxLow object."
    ::=  { thresholdPhysPerfCapEntry 5 }

thresholdPhysPerfCapAttTxHigh OBJECT-TYPE
    SYNTAX      FspR7Integer32Caps
    UNITS       "0.1 dB"
    MAX-ACCESS  read-only
    STATUS      current
    DESCRIPTION   "This object contains capabilities for ThresholdPhysPerfAttTxHigh object."
    ::=  { thresholdPhysPerfCapEntry 6 }

thresholdPhysPerfCapOscPwrRcvHighThres OBJECT-TYPE
    SYNTAX      FspR7Integer32Caps
    UNITS       "0.1 dBm"
    MAX-ACCESS  read-only
    STATUS      current
    DESCRIPTION   "This object contains capabilities for ThresholdPhysPerfOscPwrRcvHighThres object."
    ::=  { thresholdPhysPerfCapEntry 7 }

thresholdPhysPerfCapOscPwrRcvLowThres OBJECT-TYPE
    SYNTAX      FspR7Integer32Caps
    UNITS       "0.1 dBm"
    MAX-ACCESS  read-only
    STATUS      current
    DESCRIPTION   "This object contains capabilities for ThresholdPhysPerfOscPwrRcvLowThres object."
    ::=  { thresholdPhysPerfCapEntry 8 }

thresholdPhysPerfCapConfigurableOpticalOutputPwrLow OBJECT-TYPE
    SYNTAX      FspR7Integer32Caps
    UNITS       "0.1 dBm"
    MAX-ACCESS  read-only
    STATUS      current
    DESCRIPTION   "This object contains capabilities for ThresholdPhysPerfConfigurableOpticalOutputPwrLow object."
    ::=  { thresholdPhysPerfCapEntry 9 }

thresholdPhysPerfCapConfigurableOpticalOutputPwrHigh OBJECT-TYPE
    SYNTAX      FspR7Integer32Caps
    UNITS       "0.1 dBm"
    MAX-ACCESS  read-only
    STATUS      current
    DESCRIPTION   "This object contains capabilities for ThresholdPhysPerfConfigurableOpticalOutputPwrHigh object."
    ::=  { thresholdPhysPerfCapEntry 10 }

thresholdPhysPerfCapBrPwrReceivedHighThres OBJECT-TYPE
    SYNTAX      FspR7Integer32Caps
    UNITS       "0.1 dB"
    MAX-ACCESS  read-only
    STATUS      current
    DESCRIPTION   "This object contains capabilities for ThresholdPhysPerfBrPwrReceivedHighThres object."
    ::=  { thresholdPhysPerfCapEntry 11 }

thresholdPhysPerfCapDispersionCompensationLowThres OBJECT-TYPE
    SYNTAX      FspR7Integer32Caps
    UNITS       "ps/nm"
    MAX-ACCESS  read-only
    STATUS      current
    DESCRIPTION   "This object contains capabilities for ThresholdPhysPerfDispersionCompensationLowThres object."
    ::=  { thresholdPhysPerfCapEntry 12 }

thresholdPhysPerfCapDispersionCompensationHighThres OBJECT-TYPE
    SYNTAX      FspR7Integer32Caps
    UNITS       "ps/nm"
    MAX-ACCESS  read-only
    STATUS      current
    DESCRIPTION   "This object contains capabilities for ThresholdPhysPerfDispersionCompensationHighThres object."
    ::=  { thresholdPhysPerfCapEntry 13 }

thresholdPhysPerfCapLowerAtlinkThres OBJECT-TYPE
    SYNTAX      FspR7Integer32Caps
    UNITS       "0.1 dB"
    MAX-ACCESS  read-only
    STATUS      current
    DESCRIPTION   "This object contains capabilities for ThresholdPhysPerfLowerAtlinkThres object."
    ::=  { thresholdPhysPerfCapEntry 14 }

thresholdPhysPerfCapUpperAtlinkThres OBJECT-TYPE
    SYNTAX      FspR7Integer32Caps
    UNITS       "0.1 dB"
    MAX-ACCESS  read-only
    STATUS      current
    DESCRIPTION   "This object contains capabilities for ThresholdPhysPerfUpperAtlinkThres object."
    ::=  { thresholdPhysPerfCapEntry 15 }

thresholdPhysPerfCapLatencyLowThres OBJECT-TYPE
    SYNTAX      FspR7Integer32Caps
    UNITS       "0.1 us"
    MAX-ACCESS  read-only
    STATUS      current
    DESCRIPTION   "This object contains capabilities for ThresholdPhysPerfLatencyLowThres object."
    ::=  { thresholdPhysPerfCapEntry 16 }

thresholdPhysPerfCapLatencyHighThres OBJECT-TYPE
    SYNTAX      FspR7Integer32Caps
    UNITS       "0.1 us"
    MAX-ACCESS  read-only
    STATUS      current
    DESCRIPTION   "This object contains capabilities for ThresholdPhysPerfLatencyHighThres object."
    ::=  { thresholdPhysPerfCapEntry 17 }

thresholdPhysPerfCapRoundTripDelayHighThres OBJECT-TYPE
    SYNTAX      FspR7Integer32Caps
    UNITS       "ns"
    MAX-ACCESS  read-only
    STATUS      current
    DESCRIPTION
        "Configurable high threshold for round trip delay" 
    ::=  { thresholdPhysPerfCapEntry 18 }

thresholdPhysPerfCapRoundTripDelayLowThres OBJECT-TYPE
    SYNTAX      FspR7Integer32Caps
    UNITS       "ns"
    MAX-ACCESS  read-only
    STATUS      current
    DESCRIPTION
        "Configurable low threshold for round trip delay" 
    ::=  { thresholdPhysPerfCapEntry 19 }

thresholdPhysPerfCapDifferentialGroupDelayHigh OBJECT-TYPE
    SYNTAX      FspR7Integer32Caps
    UNITS       "ps"
    MAX-ACCESS  read-only
    STATUS      current
    DESCRIPTION
        "Differential Group Delay High TH" 
    ::=  { thresholdPhysPerfCapEntry 20 }

thresholdPhysPerfCapChromaticDispersionLow OBJECT-TYPE
    SYNTAX      FspR7Integer32Caps
    UNITS       "ps/nm"
    MAX-ACCESS  read-only
    STATUS      current
    DESCRIPTION
        "Chromatic Dispersion Compensation Low Threshold" 
    ::=  { thresholdPhysPerfCapEntry 21 }

thresholdPhysPerfCapChromaticDispersionHigh OBJECT-TYPE
    SYNTAX      FspR7Integer32Caps
    UNITS       "ps/nm"
    MAX-ACCESS  read-only
    STATUS      current
    DESCRIPTION
        "Chromatic Dispersion Compensation High Threshold" 
    ::=  { thresholdPhysPerfCapEntry 22 }

thresholdPhysPerfCapSignalToNoiseRatioLow OBJECT-TYPE
    SYNTAX      FspR7Integer32Caps
    UNITS       "0.1 dB"
    MAX-ACCESS  read-only
    STATUS      current
    DESCRIPTION
        "Signal-to-Noise Ratio Low TH" 
    ::=  { thresholdPhysPerfCapEntry 23 }

thresholdPhysPerfCapCarrierFreqOffsetLow OBJECT-TYPE
    SYNTAX      FspR7Integer32Caps
    UNITS       "0.001 GHz"
    MAX-ACCESS  read-only
    STATUS      current
    DESCRIPTION
        "Carrier Frequency Offset Low TH" 
    ::=  { thresholdPhysPerfCapEntry 24 }

thresholdPhysPerfCapCarrierFreqOffsetHigh OBJECT-TYPE
    SYNTAX      FspR7Integer32Caps
    UNITS       "0.001 GHz"
    MAX-ACCESS  read-only
    STATUS      current
    DESCRIPTION
        "Carrier Frequency Offset High TH" 
    ::=  { thresholdPhysPerfCapEntry 25 }

thresholdPhysPerfCapLogicalLanesSkewHigh OBJECT-TYPE
    SYNTAX      FspR7Integer32Caps
    UNITS       "ns"
    MAX-ACCESS  read-only
    STATUS      current
    DESCRIPTION
        "Skew between logical lanes farthest apart high threshold" 
    ::=  { thresholdPhysPerfCapEntry 26 }

thresholdFarEndPhysPerfTable OBJECT-TYPE
    SYNTAX      SEQUENCE OF ThresholdFarEndPhysPerfEntry
    MAX-ACCESS  not-accessible
    STATUS      current
    DESCRIPTION   ""
    ::=  { performanceAdmin 23 }

thresholdFarEndPhysPerfEntry OBJECT-TYPE
    SYNTAX      ThresholdFarEndPhysPerfEntry
    MAX-ACCESS  not-accessible
    STATUS      current
    DESCRIPTION   ""
    INDEX       {
                  entityIndex
                }
    ::=  { thresholdFarEndPhysPerfTable 1 }

ThresholdFarEndPhysPerfEntry ::=  SEQUENCE
  { thresholdFarEndPhysPerfOpticalInputPwrLow Integer32,
    thresholdFarEndPhysPerfOpticalInputPwrHigh Integer32,
    thresholdFarEndPhysPerfOpticalOutputPwrLow Integer32,
    thresholdFarEndPhysPerfOpticalOutputPwrHigh Integer32 }

thresholdFarEndPhysPerfOpticalInputPwrLow OBJECT-TYPE
    SYNTAX      Integer32 (-450..260 | -2147483648) 
    UNITS       "0.1 dBm"
    MAX-ACCESS  read-write
    STATUS      current
    DESCRIPTION
        "Optical Input Power Received" 
    ::=  { thresholdFarEndPhysPerfEntry 1 }

thresholdFarEndPhysPerfOpticalInputPwrHigh OBJECT-TYPE
    SYNTAX      Integer32 (-450..270 | -2147483648) 
    UNITS       "0.1 dBm"
    MAX-ACCESS  read-write
    STATUS      current
    DESCRIPTION
        "Optical Input Power Received" 
    ::=  { thresholdFarEndPhysPerfEntry 2 }

thresholdFarEndPhysPerfOpticalOutputPwrLow OBJECT-TYPE
    SYNTAX      Integer32 
    UNITS       "0.1 dBm"
    MAX-ACCESS  read-only
    STATUS      current
    DESCRIPTION
        "Low fixed threshold of the Optical Power Transmitted (output)" 
    ::=  { thresholdFarEndPhysPerfEntry 3 }

thresholdFarEndPhysPerfOpticalOutputPwrHigh OBJECT-TYPE
    SYNTAX      Integer32 
    UNITS       "0.1 dBm"
    MAX-ACCESS  read-only
    STATUS      current
    DESCRIPTION
        "High fixed threshold of the Optical Power Transmitted (output)" 
    ::=  { thresholdFarEndPhysPerfEntry 4 }

thresholdFarEndPhysPerfCapTable OBJECT-TYPE
    SYNTAX      SEQUENCE OF ThresholdFarEndPhysPerfCapEntry
    MAX-ACCESS  not-accessible
    STATUS      current
    DESCRIPTION   ""
    ::=  { performanceAdmin 24 }

thresholdFarEndPhysPerfCapEntry OBJECT-TYPE
    SYNTAX      ThresholdFarEndPhysPerfCapEntry
    MAX-ACCESS  not-accessible
    STATUS      current
    DESCRIPTION   ""
    INDEX       {
                  entityIndex
                }
    ::=  { thresholdFarEndPhysPerfCapTable 1 }

ThresholdFarEndPhysPerfCapEntry ::=  SEQUENCE
  { thresholdFarEndPhysPerfCapOpticalInputPwrLow FspR7Integer32Caps,
    thresholdFarEndPhysPerfCapOpticalInputPwrHigh FspR7Integer32Caps }

thresholdFarEndPhysPerfCapOpticalInputPwrLow OBJECT-TYPE
    SYNTAX      FspR7Integer32Caps
    UNITS       "0.1 dBm"
    MAX-ACCESS  read-only
    STATUS      current
    DESCRIPTION   "This object contains capabilities for ThresholdPhysPerfOpticalInputPwrLow object."
    ::=  { thresholdFarEndPhysPerfCapEntry 1 }

thresholdFarEndPhysPerfCapOpticalInputPwrHigh OBJECT-TYPE
    SYNTAX      FspR7Integer32Caps
    UNITS       "0.1 dBm"
    MAX-ACCESS  read-only
    STATUS      current
    DESCRIPTION   "This object contains capabilities for ThresholdPhysPerfOpticalInputPwrHigh object."
    ::=  { thresholdFarEndPhysPerfCapEntry 2 }

thresholdPhysConvTxHighSpeedTable OBJECT-TYPE
    SYNTAX      SEQUENCE OF ThresholdPhysConvTxHighSpeedEntry
    MAX-ACCESS  not-accessible
    STATUS      current
    DESCRIPTION   ""
    ::=  { performanceAdmin 25 }

thresholdPhysConvTxHighSpeedEntry OBJECT-TYPE
    SYNTAX      ThresholdPhysConvTxHighSpeedEntry
    MAX-ACCESS  not-accessible
    STATUS      current
    DESCRIPTION   ""
    INDEX       {
                  entityIndex
                }
    ::=  { thresholdPhysConvTxHighSpeedTable 1 }

ThresholdPhysConvTxHighSpeedEntry ::=  SEQUENCE
  { thresholdPhysConvTxHighSpeedESTXHighThres15min Unsigned32,
    thresholdPhysConvTxHighSpeedESTXHighThres1day Unsigned32,
    thresholdPhysConvTxHighSpeedCVTXHighThres15min Counter64String,
    thresholdPhysConvTxHighSpeedCVTXHighThres1day Counter64String,
    thresholdPhysConvTxHighSpeedSETXHighThres15min Unsigned32,
    thresholdPhysConvTxHighSpeedSETXHighThres1day Unsigned32 }

thresholdPhysConvTxHighSpeedESTXHighThres15min OBJECT-TYPE
    SYNTAX      Unsigned32 (0..900 | 4294967295)
    MAX-ACCESS  read-write
    STATUS      current
    DESCRIPTION
        "Physical Coding Layer Tx Errored Seconds 15 Minute Threshold" 
    ::=  { thresholdPhysConvTxHighSpeedEntry 1 }

thresholdPhysConvTxHighSpeedESTXHighThres1day OBJECT-TYPE
    SYNTAX      Unsigned32 (0..89400 | 4294967295)
    MAX-ACCESS  read-write
    STATUS      current
    DESCRIPTION
        "Physical Coding Layer Tx Errored Seconds 1 Day Threshold" 
    ::=  { thresholdPhysConvTxHighSpeedEntry 2 }

thresholdPhysConvTxHighSpeedCVTXHighThres15min OBJECT-TYPE
    SYNTAX      Counter64String
    MAX-ACCESS  read-write
    STATUS      current
    DESCRIPTION
        "Physical Coding Layer Transmit Coding Violations 15 Minute Threshold" 
    ::=  { thresholdPhysConvTxHighSpeedEntry 3 }

thresholdPhysConvTxHighSpeedCVTXHighThres1day OBJECT-TYPE
    SYNTAX      Counter64String
    MAX-ACCESS  read-write
    STATUS      current
    DESCRIPTION
        "Physical Coding Layer Transmit Coding Violations 1 Day Threshold" 
    ::=  { thresholdPhysConvTxHighSpeedEntry 4 }

thresholdPhysConvTxHighSpeedSETXHighThres15min OBJECT-TYPE
    SYNTAX      Unsigned32 (0..900 | 4294967295)
    MAX-ACCESS  read-write
    STATUS      current
    DESCRIPTION
        "Physical Coding Layer Sync Header Errors Tranmit 15 Minute Threshold" 
    ::=  { thresholdPhysConvTxHighSpeedEntry 5 }

thresholdPhysConvTxHighSpeedSETXHighThres1day OBJECT-TYPE
    SYNTAX      Unsigned32 (0..86400 | 4294967295)
    MAX-ACCESS  read-write
    STATUS      current
    DESCRIPTION
        "Physical Coding Layer Sync Header Errors Tranmit 1 Day Threshold" 
    ::=  { thresholdPhysConvTxHighSpeedEntry 6 }

thresholdType4PhysCodingLayerTable OBJECT-TYPE
    SYNTAX      SEQUENCE OF ThresholdType4PhysCodingLayerEntry
    MAX-ACCESS  not-accessible
    STATUS      current
    DESCRIPTION   ""
    ::=  { performanceAdmin 26 }

thresholdType4PhysCodingLayerEntry OBJECT-TYPE
    SYNTAX      ThresholdType4PhysCodingLayerEntry
    MAX-ACCESS  not-accessible
    STATUS      current
    DESCRIPTION   ""
    INDEX       {
                  entityIndex
                }
    ::=  { thresholdType4PhysCodingLayerTable 1 }

ThresholdType4PhysCodingLayerEntry ::=  SEQUENCE
  { thresholdType4PhysCodingLayerESHighThres15min Unsigned32,
    thresholdType4PhysCodingLayerESHighThres1day Unsigned32,
    thresholdType4PhysCodingLayerCVHighThres15min Counter64String,
    thresholdType4PhysCodingLayerCVHighThres1day Counter64String,
    thresholdType4PhysCodingLayerBBEHighThres15min Counter64String,
    thresholdType4PhysCodingLayerBBEHighThres1day Counter64String }

thresholdType4PhysCodingLayerESHighThres15min OBJECT-TYPE
    SYNTAX      Unsigned32 (0..900 | 4294967295)
    MAX-ACCESS  read-write
    STATUS      current
    DESCRIPTION
        "Physical Coding Layer Errored Seconds 15 Minute Threshold" 
    ::=  { thresholdType4PhysCodingLayerEntry 1 }

thresholdType4PhysCodingLayerESHighThres1day OBJECT-TYPE
    SYNTAX      Unsigned32 (0..89400 | 4294967295)
    MAX-ACCESS  read-write
    STATUS      current
    DESCRIPTION
        "Physical Coding Layer Errored Seconds 1 Day Threshold" 
    ::=  { thresholdType4PhysCodingLayerEntry 2 }

thresholdType4PhysCodingLayerCVHighThres15min OBJECT-TYPE
    SYNTAX      Counter64String
    MAX-ACCESS  read-write
    STATUS      current
    DESCRIPTION
        "Physical Coding Layer 15 Minute Threshold" 
    ::=  { thresholdType4PhysCodingLayerEntry 3 }

thresholdType4PhysCodingLayerCVHighThres1day OBJECT-TYPE
    SYNTAX      Counter64String
    MAX-ACCESS  read-write
    STATUS      current
    DESCRIPTION
        "Physical Coding Layer Coding Violations 1 Day Threshold" 
    ::=  { thresholdType4PhysCodingLayerEntry 4 }

thresholdType4PhysCodingLayerBBEHighThres15min OBJECT-TYPE
    SYNTAX      Counter64String
    MAX-ACCESS  read-write
    STATUS      current
    DESCRIPTION
        "PCS Background Block Errors 15 Minute Threshold" 
    ::=  { thresholdType4PhysCodingLayerEntry 5 }

thresholdType4PhysCodingLayerBBEHighThres1day OBJECT-TYPE
    SYNTAX      Counter64String
    MAX-ACCESS  read-write
    STATUS      current
    DESCRIPTION
        "PCS Background Block Errors 1 Day Threshold" 
    ::=  { thresholdType4PhysCodingLayerEntry 6 }

thresholdDefectSecondsTable OBJECT-TYPE
    SYNTAX      SEQUENCE OF ThresholdDefectSecondsEntry
    MAX-ACCESS  not-accessible
    STATUS      current
    DESCRIPTION   ""
    ::=  { performanceMIB 14 }

thresholdDefectSecondsEntry OBJECT-TYPE
    SYNTAX      ThresholdDefectSecondsEntry
    MAX-ACCESS  not-accessible
    STATUS      current
    DESCRIPTION   ""
    INDEX       {
                  entityIndex
                }
    ::=  { thresholdDefectSecondsTable 1 }

ThresholdDefectSecondsEntry ::=  SEQUENCE
  { thresholdDefectSecondsDefectSecondsHighThres15Min Unsigned32,
    thresholdDefectSecondsDefectSecondsHighThres1Day Unsigned32 }

thresholdDefectSecondsDefectSecondsHighThres15Min OBJECT-TYPE
    SYNTAX      Unsigned32 (0..900 | 4294967295)
    MAX-ACCESS  read-write
    STATUS      current
    DESCRIPTION
        "Defect Seconds 15 Minute Threshold" 
    ::=  { thresholdDefectSecondsEntry 1 }

thresholdDefectSecondsDefectSecondsHighThres1Day OBJECT-TYPE
    SYNTAX      Unsigned32 (0..86400 | 4294967295)
    MAX-ACCESS  read-write
    STATUS      current
    DESCRIPTION
        "Defect Seconds 1 Day Threshold" 
    ::=  { thresholdDefectSecondsEntry 2 }

currentOtu15minTable OBJECT-TYPE
    SYNTAX      SEQUENCE OF CurrentOtu15minEntry
    MAX-ACCESS  not-accessible
    STATUS      current
    DESCRIPTION   ""
    ::=  { performanceMonitoring 1 }

currentOtu15minEntry OBJECT-TYPE
    SYNTAX      CurrentOtu15minEntry
    MAX-ACCESS  not-accessible
    STATUS      current
    DESCRIPTION   ""
    INDEX       {
                  entityIndex
                }
    ::=  { currentOtu15minTable 1 }

CurrentOtu15minEntry ::=  SEQUENCE
  { currentOtu15minES Unsigned32,
    currentOtu15minSES Unsigned32,
    currentOtu15minBbe Counter64String,
    currentOtu15minUAS Unsigned32,
    currentOtu15minElapsedTime Integer32 }

currentOtu15minES OBJECT-TYPE
    SYNTAX      Unsigned32
    MAX-ACCESS  read-only
    STATUS      current
    DESCRIPTION
        "OTU Errored Seconds" 
    ::=  { currentOtu15minEntry 1 }

currentOtu15minSES OBJECT-TYPE
    SYNTAX      Unsigned32
    MAX-ACCESS  read-only
    STATUS      current
    DESCRIPTION
        "OTU Severely Errored Seconds" 
    ::=  { currentOtu15minEntry 2 }

currentOtu15minBbe OBJECT-TYPE
    SYNTAX      Counter64String
    MAX-ACCESS  read-only
    STATUS      current
    DESCRIPTION
        "OTU Background Block Errors" 
    ::=  { currentOtu15minEntry 3 }

currentOtu15minUAS OBJECT-TYPE
    SYNTAX      Unsigned32
    MAX-ACCESS  read-only
    STATUS      current
    DESCRIPTION
        "OTU Unavailable Seconds" 
    ::=  { currentOtu15minEntry 4 }

currentOtu15minElapsedTime OBJECT-TYPE
    SYNTAX      Integer32 (0..9000 | -2147483648)
    MAX-ACCESS  read-only
    STATUS      current
    DESCRIPTION
        "Elapsed 15Min" 
    ::=  { currentOtu15minEntry 5 }

currentOtu1dayTable OBJECT-TYPE
    SYNTAX      SEQUENCE OF CurrentOtu1dayEntry
    MAX-ACCESS  not-accessible
    STATUS      current
    DESCRIPTION   ""
    ::=  { performanceMonitoring 2 }

currentOtu1dayEntry OBJECT-TYPE
    SYNTAX      CurrentOtu1dayEntry
    MAX-ACCESS  not-accessible
    STATUS      current
    DESCRIPTION   ""
    INDEX       {
                  entityIndex
                }
    ::=  { currentOtu1dayTable 1 }

CurrentOtu1dayEntry ::=  SEQUENCE
  { currentOtu1dayES Unsigned32,
    currentOtu1daySES Unsigned32,
    currentOtu1dayBbe Counter64String,
    currentOtu1dayUAS Unsigned32,
    currentOtu1dayElapsedTime Integer32 }

currentOtu1dayES OBJECT-TYPE
    SYNTAX      Unsigned32
    MAX-ACCESS  read-only
    STATUS      current
    DESCRIPTION
        "OTU Errored Seconds" 
    ::=  { currentOtu1dayEntry 1 }

currentOtu1daySES OBJECT-TYPE
    SYNTAX      Unsigned32
    MAX-ACCESS  read-only
    STATUS      current
    DESCRIPTION
        "OTU Severely Errored Seconds" 
    ::=  { currentOtu1dayEntry 2 }

currentOtu1dayBbe OBJECT-TYPE
    SYNTAX      Counter64String
    MAX-ACCESS  read-only
    STATUS      current
    DESCRIPTION
        "OTU Background Block Errors" 
    ::=  { currentOtu1dayEntry 3 }

currentOtu1dayUAS OBJECT-TYPE
    SYNTAX      Unsigned32
    MAX-ACCESS  read-only
    STATUS      current
    DESCRIPTION
        "OTU Unavailable Seconds" 
    ::=  { currentOtu1dayEntry 4 }

currentOtu1dayElapsedTime OBJECT-TYPE
    SYNTAX      Integer32 (0..86400 | -2147483648)
    MAX-ACCESS  read-only
    STATUS      current
    DESCRIPTION
        "Elapsed 1Day" 
    ::=  { currentOtu1dayEntry 5 }

intervalOtu15minTable OBJECT-TYPE
    SYNTAX      SEQUENCE OF IntervalOtu15minEntry
    MAX-ACCESS  not-accessible
    STATUS      current
    DESCRIPTION   ""
    ::=  { performanceMonitoring 3 }

intervalOtu15minEntry OBJECT-TYPE
    SYNTAX      IntervalOtu15minEntry
    MAX-ACCESS  not-accessible
    STATUS      current
    DESCRIPTION   ""
    INDEX       {
                  entityIndex,
                  intervalOtu15minNumber
                }
    ::=  { intervalOtu15minTable 1 }

IntervalOtu15minEntry ::=  SEQUENCE
  { intervalOtu15minNumber Integer32,
    intervalOtu15minES Unsigned32,
    intervalOtu15minSES Unsigned32,
    intervalOtu15minBbe Counter64String,
    intervalOtu15minUAS Unsigned32,
    intervalOtu15minValidFlag TruthValue,
    intervalOtu15minTimeStamp DateAndTime }

intervalOtu15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalOtu15minEntry 1 }

intervalOtu15minES OBJECT-TYPE
    SYNTAX      Unsigned32
    MAX-ACCESS  read-only
    STATUS      current
    DESCRIPTION
        "OTU Errored Seconds" 
    ::=  { intervalOtu15minEntry 2 }

intervalOtu15minSES OBJECT-TYPE
    SYNTAX      Unsigned32
    MAX-ACCESS  read-only
    STATUS      current
    DESCRIPTION
        "OTU Severely Errored Seconds" 
    ::=  { intervalOtu15minEntry 3 }

intervalOtu15minBbe OBJECT-TYPE
    SYNTAX      Counter64String
    MAX-ACCESS  read-only
    STATUS      current
    DESCRIPTION
        "OTU Background Block Errors" 
    ::=  { intervalOtu15minEntry 4 }

intervalOtu15minUAS OBJECT-TYPE
    SYNTAX      Unsigned32
    MAX-ACCESS  read-only
    STATUS      current
    DESCRIPTION
        "OTU Unavailable Seconds" 
    ::=  { intervalOtu15minEntry 5 }

intervalOtu15minValidFlag OBJECT-TYPE
    SYNTAX      TruthValue
    MAX-ACCESS  read-only
    STATUS      current
    DESCRIPTION
        "Valid Flag" 
    ::=  { intervalOtu15minEntry 6 }

intervalOtu15minTimeStamp OBJECT-TYPE
    SYNTAX      DateAndTime
    MAX-ACCESS  read-only
    STATUS      current
    DESCRIPTION
        "Timestamp" 
    ::=  { intervalOtu15minEntry 7 }

intervalOtu1dayTable OBJECT-TYPE
    SYNTAX      SEQUENCE OF IntervalOtu1dayEntry
    MAX-ACCESS  not-accessible
    STATUS      current
    DESCRIPTION   ""
    ::=  { performanceMonitoring 4 }

intervalOtu1dayEntry OBJECT-TYPE
    SYNTAX      IntervalOtu1dayEntry
    MAX-ACCESS  not-accessible
    STATUS      current
    DESCRIPTION   ""
    INDEX       {
                  entityIndex,
                  intervalOtu1dayNumber
                }
    ::=  { intervalOtu1dayTable 1 }

IntervalOtu1dayEntry ::=  SEQUENCE
  { intervalOtu1dayNumber Integer32,
    intervalOtu1dayES Unsigned32,
    intervalOtu1daySES Unsigned32,
    intervalOtu1dayBbe Counter64String,
    intervalOtu1dayUAS Unsigned32,
    intervalOtu1dayValidFlag TruthValue,
    intervalOtu1dayTimeStamp DateAndTime }

intervalOtu1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalOtu1dayEntry 1 }

intervalOtu1dayES OBJECT-TYPE
    SYNTAX      Unsigned32
    MAX-ACCESS  read-only
    STATUS      current
    DESCRIPTION
        "OTU Errored Seconds" 
    ::=  { intervalOtu1dayEntry 2 }

intervalOtu1daySES OBJECT-TYPE
    SYNTAX      Unsigned32
    MAX-ACCESS  read-only
    STATUS      current
    DESCRIPTION
        "OTU Severely Errored Seconds" 
    ::=  { intervalOtu1dayEntry 3 }

intervalOtu1dayBbe OBJECT-TYPE
    SYNTAX      Counter64String
    MAX-ACCESS  read-only
    STATUS      current
    DESCRIPTION
        "OTU Background Block Errors" 
    ::=  { intervalOtu1dayEntry 4 }

intervalOtu1dayUAS OBJECT-TYPE
    SYNTAX      Unsigned32
    MAX-ACCESS  read-only
    STATUS      current
    DESCRIPTION
        "OTU Unavailable Seconds" 
    ::=  { intervalOtu1dayEntry 5 }

intervalOtu1dayValidFlag OBJECT-TYPE
    SYNTAX      TruthValue
    MAX-ACCESS  read-only
    STATUS      current
    DESCRIPTION
        "Valid Flag" 
    ::=  { intervalOtu1dayEntry 6 }

intervalOtu1dayTimeStamp OBJECT-TYPE
    SYNTAX      DateAndTime
    MAX-ACCESS  read-only
    STATUS      current
    DESCRIPTION
        "Timestamp" 
    ::=  { intervalOtu1dayEntry 7 }

currentOdu15minTable OBJECT-TYPE
    SYNTAX      SEQUENCE OF CurrentOdu15minEntry
    MAX-ACCESS  not-accessible
    STATUS      current
    DESCRIPTION   ""
    ::=  { performanceMonitoring 5 }

currentOdu15minEntry OBJECT-TYPE
    SYNTAX      CurrentOdu15minEntry
    MAX-ACCESS  not-accessible
    STATUS      current
    DESCRIPTION   ""
    INDEX       {
                  entityIndex
                }
    ::=  { currentOdu15minTable 1 }

CurrentOdu15minEntry ::=  SEQUENCE
  { currentOdu15minES Unsigned32,
    currentOdu15minSES Unsigned32,
    currentOdu15minBbe Counter64String,
    currentOdu15minUAS Unsigned32,
    currentOdu15minElapsedTime Integer32 }

currentOdu15minES OBJECT-TYPE
    SYNTAX      Unsigned32
    MAX-ACCESS  read-only
    STATUS      current
    DESCRIPTION
        "ODU Errored Seconds" 
    ::=  { currentOdu15minEntry 1 }

currentOdu15minSES OBJECT-TYPE
    SYNTAX      Unsigned32
    MAX-ACCESS  read-only
    STATUS      current
    DESCRIPTION
        "ODU Severely Errored Seconds" 
    ::=  { currentOdu15minEntry 2 }

currentOdu15minBbe OBJECT-TYPE
    SYNTAX      Counter64String
    MAX-ACCESS  read-only
    STATUS      current
    DESCRIPTION
        "ODU Background Block Errors" 
    ::=  { currentOdu15minEntry 3 }

currentOdu15minUAS OBJECT-TYPE
    SYNTAX      Unsigned32
    MAX-ACCESS  read-only
    STATUS      current
    DESCRIPTION
        "ODU Unavailable Seconds" 
    ::=  { currentOdu15minEntry 4 }

currentOdu15minElapsedTime OBJECT-TYPE
    SYNTAX      Integer32 (0..9000 | -2147483648)
    MAX-ACCESS  read-only
    STATUS      current
    DESCRIPTION
        "Elapsed 15Min" 
    ::=  { currentOdu15minEntry 5 }

currentOdu1dayTable OBJECT-TYPE
    SYNTAX      SEQUENCE OF CurrentOdu1dayEntry
    MAX-ACCESS  not-accessible
    STATUS      current
    DESCRIPTION   ""
    ::=  { performanceMonitoring 6 }

currentOdu1dayEntry OBJECT-TYPE
    SYNTAX      CurrentOdu1dayEntry
    MAX-ACCESS  not-accessible
    STATUS      current
    DESCRIPTION   ""
    INDEX       {
                  entityIndex
                }
    ::=  { currentOdu1dayTable 1 }

CurrentOdu1dayEntry ::=  SEQUENCE
  { currentOdu1dayES Unsigned32,
    currentOdu1daySES Unsigned32,
    currentOdu1dayBbe Counter64String,
    currentOdu1dayUAS Unsigned32,
    currentOdu1dayElapsedTime Integer32 }

currentOdu1dayES OBJECT-TYPE
    SYNTAX      Unsigned32
    MAX-ACCESS  read-only
    STATUS      current
    DESCRIPTION
        "ODU Errored Seconds" 
    ::=  { currentOdu1dayEntry 1 }

currentOdu1daySES OBJECT-TYPE
    SYNTAX      Unsigned32
    MAX-ACCESS  read-only
    STATUS      current
    DESCRIPTION
        "ODU Severely Errored Seconds" 
    ::=  { currentOdu1dayEntry 2 }

currentOdu1dayBbe OBJECT-TYPE
    SYNTAX      Counter64String
    MAX-ACCESS  read-only
    STATUS      current
    DESCRIPTION
        "ODU Background Block Errors" 
    ::=  { currentOdu1dayEntry 3 }

currentOdu1dayUAS OBJECT-TYPE
    SYNTAX      Unsigned32
    MAX-ACCESS  read-only
    STATUS      current
    DESCRIPTION
        "ODU Unavailable Seconds" 
    ::=  { currentOdu1dayEntry 4 }

currentOdu1dayElapsedTime OBJECT-TYPE
    SYNTAX      Integer32 (0..86400 | -2147483648)
    MAX-ACCESS  read-only
    STATUS      current
    DESCRIPTION
        "Elapsed 1Day" 
    ::=  { currentOdu1dayEntry 5 }

intervalOdu15minTable OBJECT-TYPE
    SYNTAX      SEQUENCE OF IntervalOdu15minEntry
    MAX-ACCESS  not-accessible
    STATUS      current
    DESCRIPTION   ""
    ::=  { performanceMonitoring 7 }

intervalOdu15minEntry OBJECT-TYPE
    SYNTAX      IntervalOdu15minEntry
    MAX-ACCESS  not-accessible
    STATUS      current
    DESCRIPTION   ""
    INDEX       {
                  entityIndex,
                  intervalOdu15minNumber
                }
    ::=  { intervalOdu15minTable 1 }

IntervalOdu15minEntry ::=  SEQUENCE
  { intervalOdu15minNumber Integer32,
    intervalOdu15minES Unsigned32,
    intervalOdu15minSES Unsigned32,
    intervalOdu15minBbe Counter64String,
    intervalOdu15minUAS Unsigned32,
    intervalOdu15minValidFlag TruthValue,
    intervalOdu15minTimeStamp DateAndTime }

intervalOdu15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalOdu15minEntry 1 }

intervalOdu15minES OBJECT-TYPE
    SYNTAX      Unsigned32
    MAX-ACCESS  read-only
    STATUS      current
    DESCRIPTION
        "ODU Errored Seconds" 
    ::=  { intervalOdu15minEntry 2 }

intervalOdu15minSES OBJECT-TYPE
    SYNTAX      Unsigned32
    MAX-ACCESS  read-only
    STATUS      current
    DESCRIPTION
        "ODU Severely Errored Seconds" 
    ::=  { intervalOdu15minEntry 3 }

intervalOdu15minBbe OBJECT-TYPE
    SYNTAX      Counter64String
    MAX-ACCESS  read-only
    STATUS      current
    DESCRIPTION
        "ODU Background Block Errors" 
    ::=  { intervalOdu15minEntry 4 }

intervalOdu15minUAS OBJECT-TYPE
    SYNTAX      Unsigned32
    MAX-ACCESS  read-only
    STATUS      current
    DESCRIPTION
        "ODU Unavailable Seconds" 
    ::=  { intervalOdu15minEntry 5 }

intervalOdu15minValidFlag OBJECT-TYPE
    SYNTAX      TruthValue
    MAX-ACCESS  read-only
    STATUS      current
    DESCRIPTION
        "Valid Flag" 
    ::=  { intervalOdu15minEntry 6 }

intervalOdu15minTimeStamp OBJECT-TYPE
    SYNTAX      DateAndTime
    MAX-ACCESS  read-only
    STATUS      current
    DESCRIPTION
        "Timestamp" 
    ::=  { intervalOdu15minEntry 7 }

intervalOdu1dayTable OBJECT-TYPE
    SYNTAX      SEQUENCE OF IntervalOdu1dayEntry
    MAX-ACCESS  not-accessible
    STATUS      current
    DESCRIPTION   ""
    ::=  { performanceMonitoring 8 }

intervalOdu1dayEntry OBJECT-TYPE
    SYNTAX      IntervalOdu1dayEntry
    MAX-ACCESS  not-accessible
    STATUS      current
    DESCRIPTION   ""
    INDEX       {
                  entityIndex,
                  intervalOdu1dayNumber
                }
    ::=  { intervalOdu1dayTable 1 }

IntervalOdu1dayEntry ::=  SEQUENCE
  { intervalOdu1dayNumber Integer32,
    intervalOdu1dayES Unsigned32,
    intervalOdu1daySES Unsigned32,
    intervalOdu1dayBbe Counter64String,
    intervalOdu1dayUAS Unsigned32,
    intervalOdu1dayValidFlag TruthValue,
    intervalOdu1dayTimeStamp DateAndTime }

intervalOdu1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalOdu1dayEntry 1 }

intervalOdu1dayES OBJECT-TYPE
    SYNTAX      Unsigned32
    MAX-ACCESS  read-only
    STATUS      current
    DESCRIPTION
        "ODU Errored Seconds" 
    ::=  { intervalOdu1dayEntry 2 }

intervalOdu1daySES OBJECT-TYPE
    SYNTAX      Unsigned32
    MAX-ACCESS  read-only
    STATUS      current
    DESCRIPTION
        "ODU Severely Errored Seconds" 
    ::=  { intervalOdu1dayEntry 3 }

intervalOdu1dayBbe OBJECT-TYPE
    SYNTAX      Counter64String
    MAX-ACCESS  read-only
    STATUS      current
    DESCRIPTION
        "ODU Background Block Errors" 
    ::=  { intervalOdu1dayEntry 4 }

intervalOdu1dayUAS OBJECT-TYPE
    SYNTAX      Unsigned32
    MAX-ACCESS  read-only
    STATUS      current
    DESCRIPTION
        "ODU Unavailable Seconds" 
    ::=  { intervalOdu1dayEntry 5 }

intervalOdu1dayValidFlag OBJECT-TYPE
    SYNTAX      TruthValue
    MAX-ACCESS  read-only
    STATUS      current
    DESCRIPTION
        "Valid Flag" 
    ::=  { intervalOdu1dayEntry 6 }

intervalOdu1dayTimeStamp OBJECT-TYPE
    SYNTAX      DateAndTime
    MAX-ACCESS  read-only
    STATUS      current
    DESCRIPTION
        "Timestamp" 
    ::=  { intervalOdu1dayEntry 7 }

currentOduTcmA15minTable OBJECT-TYPE
    SYNTAX      SEQUENCE OF CurrentOduTcmA15minEntry
    MAX-ACCESS  not-accessible
    STATUS      current
    DESCRIPTION   ""
    ::=  { performanceMonitoring 9 }

currentOduTcmA15minEntry OBJECT-TYPE
    SYNTAX      CurrentOduTcmA15minEntry
    MAX-ACCESS  not-accessible
    STATUS      current
    DESCRIPTION   ""
    INDEX       {
                  entityIndex
                }
    ::=  { currentOduTcmA15minTable 1 }

CurrentOduTcmA15minEntry ::=  SEQUENCE
  { currentOduTcmA15minES Unsigned32,
    currentOduTcmA15minSES Unsigned32,
    currentOduTcmA15minBbe Counter64String,
    currentOduTcmA15minUAS Unsigned32,
    currentOduTcmA15minElapsedTime Integer32 }

currentOduTcmA15minES OBJECT-TYPE
    SYNTAX      Unsigned32
    MAX-ACCESS  read-only
    STATUS      current
    DESCRIPTION
        "ODU Tandem Connection Monitoring A Errored Seconds" 
    ::=  { currentOduTcmA15minEntry 1 }

currentOduTcmA15minSES OBJECT-TYPE
    SYNTAX      Unsigned32
    MAX-ACCESS  read-only
    STATUS      current
    DESCRIPTION
        "ODU Tandem Connection Monitoring A Severely Errored Seconds" 
    ::=  { currentOduTcmA15minEntry 2 }

currentOduTcmA15minBbe OBJECT-TYPE
    SYNTAX      Counter64String
    MAX-ACCESS  read-only
    STATUS      current
    DESCRIPTION
        "ODU Tandem Connection Monitoring A Background Block Errors" 
    ::=  { currentOduTcmA15minEntry 3 }

currentOduTcmA15minUAS OBJECT-TYPE
    SYNTAX      Unsigned32
    MAX-ACCESS  read-only
    STATUS      current
    DESCRIPTION
        "ODU Tandem Connection Monitoring A Unavailable Seconds" 
    ::=  { currentOduTcmA15minEntry 4 }

currentOduTcmA15minElapsedTime OBJECT-TYPE
    SYNTAX      Integer32 (0..9000 | -2147483648)
    MAX-ACCESS  read-only
    STATUS      current
    DESCRIPTION
        "Elapsed 15Min" 
    ::=  { currentOduTcmA15minEntry 5 }

currentOduTcmA1dayTable OBJECT-TYPE
    SYNTAX      SEQUENCE OF CurrentOduTcmA1dayEntry
    MAX-ACCESS  not-accessible
    STATUS      current
    DESCRIPTION   ""
    ::=  { performanceMonitoring 10 }

currentOduTcmA1dayEntry OBJECT-TYPE
    SYNTAX      CurrentOduTcmA1dayEntry
    MAX-ACCESS  not-accessible
    STATUS      current
    DESCRIPTION   ""
    INDEX       {
                  entityIndex
                }
    ::=  { currentOduTcmA1dayTable 1 }

CurrentOduTcmA1dayEntry ::=  SEQUENCE
  { currentOduTcmA1dayES Unsigned32,
    currentOduTcmA1daySES Unsigned32,
    currentOduTcmA1dayBbe Counter64String,
    currentOduTcmA1dayUAS Unsigned32,
    currentOduTcmA1dayElapsedTime Integer32 }

currentOduTcmA1dayES OBJECT-TYPE
    SYNTAX      Unsigned32
    MAX-ACCESS  read-only
    STATUS      current
    DESCRIPTION
        "ODU Tandem Connection Monitoring A Errored Seconds" 
    ::=  { currentOduTcmA1dayEntry 1 }

currentOduTcmA1daySES OBJECT-TYPE
    SYNTAX      Unsigned32
    MAX-ACCESS  read-only
    STATUS      current
    DESCRIPTION
        "ODU Tandem Connection Monitoring A Severely Errored Seconds" 
    ::=  { currentOduTcmA1dayEntry 2 }

currentOduTcmA1dayBbe OBJECT-TYPE
    SYNTAX      Counter64String
    MAX-ACCESS  read-only
    STATUS      current
    DESCRIPTION
        "ODU Tandem Connection Monitoring A Background Block Errors" 
    ::=  { currentOduTcmA1dayEntry 3 }

currentOduTcmA1dayUAS OBJECT-TYPE
    SYNTAX      Unsigned32
    MAX-ACCESS  read-only
    STATUS      current
    DESCRIPTION
        "ODU Tandem Connection Monitoring A Unavailable Seconds" 
    ::=  { currentOduTcmA1dayEntry 4 }

currentOduTcmA1dayElapsedTime OBJECT-TYPE
    SYNTAX      Integer32 (0..86400 | -2147483648)
    MAX-ACCESS  read-only
    STATUS      current
    DESCRIPTION
        "Elapsed 1Day" 
    ::=  { currentOduTcmA1dayEntry 5 }

intervalOduTcmA15minTable OBJECT-TYPE
    SYNTAX      SEQUENCE OF IntervalOduTcmA15minEntry
    MAX-ACCESS  not-accessible
    STATUS      current
    DESCRIPTION   ""
    ::=  { performanceMonitoring 11 }

intervalOduTcmA15minEntry OBJECT-TYPE
    SYNTAX      IntervalOduTcmA15minEntry
    MAX-ACCESS  not-accessible
    STATUS      current
    DESCRIPTION   ""
    INDEX       {
                  entityIndex,
                  intervalOduTcmA15minNumber
                }
    ::=  { intervalOduTcmA15minTable 1 }

IntervalOduTcmA15minEntry ::=  SEQUENCE
  { intervalOduTcmA15minNumber Integer32,
    intervalOduTcmA15minES Unsigned32,
    intervalOduTcmA15minSES Unsigned32,
    intervalOduTcmA15minBbe Counter64String,
    intervalOduTcmA15minUAS Unsigned32,
    intervalOduTcmA15minValidFlag TruthValue,
    intervalOduTcmA15minTimeStamp DateAndTime }

intervalOduTcmA15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalOduTcmA15minEntry 1 }

intervalOduTcmA15minES OBJECT-TYPE
    SYNTAX      Unsigned32
    MAX-ACCESS  read-only
    STATUS      current
    DESCRIPTION
        "ODU Tandem Connection Monitoring A Errored Seconds" 
    ::=  { intervalOduTcmA15minEntry 2 }

intervalOduTcmA15minSES OBJECT-TYPE
    SYNTAX      Unsigned32
    MAX-ACCESS  read-only
    STATUS      current
    DESCRIPTION
        "ODU Tandem Connection Monitoring A Severely Errored Seconds" 
    ::=  { intervalOduTcmA15minEntry 3 }

intervalOduTcmA15minBbe OBJECT-TYPE
    SYNTAX      Counter64String
    MAX-ACCESS  read-only
    STATUS      current
    DESCRIPTION
        "ODU Tandem Connection Monitoring A Background Block Errors" 
    ::=  { intervalOduTcmA15minEntry 4 }

intervalOduTcmA15minUAS OBJECT-TYPE
    SYNTAX      Unsigned32
    MAX-ACCESS  read-only
    STATUS      current
    DESCRIPTION
        "ODU Tandem Connection Monitoring A Unavailable Seconds" 
    ::=  { intervalOduTcmA15minEntry 5 }

intervalOduTcmA15minValidFlag OBJECT-TYPE
    SYNTAX      TruthValue
    MAX-ACCESS  read-only
    STATUS      current
    DESCRIPTION
        "Valid Flag" 
    ::=  { intervalOduTcmA15minEntry 6 }

intervalOduTcmA15minTimeStamp OBJECT-TYPE
    SYNTAX      DateAndTime
    MAX-ACCESS  read-only
    STATUS      current
    DESCRIPTION
        "Timestamp" 
    ::=  { intervalOduTcmA15minEntry 7 }

intervalOduTcmA1dayTable OBJECT-TYPE
    SYNTAX      SEQUENCE OF IntervalOduTcmA1dayEntry
    MAX-ACCESS  not-accessible
    STATUS      current
    DESCRIPTION   ""
    ::=  { performanceMonitoring 12 }

intervalOduTcmA1dayEntry OBJECT-TYPE
    SYNTAX      IntervalOduTcmA1dayEntry
    MAX-ACCESS  not-accessible
    STATUS      current
    DESCRIPTION   ""
    INDEX       {
                  entityIndex,
                  intervalOduTcmA1dayNumber
                }
    ::=  { intervalOduTcmA1dayTable 1 }

IntervalOduTcmA1dayEntry ::=  SEQUENCE
  { intervalOduTcmA1dayNumber Integer32,
    intervalOduTcmA1dayES Unsigned32,
    intervalOduTcmA1daySES Unsigned32,
    intervalOduTcmA1dayBbe Counter64String,
    intervalOduTcmA1dayUAS Unsigned32,
    intervalOduTcmA1dayValidFlag TruthValue,
    intervalOduTcmA1dayTimeStamp DateAndTime }

intervalOduTcmA1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalOduTcmA1dayEntry 1 }

intervalOduTcmA1dayES OBJECT-TYPE
    SYNTAX      Unsigned32
    MAX-ACCESS  read-only
    STATUS      current
    DESCRIPTION
        "ODU Tandem Connection Monitoring A Errored Seconds" 
    ::=  { intervalOduTcmA1dayEntry 2 }

intervalOduTcmA1daySES OBJECT-TYPE
    SYNTAX      Unsigned32
    MAX-ACCESS  read-only
    STATUS      current
    DESCRIPTION
        "ODU Tandem Connection Monitoring A Severely Errored Seconds" 
    ::=  { intervalOduTcmA1dayEntry 3 }

intervalOduTcmA1dayBbe OBJECT-TYPE
    SYNTAX      Counter64String
    MAX-ACCESS  read-only
    STATUS      current
    DESCRIPTION
        "ODU Tandem Connection Monitoring A Background Block Errors" 
    ::=  { intervalOduTcmA1dayEntry 4 }

intervalOduTcmA1dayUAS OBJECT-TYPE
    SYNTAX      Unsigned32
    MAX-ACCESS  read-only
    STATUS      current
    DESCRIPTION
        "ODU Tandem Connection Monitoring A Unavailable Seconds" 
    ::=  { intervalOduTcmA1dayEntry 5 }

intervalOduTcmA1dayValidFlag OBJECT-TYPE
    SYNTAX      TruthValue
    MAX-ACCESS  read-only
    STATUS      current
    DESCRIPTION
        "Valid Flag" 
    ::=  { intervalOduTcmA1dayEntry 6 }

intervalOduTcmA1dayTimeStamp OBJECT-TYPE
    SYNTAX      DateAndTime
    MAX-ACCESS  read-only
    STATUS      current
    DESCRIPTION
        "Timestamp" 
    ::=  { intervalOduTcmA1dayEntry 7 }

currentOduTcmB15minTable OBJECT-TYPE
    SYNTAX      SEQUENCE OF CurrentOduTcmB15minEntry
    MAX-ACCESS  not-accessible
    STATUS      current
    DESCRIPTION   ""
    ::=  { performanceMonitoring 13 }

currentOduTcmB15minEntry OBJECT-TYPE
    SYNTAX      CurrentOduTcmB15minEntry
    MAX-ACCESS  not-accessible
    STATUS      current
    DESCRIPTION   ""
    INDEX       {
                  entityIndex
                }
    ::=  { currentOduTcmB15minTable 1 }

CurrentOduTcmB15minEntry ::=  SEQUENCE
  { currentOduTcmB15minES Unsigned32,
    currentOduTcmB15minSES Unsigned32,
    currentOduTcmB15minBbe Counter64String,
    currentOduTcmB15minUAS Unsigned32,
    currentOduTcmB15minElapsedTime Integer32 }

currentOduTcmB15minES OBJECT-TYPE
    SYNTAX      Unsigned32
    MAX-ACCESS  read-only
    STATUS      current
    DESCRIPTION
        "ODU Tandem Connection Monitoring B Errored Seconds" 
    ::=  { currentOduTcmB15minEntry 1 }

currentOduTcmB15minSES OBJECT-TYPE
    SYNTAX      Unsigned32
    MAX-ACCESS  read-only
    STATUS      current
    DESCRIPTION
        "ODU Tandem Connection Monitoring B Severely Errored Seconds" 
    ::=  { currentOduTcmB15minEntry 2 }

currentOduTcmB15minBbe OBJECT-TYPE
    SYNTAX      Counter64String
    MAX-ACCESS  read-only
    STATUS      current
    DESCRIPTION
        "ODU Tandem Connection Monitoring B Background Block Errors" 
    ::=  { currentOduTcmB15minEntry 3 }

currentOduTcmB15minUAS OBJECT-TYPE
    SYNTAX      Unsigned32
    MAX-ACCESS  read-only
    STATUS      current
    DESCRIPTION
        "ODU Tandem Connection Monitoring B Unavailable Seconds" 
    ::=  { currentOduTcmB15minEntry 4 }

currentOduTcmB15minElapsedTime OBJECT-TYPE
    SYNTAX      Integer32 (0..9000 | -2147483648)
    MAX-ACCESS  read-only
    STATUS      current
    DESCRIPTION
        "Elapsed 15Min" 
    ::=  { currentOduTcmB15minEntry 5 }

currentOduTcmB1dayTable OBJECT-TYPE
    SYNTAX      SEQUENCE OF CurrentOduTcmB1dayEntry
    MAX-ACCESS  not-accessible
    STATUS      current
    DESCRIPTION   ""
    ::=  { performanceMonitoring 14 }

currentOduTcmB1dayEntry OBJECT-TYPE
    SYNTAX      CurrentOduTcmB1dayEntry
    MAX-ACCESS  not-accessible
    STATUS      current
    DESCRIPTION   ""
    INDEX       {
                  entityIndex
                }
    ::=  { currentOduTcmB1dayTable 1 }

CurrentOduTcmB1dayEntry ::=  SEQUENCE
  { currentOduTcmB1dayES Unsigned32,
    currentOduTcmB1daySES Unsigned32,
    currentOduTcmB1dayBbe Counter64String,
    currentOduTcmB1dayUAS Unsigned32,
    currentOduTcmB1dayElapsedTime Integer32 }

currentOduTcmB1dayES OBJECT-TYPE
    SYNTAX      Unsigned32
    MAX-ACCESS  read-only
    STATUS      current
    DESCRIPTION
        "ODU Tandem Connection Monitoring B Errored Seconds" 
    ::=  { currentOduTcmB1dayEntry 1 }

currentOduTcmB1daySES OBJECT-TYPE
    SYNTAX      Unsigned32
    MAX-ACCESS  read-only
    STATUS      current
    DESCRIPTION
        "ODU Tandem Connection Monitoring B Severely Errored Seconds" 
    ::=  { currentOduTcmB1dayEntry 2 }

currentOduTcmB1dayBbe OBJECT-TYPE
    SYNTAX      Counter64String
    MAX-ACCESS  read-only
    STATUS      current
    DESCRIPTION
        "ODU Tandem Connection Monitoring B Background Block Errors" 
    ::=  { currentOduTcmB1dayEntry 3 }

currentOduTcmB1dayUAS OBJECT-TYPE
    SYNTAX      Unsigned32
    MAX-ACCESS  read-only
    STATUS      current
    DESCRIPTION
        "ODU Tandem Connection Monitoring B Unavailable Seconds" 
    ::=  { currentOduTcmB1dayEntry 4 }

currentOduTcmB1dayElapsedTime OBJECT-TYPE
    SYNTAX      Integer32 (0..86400 | -2147483648)
    MAX-ACCESS  read-only
    STATUS      current
    DESCRIPTION
        "Elapsed 1Day" 
    ::=  { currentOduTcmB1dayEntry 5 }

intervalOduTcmB15minTable OBJECT-TYPE
    SYNTAX      SEQUENCE OF IntervalOduTcmB15minEntry
    MAX-ACCESS  not-accessible
    STATUS      current
    DESCRIPTION   ""
    ::=  { performanceMonitoring 15 }

intervalOduTcmB15minEntry OBJECT-TYPE
    SYNTAX      IntervalOduTcmB15minEntry
    MAX-ACCESS  not-accessible
    STATUS      current
    DESCRIPTION   ""
    INDEX       {
                  entityIndex,
                  intervalOduTcmB15minNumber
                }
    ::=  { intervalOduTcmB15minTable 1 }

IntervalOduTcmB15minEntry ::=  SEQUENCE
  { intervalOduTcmB15minNumber Integer32,
    intervalOduTcmB15minES Unsigned32,
    intervalOduTcmB15minSES Unsigned32,
    intervalOduTcmB15minBbe Counter64String,
    intervalOduTcmB15minUAS Unsigned32,
    intervalOduTcmB15minValidFlag TruthValue,
    intervalOduTcmB15minTimeStamp DateAndTime }

intervalOduTcmB15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalOduTcmB15minEntry 1 }

intervalOduTcmB15minES OBJECT-TYPE
    SYNTAX      Unsigned32
    MAX-ACCESS  read-only
    STATUS      current
    DESCRIPTION
        "ODU Tandem Connection Monitoring B Errored Seconds" 
    ::=  { intervalOduTcmB15minEntry 2 }

intervalOduTcmB15minSES OBJECT-TYPE
    SYNTAX      Unsigned32
    MAX-ACCESS  read-only
    STATUS      current
    DESCRIPTION
        "ODU Tandem Connection Monitoring B Severely Errored Seconds" 
    ::=  { intervalOduTcmB15minEntry 3 }

intervalOduTcmB15minBbe OBJECT-TYPE
    SYNTAX      Counter64String
    MAX-ACCESS  read-only
    STATUS      current
    DESCRIPTION
        "ODU Tandem Connection Monitoring B Background Block Errors" 
    ::=  { intervalOduTcmB15minEntry 4 }

intervalOduTcmB15minUAS OBJECT-TYPE
    SYNTAX      Unsigned32
    MAX-ACCESS  read-only
    STATUS      current
    DESCRIPTION
        "ODU Tandem Connection Monitoring B Unavailable Seconds" 
    ::=  { intervalOduTcmB15minEntry 5 }

intervalOduTcmB15minValidFlag OBJECT-TYPE
    SYNTAX      TruthValue
    MAX-ACCESS  read-only
    STATUS      current
    DESCRIPTION
        "Valid Flag" 
    ::=  { intervalOduTcmB15minEntry 6 }

intervalOduTcmB15minTimeStamp OBJECT-TYPE
    SYNTAX      DateAndTime
    MAX-ACCESS  read-only
    STATUS      current
    DESCRIPTION
        "Timestamp" 
    ::=  { intervalOduTcmB15minEntry 7 }

intervalOduTcmB1dayTable OBJECT-TYPE
    SYNTAX      SEQUENCE OF IntervalOduTcmB1dayEntry
    MAX-ACCESS  not-accessible
    STATUS      current
    DESCRIPTION   ""
    ::=  { performanceMonitoring 16 }

intervalOduTcmB1dayEntry OBJECT-TYPE
    SYNTAX      IntervalOduTcmB1dayEntry
    MAX-ACCESS  not-accessible
    STATUS      current
    DESCRIPTION   ""
    INDEX       {
                  entityIndex,
                  intervalOduTcmB1dayNumber
                }
    ::=  { intervalOduTcmB1dayTable 1 }

IntervalOduTcmB1dayEntry ::=  SEQUENCE
  { intervalOduTcmB1dayNumber Integer32,
    intervalOduTcmB1dayES Unsigned32,
    intervalOduTcmB1daySES Unsigned32,
    intervalOduTcmB1dayBbe Counter64String,
    intervalOduTcmB1dayUAS Unsigned32,
    intervalOduTcmB1dayValidFlag TruthValue,
    intervalOduTcmB1dayTimeStamp DateAndTime }

intervalOduTcmB1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalOduTcmB1dayEntry 1 }

intervalOduTcmB1dayES OBJECT-TYPE
    SYNTAX      Unsigned32
    MAX-ACCESS  read-only
    STATUS      current
    DESCRIPTION
        "ODU Tandem Connection Monitoring B Errored Seconds" 
    ::=  { intervalOduTcmB1dayEntry 2 }

intervalOduTcmB1daySES OBJECT-TYPE
    SYNTAX      Unsigned32
    MAX-ACCESS  read-only
    STATUS      current
    DESCRIPTION
        "ODU Tandem Connection Monitoring B Severely Errored Seconds" 
    ::=  { intervalOduTcmB1dayEntry 3 }

intervalOduTcmB1dayBbe OBJECT-TYPE
    SYNTAX      Counter64String
    MAX-ACCESS  read-only
    STATUS      current
    DESCRIPTION
        "ODU Tandem Connection Monitoring B Background Block Errors" 
    ::=  { intervalOduTcmB1dayEntry 4 }

intervalOduTcmB1dayUAS OBJECT-TYPE
    SYNTAX      Unsigned32
    MAX-ACCESS  read-only
    STATUS      current
    DESCRIPTION
        "ODU Tandem Connection Monitoring B Unavailable Seconds" 
    ::=  { intervalOduTcmB1dayEntry 5 }

intervalOduTcmB1dayValidFlag OBJECT-TYPE
    SYNTAX      TruthValue
    MAX-ACCESS  read-only
    STATUS      current
    DESCRIPTION
        "Valid Flag" 
    ::=  { intervalOduTcmB1dayEntry 6 }

intervalOduTcmB1dayTimeStamp OBJECT-TYPE
    SYNTAX      DateAndTime
    MAX-ACCESS  read-only
    STATUS      current
    DESCRIPTION
        "Timestamp" 
    ::=  { intervalOduTcmB1dayEntry 7 }

currentSonetSect15minTable OBJECT-TYPE
    SYNTAX      SEQUENCE OF CurrentSonetSect15minEntry
    MAX-ACCESS  not-accessible
    STATUS      current
    DESCRIPTION   ""
    ::=  { performanceMonitoring 17 }

currentSonetSect15minEntry OBJECT-TYPE
    SYNTAX      CurrentSonetSect15minEntry
    MAX-ACCESS  not-accessible
    STATUS      current
    DESCRIPTION   ""
    INDEX       {
                  entityIndex
                }
    ::=  { currentSonetSect15minTable 1 }

CurrentSonetSect15minEntry ::=  SEQUENCE
  { currentSonetSect15minES Unsigned32,
    currentSonetSect15minSES Unsigned32,
    currentSonetSect15minSEFS Unsigned32,
    currentSonetSect15minCV Counter64String,
    currentSonetSect15minElapsedTime Integer32 }

currentSonetSect15minES OBJECT-TYPE
    SYNTAX      Unsigned32
    MAX-ACCESS  read-only
    STATUS      current
    DESCRIPTION
        "Section / Regenerator Section Errored Seconds" 
    ::=  { currentSonetSect15minEntry 1 }

currentSonetSect15minSES OBJECT-TYPE
    SYNTAX      Unsigned32
    MAX-ACCESS  read-only
    STATUS      current
    DESCRIPTION
        "Section Severely Errored Seconds" 
    ::=  { currentSonetSect15minEntry 2 }

currentSonetSect15minSEFS OBJECT-TYPE
    SYNTAX      Unsigned32
    MAX-ACCESS  read-only
    STATUS      current
    DESCRIPTION
        "Section Severely Errored Frame Seconds" 
    ::=  { currentSonetSect15minEntry 3 }

currentSonetSect15minCV OBJECT-TYPE
    SYNTAX      Counter64String
    MAX-ACCESS  read-only
    STATUS      current
    DESCRIPTION
        "Section / Regenator Section Coding Violations" 
    ::=  { currentSonetSect15minEntry 4 }

currentSonetSect15minElapsedTime OBJECT-TYPE
    SYNTAX      Integer32 (0..9000 | -2147483648)
    MAX-ACCESS  read-only
    STATUS      current
    DESCRIPTION
        "Elapsed 15Min" 
    ::=  { currentSonetSect15minEntry 5 }

currentSonetSect1dayTable OBJECT-TYPE
    SYNTAX      SEQUENCE OF CurrentSonetSect1dayEntry
    MAX-ACCESS  not-accessible
    STATUS      current
    DESCRIPTION   ""
    ::=  { performanceMonitoring 18 }

currentSonetSect1dayEntry OBJECT-TYPE
    SYNTAX      CurrentSonetSect1dayEntry
    MAX-ACCESS  not-accessible
    STATUS      current
    DESCRIPTION   ""
    INDEX       {
                  entityIndex
                }
    ::=  { currentSonetSect1dayTable 1 }

CurrentSonetSect1dayEntry ::=  SEQUENCE
  { currentSonetSect1dayES Unsigned32,
    currentSonetSect1daySES Unsigned32,
    currentSonetSect1daySEFS Unsigned32,
    currentSonetSect1dayCV Counter64String,
    currentSonetSect1dayElapsedTime Integer32 }

currentSonetSect1dayES OBJECT-TYPE
    SYNTAX      Unsigned32
    MAX-ACCESS  read-only
    STATUS      current
    DESCRIPTION
        "Section / Regenerator Section Errored Seconds" 
    ::=  { currentSonetSect1dayEntry 1 }

currentSonetSect1daySES OBJECT-TYPE
    SYNTAX      Unsigned32
    MAX-ACCESS  read-only
    STATUS      current
    DESCRIPTION
        "Section Severely Errored Seconds" 
    ::=  { currentSonetSect1dayEntry 2 }

currentSonetSect1daySEFS OBJECT-TYPE
    SYNTAX      Unsigned32
    MAX-ACCESS  read-only
    STATUS      current
    DESCRIPTION
        "Section Severely Errored Frame Seconds" 
    ::=  { currentSonetSect1dayEntry 3 }

currentSonetSect1dayCV OBJECT-TYPE
    SYNTAX      Counter64String
    MAX-ACCESS  read-only
    STATUS      current
    DESCRIPTION
        "Section / Regenator Section Coding Violations" 
    ::=  { currentSonetSect1dayEntry 4 }

currentSonetSect1dayElapsedTime OBJECT-TYPE
    SYNTAX      Integer32 (0..86400 | -2147483648)
    MAX-ACCESS  read-only
    STATUS      current
    DESCRIPTION
        "Elapsed 1Day" 
    ::=  { currentSonetSect1dayEntry 5 }

intervalSonetSect15minTable OBJECT-TYPE
    SYNTAX      SEQUENCE OF IntervalSonetSect15minEntry
    MAX-ACCESS  not-accessible
    STATUS      current
    DESCRIPTION   ""
    ::=  { performanceMonitoring 19 }

intervalSonetSect15minEntry OBJECT-TYPE
    SYNTAX      IntervalSonetSect15minEntry
    MAX-ACCESS  not-accessible
    STATUS      current
    DESCRIPTION   ""
    INDEX       {
                  entityIndex,
                  intervalSonetSect15minNumber
                }
    ::=  { intervalSonetSect15minTable 1 }

IntervalSonetSect15minEntry ::=  SEQUENCE
  { intervalSonetSect15minNumber Integer32,
    intervalSonetSect15minES Unsigned32,
    intervalSonetSect15minSES Unsigned32,
    intervalSonetSect15minSEFS Unsigned32,
    intervalSonetSect15minCV Counter64String,
    intervalSonetSect15minValidFlag TruthValue,
    intervalSonetSect15minTimeStamp DateAndTime }

intervalSonetSect15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalSonetSect15minEntry 1 }

intervalSonetSect15minES OBJECT-TYPE
    SYNTAX      Unsigned32
    MAX-ACCESS  read-only
    STATUS      current
    DESCRIPTION
        "Section / Regenerator Section Errored Seconds" 
    ::=  { intervalSonetSect15minEntry 2 }

intervalSonetSect15minSES OBJECT-TYPE
    SYNTAX      Unsigned32
    MAX-ACCESS  read-only
    STATUS      current
    DESCRIPTION
        "Section Severely Errored Seconds" 
    ::=  { intervalSonetSect15minEntry 3 }

intervalSonetSect15minSEFS OBJECT-TYPE
    SYNTAX      Unsigned32
    MAX-ACCESS  read-only
    STATUS      current
    DESCRIPTION
        "Section Severely Errored Frame Seconds" 
    ::=  { intervalSonetSect15minEntry 4 }

intervalSonetSect15minCV OBJECT-TYPE
    SYNTAX      Counter64String
    MAX-ACCESS  read-only
    STATUS      current
    DESCRIPTION
        "Section / Regenator Section Coding Violations" 
    ::=  { intervalSonetSect15minEntry 5 }

intervalSonetSect15minValidFlag OBJECT-TYPE
    SYNTAX      TruthValue
    MAX-ACCESS  read-only
    STATUS      current
    DESCRIPTION
        "Valid Flag" 
    ::=  { intervalSonetSect15minEntry 6 }

intervalSonetSect15minTimeStamp OBJECT-TYPE
    SYNTAX      DateAndTime
    MAX-ACCESS  read-only
    STATUS      current
    DESCRIPTION
        "Timestamp" 
    ::=  { intervalSonetSect15minEntry 7 }

intervalSonetSect1dayTable OBJECT-TYPE
    SYNTAX      SEQUENCE OF IntervalSonetSect1dayEntry
    MAX-ACCESS  not-accessible
    STATUS      current
    DESCRIPTION   ""
    ::=  { performanceMonitoring 20 }

intervalSonetSect1dayEntry OBJECT-TYPE
    SYNTAX      IntervalSonetSect1dayEntry
    MAX-ACCESS  not-accessible
    STATUS      current
    DESCRIPTION   ""
    INDEX       {
                  entityIndex,
                  intervalSonetSect1dayNumber
                }
    ::=  { intervalSonetSect1dayTable 1 }

IntervalSonetSect1dayEntry ::=  SEQUENCE
  { intervalSonetSect1dayNumber Integer32,
    intervalSonetSect1dayES Unsigned32,
    intervalSonetSect1daySES Unsigned32,
    intervalSonetSect1daySEFS Unsigned32,
    intervalSonetSect1dayCV Counter64String,
    intervalSonetSect1dayValidFlag TruthValue,
    intervalSonetSect1dayTimeStamp DateAndTime }

intervalSonetSect1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalSonetSect1dayEntry 1 }

intervalSonetSect1dayES OBJECT-TYPE
    SYNTAX      Unsigned32
    MAX-ACCESS  read-only
    STATUS      current
    DESCRIPTION
        "Section / Regenerator Section Errored Seconds" 
    ::=  { intervalSonetSect1dayEntry 2 }

intervalSonetSect1daySES OBJECT-TYPE
    SYNTAX      Unsigned32
    MAX-ACCESS  read-only
    STATUS      current
    DESCRIPTION
        "Section Severely Errored Seconds" 
    ::=  { intervalSonetSect1dayEntry 3 }

intervalSonetSect1daySEFS OBJECT-TYPE
    SYNTAX      Unsigned32
    MAX-ACCESS  read-only
    STATUS      current
    DESCRIPTION
        "Section Severely Errored Frame Seconds" 
    ::=  { intervalSonetSect1dayEntry 4 }

intervalSonetSect1dayCV OBJECT-TYPE
    SYNTAX      Counter64String
    MAX-ACCESS  read-only
    STATUS      current
    DESCRIPTION
        "Section / Regenator Section Coding Violations" 
    ::=  { intervalSonetSect1dayEntry 5 }

intervalSonetSect1dayValidFlag OBJECT-TYPE
    SYNTAX      TruthValue
    MAX-ACCESS  read-only
    STATUS      current
    DESCRIPTION
        "Valid Flag" 
    ::=  { intervalSonetSect1dayEntry 6 }

intervalSonetSect1dayTimeStamp OBJECT-TYPE
    SYNTAX      DateAndTime
    MAX-ACCESS  read-only
    STATUS      current
    DESCRIPTION
        "Timestamp" 
    ::=  { intervalSonetSect1dayEntry 7 }

currentSonetLine15minTable OBJECT-TYPE
    SYNTAX      SEQUENCE OF CurrentSonetLine15minEntry
    MAX-ACCESS  not-accessible
    STATUS      current
    DESCRIPTION   ""
    ::=  { performanceMonitoring 21 }

currentSonetLine15minEntry OBJECT-TYPE
    SYNTAX      CurrentSonetLine15minEntry
    MAX-ACCESS  not-accessible
    STATUS      current
    DESCRIPTION   ""
    INDEX       {
                  entityIndex
                }
    ::=  { currentSonetLine15minTable 1 }

CurrentSonetLine15minEntry ::=  SEQUENCE
  { currentSonetLine15minES Unsigned32,
    currentSonetLine15minSES Unsigned32,
    currentSonetLine15minUAS Unsigned32,
    currentSonetLine15minCV Counter64String,
    currentSonetLine15minElapsedTime Integer32 }

currentSonetLine15minES OBJECT-TYPE
    SYNTAX      Unsigned32
    MAX-ACCESS  read-only
    STATUS      current
    DESCRIPTION
        "Line / Multiplex Section Errored Second" 
    ::=  { currentSonetLine15minEntry 1 }

currentSonetLine15minSES OBJECT-TYPE
    SYNTAX      Unsigned32
    MAX-ACCESS  read-only
    STATUS      current
    DESCRIPTION
        "Line / Multiplex Section Severely Errored Seconds" 
    ::=  { currentSonetLine15minEntry 2 }

currentSonetLine15minUAS OBJECT-TYPE
    SYNTAX      Unsigned32
    MAX-ACCESS  read-only
    STATUS      current
    DESCRIPTION
        "Line / Multiplex Section Unavailable Seconds" 
    ::=  { currentSonetLine15minEntry 3 }

currentSonetLine15minCV OBJECT-TYPE
    SYNTAX      Counter64String
    MAX-ACCESS  read-only
    STATUS      current
    DESCRIPTION
        "Line / Multiplex Section Coding Violations" 
    ::=  { currentSonetLine15minEntry 4 }

currentSonetLine15minElapsedTime OBJECT-TYPE
    SYNTAX      Integer32 (0..9000 | -2147483648)
    MAX-ACCESS  read-only
    STATUS      current
    DESCRIPTION
        "Elapsed 15Min" 
    ::=  { currentSonetLine15minEntry 5 }

currentSonetLine1dayTable OBJECT-TYPE
    SYNTAX      SEQUENCE OF CurrentSonetLine1dayEntry
    MAX-ACCESS  not-accessible
    STATUS      current
    DESCRIPTION   ""
    ::=  { performanceMonitoring 22 }

currentSonetLine1dayEntry OBJECT-TYPE
    SYNTAX      CurrentSonetLine1dayEntry
    MAX-ACCESS  not-accessible
    STATUS      current
    DESCRIPTION   ""
    INDEX       {
                  entityIndex
                }
    ::=  { currentSonetLine1dayTable 1 }

CurrentSonetLine1dayEntry ::=  SEQUENCE
  { currentSonetLine1dayES Unsigned32,
    currentSonetLine1daySES Unsigned32,
    currentSonetLine1dayUAS Unsigned32,
    currentSonetLine1dayCV Counter64String,
    currentSonetLine1dayElapsedTime Integer32 }

currentSonetLine1dayES OBJECT-TYPE
    SYNTAX      Unsigned32
    MAX-ACCESS  read-only
    STATUS      current
    DESCRIPTION
        "Line / Multiplex Section Errored Second" 
    ::=  { currentSonetLine1dayEntry 1 }

currentSonetLine1daySES OBJECT-TYPE
    SYNTAX      Unsigned32
    MAX-ACCESS  read-only
    STATUS      current
    DESCRIPTION
        "Line / Multiplex Section Severely Errored Seconds" 
    ::=  { currentSonetLine1dayEntry 2 }

currentSonetLine1dayUAS OBJECT-TYPE
    SYNTAX      Unsigned32
    MAX-ACCESS  read-only
    STATUS      current
    DESCRIPTION
        "Line / Multiplex Section Unavailable Seconds" 
    ::=  { currentSonetLine1dayEntry 3 }

currentSonetLine1dayCV OBJECT-TYPE
    SYNTAX      Counter64String
    MAX-ACCESS  read-only
    STATUS      current
    DESCRIPTION
        "Line / Multiplex Section Coding Violations" 
    ::=  { currentSonetLine1dayEntry 4 }

currentSonetLine1dayElapsedTime OBJECT-TYPE
    SYNTAX      Integer32 (0..86400 | -2147483648)
    MAX-ACCESS  read-only
    STATUS      current
    DESCRIPTION
        "Elapsed 1Day" 
    ::=  { currentSonetLine1dayEntry 5 }

intervalSonetLine15minTable OBJECT-TYPE
    SYNTAX      SEQUENCE OF IntervalSonetLine15minEntry
    MAX-ACCESS  not-accessible
    STATUS      current
    DESCRIPTION   ""
    ::=  { performanceMonitoring 23 }

intervalSonetLine15minEntry OBJECT-TYPE
    SYNTAX      IntervalSonetLine15minEntry
    MAX-ACCESS  not-accessible
    STATUS      current
    DESCRIPTION   ""
    INDEX       {
                  entityIndex,
                  intervalSonetLine15minNumber
                }
    ::=  { intervalSonetLine15minTable 1 }

IntervalSonetLine15minEntry ::=  SEQUENCE
  { intervalSonetLine15minNumber Integer32,
    intervalSonetLine15minES Unsigned32,
    intervalSonetLine15minSES Unsigned32,
    intervalSonetLine15minUAS Unsigned32,
    intervalSonetLine15minCV Counter64String,
    intervalSonetLine15minValidFlag TruthValue,
    intervalSonetLine15minTimeStamp DateAndTime }

intervalSonetLine15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalSonetLine15minEntry 1 }

intervalSonetLine15minES OBJECT-TYPE
    SYNTAX      Unsigned32
    MAX-ACCESS  read-only
    STATUS      current
    DESCRIPTION
        "Line / Multiplex Section Errored Second" 
    ::=  { intervalSonetLine15minEntry 2 }

intervalSonetLine15minSES OBJECT-TYPE
    SYNTAX      Unsigned32
    MAX-ACCESS  read-only
    STATUS      current
    DESCRIPTION
        "Line / Multiplex Section Severely Errored Seconds" 
    ::=  { intervalSonetLine15minEntry 3 }

intervalSonetLine15minUAS OBJECT-TYPE
    SYNTAX      Unsigned32
    MAX-ACCESS  read-only
    STATUS      current
    DESCRIPTION
        "Line / Multiplex Section Unavailable Seconds" 
    ::=  { intervalSonetLine15minEntry 4 }

intervalSonetLine15minCV OBJECT-TYPE
    SYNTAX      Counter64String
    MAX-ACCESS  read-only
    STATUS      current
    DESCRIPTION
        "Line / Multiplex Section Coding Violations" 
    ::=  { intervalSonetLine15minEntry 5 }

intervalSonetLine15minValidFlag OBJECT-TYPE
    SYNTAX      TruthValue
    MAX-ACCESS  read-only
    STATUS      current
    DESCRIPTION
        "Valid Flag" 
    ::=  { intervalSonetLine15minEntry 6 }

intervalSonetLine15minTimeStamp OBJECT-TYPE
    SYNTAX      DateAndTime
    MAX-ACCESS  read-only
    STATUS      current
    DESCRIPTION
        "Timestamp" 
    ::=  { intervalSonetLine15minEntry 7 }

intervalSonetLine1dayTable OBJECT-TYPE
    SYNTAX      SEQUENCE OF IntervalSonetLine1dayEntry
    MAX-ACCESS  not-accessible
    STATUS      current
    DESCRIPTION   ""
    ::=  { performanceMonitoring 24 }

intervalSonetLine1dayEntry OBJECT-TYPE
    SYNTAX      IntervalSonetLine1dayEntry
    MAX-ACCESS  not-accessible
    STATUS      current
    DESCRIPTION   ""
    INDEX       {
                  entityIndex,
                  intervalSonetLine1dayNumber
                }
    ::=  { intervalSonetLine1dayTable 1 }

IntervalSonetLine1dayEntry ::=  SEQUENCE
  { intervalSonetLine1dayNumber Integer32,
    intervalSonetLine1dayES Unsigned32,
    intervalSonetLine1daySES Unsigned32,
    intervalSonetLine1dayUAS Unsigned32,
    intervalSonetLine1dayCV Counter64String,
    intervalSonetLine1dayValidFlag TruthValue,
    intervalSonetLine1dayTimeStamp DateAndTime }

intervalSonetLine1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalSonetLine1dayEntry 1 }

intervalSonetLine1dayES OBJECT-TYPE
    SYNTAX      Unsigned32
    MAX-ACCESS  read-only
    STATUS      current
    DESCRIPTION
        "Line / Multiplex Section Errored Second" 
    ::=  { intervalSonetLine1dayEntry 2 }

intervalSonetLine1daySES OBJECT-TYPE
    SYNTAX      Unsigned32
    MAX-ACCESS  read-only
    STATUS      current
    DESCRIPTION
        "Line / Multiplex Section Severely Errored Seconds" 
    ::=  { intervalSonetLine1dayEntry 3 }

intervalSonetLine1dayUAS OBJECT-TYPE
    SYNTAX      Unsigned32
    MAX-ACCESS  read-only
    STATUS      current
    DESCRIPTION
        "Line / Multiplex Section Unavailable Seconds" 
    ::=  { intervalSonetLine1dayEntry 4 }

intervalSonetLine1dayCV OBJECT-TYPE
    SYNTAX      Counter64String
    MAX-ACCESS  read-only
    STATUS      current
    DESCRIPTION
        "Line / Multiplex Section Coding Violations" 
    ::=  { intervalSonetLine1dayEntry 5 }

intervalSonetLine1dayValidFlag OBJECT-TYPE
    SYNTAX      TruthValue
    MAX-ACCESS  read-only
    STATUS      current
    DESCRIPTION
        "Valid Flag" 
    ::=  { intervalSonetLine1dayEntry 6 }

intervalSonetLine1dayTimeStamp OBJECT-TYPE
    SYNTAX      DateAndTime
    MAX-ACCESS  read-only
    STATUS      current
    DESCRIPTION
        "Timestamp" 
    ::=  { intervalSonetLine1dayEntry 7 }

currentSonetHoPath15minTable OBJECT-TYPE
    SYNTAX      SEQUENCE OF CurrentSonetHoPath15minEntry
    MAX-ACCESS  not-accessible
    STATUS      current
    DESCRIPTION   ""
    ::=  { performanceMonitoring 25 }

currentSonetHoPath15minEntry OBJECT-TYPE
    SYNTAX      CurrentSonetHoPath15minEntry
    MAX-ACCESS  not-accessible
    STATUS      current
    DESCRIPTION   ""
    INDEX       {
                  entityIndex
                }
    ::=  { currentSonetHoPath15minTable 1 }

CurrentSonetHoPath15minEntry ::=  SEQUENCE
  { currentSonetHoPath15minES Unsigned32,
    currentSonetHoPath15minSES Unsigned32,
    currentSonetHoPath15minUAS Unsigned32,
    currentSonetHoPath15minCV Counter64String,
    currentSonetHoPath15minElapsedTime Integer32 }

currentSonetHoPath15minES OBJECT-TYPE
    SYNTAX      Unsigned32
    MAX-ACCESS  read-only
    STATUS      current
    DESCRIPTION
        "Path Errored Seconds" 
    ::=  { currentSonetHoPath15minEntry 1 }

currentSonetHoPath15minSES OBJECT-TYPE
    SYNTAX      Unsigned32
    MAX-ACCESS  read-only
    STATUS      current
    DESCRIPTION
        "Path Severely Errored Seconds" 
    ::=  { currentSonetHoPath15minEntry 2 }

currentSonetHoPath15minUAS OBJECT-TYPE
    SYNTAX      Unsigned32
    MAX-ACCESS  read-only
    STATUS      current
    DESCRIPTION
        "Path Unavailable Seconds" 
    ::=  { currentSonetHoPath15minEntry 3 }

currentSonetHoPath15minCV OBJECT-TYPE
    SYNTAX      Counter64String
    MAX-ACCESS  read-only
    STATUS      current
    DESCRIPTION
        "Path Coding Violations" 
    ::=  { currentSonetHoPath15minEntry 4 }

currentSonetHoPath15minElapsedTime OBJECT-TYPE
    SYNTAX      Integer32 (0..9000 | -2147483648)
    MAX-ACCESS  read-only
    STATUS      current
    DESCRIPTION
        "Elapsed 15Min" 
    ::=  { currentSonetHoPath15minEntry 5 }

currentSonetHoPath1dayTable OBJECT-TYPE
    SYNTAX      SEQUENCE OF CurrentSonetHoPath1dayEntry
    MAX-ACCESS  not-accessible
    STATUS      current
    DESCRIPTION   ""
    ::=  { performanceMonitoring 26 }

currentSonetHoPath1dayEntry OBJECT-TYPE
    SYNTAX      CurrentSonetHoPath1dayEntry
    MAX-ACCESS  not-accessible
    STATUS      current
    DESCRIPTION   ""
    INDEX       {
                  entityIndex
                }
    ::=  { currentSonetHoPath1dayTable 1 }

CurrentSonetHoPath1dayEntry ::=  SEQUENCE
  { currentSonetHoPath1dayES Unsigned32,
    currentSonetHoPath1daySES Unsigned32,
    currentSonetHoPath1dayUAS Unsigned32,
    currentSonetHoPath1dayCV Counter64String,
    currentSonetHoPath1dayElapsedTime Integer32 }

currentSonetHoPath1dayES OBJECT-TYPE
    SYNTAX      Unsigned32
    MAX-ACCESS  read-only
    STATUS      current
    DESCRIPTION
        "Path Errored Seconds" 
    ::=  { currentSonetHoPath1dayEntry 1 }

currentSonetHoPath1daySES OBJECT-TYPE
    SYNTAX      Unsigned32
    MAX-ACCESS  read-only
    STATUS      current
    DESCRIPTION
        "Path Severely Errored Seconds" 
    ::=  { currentSonetHoPath1dayEntry 2 }

currentSonetHoPath1dayUAS OBJECT-TYPE
    SYNTAX      Unsigned32
    MAX-ACCESS  read-only
    STATUS      current
    DESCRIPTION
        "Path Unavailable Seconds" 
    ::=  { currentSonetHoPath1dayEntry 3 }

currentSonetHoPath1dayCV OBJECT-TYPE
    SYNTAX      Counter64String
    MAX-ACCESS  read-only
    STATUS      current
    DESCRIPTION
        "Path Coding Violations" 
    ::=  { currentSonetHoPath1dayEntry 4 }

currentSonetHoPath1dayElapsedTime OBJECT-TYPE
    SYNTAX      Integer32 (0..86400 | -2147483648)
    MAX-ACCESS  read-only
    STATUS      current
    DESCRIPTION
        "Elapsed 1Day" 
    ::=  { currentSonetHoPath1dayEntry 5 }

intervalSonetHoPath15minTable OBJECT-TYPE
    SYNTAX      SEQUENCE OF IntervalSonetHoPath15minEntry
    MAX-ACCESS  not-accessible
    STATUS      current
    DESCRIPTION   ""
    ::=  { performanceMonitoring 27 }

intervalSonetHoPath15minEntry OBJECT-TYPE
    SYNTAX      IntervalSonetHoPath15minEntry
    MAX-ACCESS  not-accessible
    STATUS      current
    DESCRIPTION   ""
    INDEX       {
                  entityIndex,
                  intervalSonetHoPath15minNumber
                }
    ::=  { intervalSonetHoPath15minTable 1 }

IntervalSonetHoPath15minEntry ::=  SEQUENCE
  { intervalSonetHoPath15minNumber Integer32,
    intervalSonetHoPath15minES Unsigned32,
    intervalSonetHoPath15minSES Unsigned32,
    intervalSonetHoPath15minUAS Unsigned32,
    intervalSonetHoPath15minCV Counter64String,
    intervalSonetHoPath15minValidFlag TruthValue,
    intervalSonetHoPath15minTimeStamp DateAndTime }

intervalSonetHoPath15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalSonetHoPath15minEntry 1 }

intervalSonetHoPath15minES OBJECT-TYPE
    SYNTAX      Unsigned32
    MAX-ACCESS  read-only
    STATUS      current
    DESCRIPTION
        "Path Errored Seconds" 
    ::=  { intervalSonetHoPath15minEntry 2 }

intervalSonetHoPath15minSES OBJECT-TYPE
    SYNTAX      Unsigned32
    MAX-ACCESS  read-only
    STATUS      current
    DESCRIPTION
        "Path Severely Errored Seconds" 
    ::=  { intervalSonetHoPath15minEntry 3 }

intervalSonetHoPath15minUAS OBJECT-TYPE
    SYNTAX      Unsigned32
    MAX-ACCESS  read-only
    STATUS      current
    DESCRIPTION
        "Path Unavailable Seconds" 
    ::=  { intervalSonetHoPath15minEntry 4 }

intervalSonetHoPath15minCV OBJECT-TYPE
    SYNTAX      Counter64String
    MAX-ACCESS  read-only
    STATUS      current
    DESCRIPTION
        "Path Coding Violations" 
    ::=  { intervalSonetHoPath15minEntry 5 }

intervalSonetHoPath15minValidFlag OBJECT-TYPE
    SYNTAX      TruthValue
    MAX-ACCESS  read-only
    STATUS      current
    DESCRIPTION
        "Valid Flag" 
    ::=  { intervalSonetHoPath15minEntry 6 }

intervalSonetHoPath15minTimeStamp OBJECT-TYPE
    SYNTAX      DateAndTime
    MAX-ACCESS  read-only
    STATUS      current
    DESCRIPTION
        "Timestamp" 
    ::=  { intervalSonetHoPath15minEntry 7 }

intervalSonetHoPath1dayTable OBJECT-TYPE
    SYNTAX      SEQUENCE OF IntervalSonetHoPath1dayEntry
    MAX-ACCESS  not-accessible
    STATUS      current
    DESCRIPTION   ""
    ::=  { performanceMonitoring 28 }

intervalSonetHoPath1dayEntry OBJECT-TYPE
    SYNTAX      IntervalSonetHoPath1dayEntry
    MAX-ACCESS  not-accessible
    STATUS      current
    DESCRIPTION   ""
    INDEX       {
                  entityIndex,
                  intervalSonetHoPath1dayNumber
                }
    ::=  { intervalSonetHoPath1dayTable 1 }

IntervalSonetHoPath1dayEntry ::=  SEQUENCE
  { intervalSonetHoPath1dayNumber Integer32,
    intervalSonetHoPath1dayES Unsigned32,
    intervalSonetHoPath1daySES Unsigned32,
    intervalSonetHoPath1dayUAS Unsigned32,
    intervalSonetHoPath1dayCV Counter64String,
    intervalSonetHoPath1dayValidFlag TruthValue,
    intervalSonetHoPath1dayTimeStamp DateAndTime }

intervalSonetHoPath1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalSonetHoPath1dayEntry 1 }

intervalSonetHoPath1dayES OBJECT-TYPE
    SYNTAX      Unsigned32
    MAX-ACCESS  read-only
    STATUS      current
    DESCRIPTION
        "Path Errored Seconds" 
    ::=  { intervalSonetHoPath1dayEntry 2 }

intervalSonetHoPath1daySES OBJECT-TYPE
    SYNTAX      Unsigned32
    MAX-ACCESS  read-only
    STATUS      current
    DESCRIPTION
        "Path Severely Errored Seconds" 
    ::=  { intervalSonetHoPath1dayEntry 3 }

intervalSonetHoPath1dayUAS OBJECT-TYPE
    SYNTAX      Unsigned32
    MAX-ACCESS  read-only
    STATUS      current
    DESCRIPTION
        "Path Unavailable Seconds" 
    ::=  { intervalSonetHoPath1dayEntry 4 }

intervalSonetHoPath1dayCV OBJECT-TYPE
    SYNTAX      Counter64String
    MAX-ACCESS  read-only
    STATUS      current
    DESCRIPTION
        "Path Coding Violations" 
    ::=  { intervalSonetHoPath1dayEntry 5 }

intervalSonetHoPath1dayValidFlag OBJECT-TYPE
    SYNTAX      TruthValue
    MAX-ACCESS  read-only
    STATUS      current
    DESCRIPTION
        "Valid Flag" 
    ::=  { intervalSonetHoPath1dayEntry 6 }

intervalSonetHoPath1dayTimeStamp OBJECT-TYPE
    SYNTAX      DateAndTime
    MAX-ACCESS  read-only
    STATUS      current
    DESCRIPTION
        "Timestamp" 
    ::=  { intervalSonetHoPath1dayEntry 7 }

currentSonetLoPath15minTable OBJECT-TYPE
    SYNTAX      SEQUENCE OF CurrentSonetLoPath15minEntry
    MAX-ACCESS  not-accessible
    STATUS      current
    DESCRIPTION   ""
    ::=  { performanceMonitoring 29 }

currentSonetLoPath15minEntry OBJECT-TYPE
    SYNTAX      CurrentSonetLoPath15minEntry
    MAX-ACCESS  not-accessible
    STATUS      current
    DESCRIPTION   ""
    INDEX       {
                  entityIndex
                }
    ::=  { currentSonetLoPath15minTable 1 }

CurrentSonetLoPath15minEntry ::=  SEQUENCE
  { currentSonetLoPath15minES Unsigned32,
    currentSonetLoPath15minSES Unsigned32,
    currentSonetLoPath15minUAS Unsigned32,
    currentSonetLoPath15minCV Counter64String,
    currentSonetLoPath15minElapsedTime Integer32 }

currentSonetLoPath15minES OBJECT-TYPE
    SYNTAX      Unsigned32
    MAX-ACCESS  read-only
    STATUS      current
    DESCRIPTION
        "Path Low Order Errored Seconds" 
    ::=  { currentSonetLoPath15minEntry 1 }

currentSonetLoPath15minSES OBJECT-TYPE
    SYNTAX      Unsigned32
    MAX-ACCESS  read-only
    STATUS      current
    DESCRIPTION
        "Path Low Order Severely Errored Seconds" 
    ::=  { currentSonetLoPath15minEntry 2 }

currentSonetLoPath15minUAS OBJECT-TYPE
    SYNTAX      Unsigned32
    MAX-ACCESS  read-only
    STATUS      current
    DESCRIPTION
        "Path Low Order Unavailable Seconds" 
    ::=  { currentSonetLoPath15minEntry 3 }

currentSonetLoPath15minCV OBJECT-TYPE
    SYNTAX      Counter64String
    MAX-ACCESS  read-only
    STATUS      current
    DESCRIPTION
        "Path Low Order Coding Violations" 
    ::=  { currentSonetLoPath15minEntry 4 }

currentSonetLoPath15minElapsedTime OBJECT-TYPE
    SYNTAX      Integer32 (0..9000 | -2147483648)
    MAX-ACCESS  read-only
    STATUS      current
    DESCRIPTION
        "Elapsed 15Min" 
    ::=  { currentSonetLoPath15minEntry 5 }

currentSonetLoPath1dayTable OBJECT-TYPE
    SYNTAX      SEQUENCE OF CurrentSonetLoPath1dayEntry
    MAX-ACCESS  not-accessible
    STATUS      current
    DESCRIPTION   ""
    ::=  { performanceMonitoring 30 }

currentSonetLoPath1dayEntry OBJECT-TYPE
    SYNTAX      CurrentSonetLoPath1dayEntry
    MAX-ACCESS  not-accessible
    STATUS      current
    DESCRIPTION   ""
    INDEX       {
                  entityIndex
                }
    ::=  { currentSonetLoPath1dayTable 1 }

CurrentSonetLoPath1dayEntry ::=  SEQUENCE
  { currentSonetLoPath1dayES Unsigned32,
    currentSonetLoPath1daySES Unsigned32,
    currentSonetLoPath1dayUAS Unsigned32,
    currentSonetLoPath1dayCV Counter64String,
    currentSonetLoPath1dayElapsedTime Integer32 }

currentSonetLoPath1dayES OBJECT-TYPE
    SYNTAX      Unsigned32
    MAX-ACCESS  read-only
    STATUS      current
    DESCRIPTION
        "Path Low Order Errored Seconds" 
    ::=  { currentSonetLoPath1dayEntry 1 }

currentSonetLoPath1daySES OBJECT-TYPE
    SYNTAX      Unsigned32
    MAX-ACCESS  read-only
    STATUS      current
    DESCRIPTION
        "Path Low Order Severely Errored Seconds" 
    ::=  { currentSonetLoPath1dayEntry 2 }

currentSonetLoPath1dayUAS OBJECT-TYPE
    SYNTAX      Unsigned32
    MAX-ACCESS  read-only
    STATUS      current
    DESCRIPTION
        "Path Low Order Unavailable Seconds" 
    ::=  { currentSonetLoPath1dayEntry 3 }

currentSonetLoPath1dayCV OBJECT-TYPE
    SYNTAX      Counter64String
    MAX-ACCESS  read-only
    STATUS      current
    DESCRIPTION
        "Path Low Order Coding Violations" 
    ::=  { currentSonetLoPath1dayEntry 4 }

currentSonetLoPath1dayElapsedTime OBJECT-TYPE
    SYNTAX      Integer32 (0..86400 | -2147483648)
    MAX-ACCESS  read-only
    STATUS      current
    DESCRIPTION
        "Elapsed 1Day" 
    ::=  { currentSonetLoPath1dayEntry 5 }

intervalSonetLoPath15minTable OBJECT-TYPE
    SYNTAX      SEQUENCE OF IntervalSonetLoPath15minEntry
    MAX-ACCESS  not-accessible
    STATUS      current
    DESCRIPTION   ""
    ::=  { performanceMonitoring 31 }

intervalSonetLoPath15minEntry OBJECT-TYPE
    SYNTAX      IntervalSonetLoPath15minEntry
    MAX-ACCESS  not-accessible
    STATUS      current
    DESCRIPTION   ""
    INDEX       {
                  entityIndex,
                  intervalSonetLoPath15minNumber
                }
    ::=  { intervalSonetLoPath15minTable 1 }

IntervalSonetLoPath15minEntry ::=  SEQUENCE
  { intervalSonetLoPath15minNumber Integer32,
    intervalSonetLoPath15minES Unsigned32,
    intervalSonetLoPath15minSES Unsigned32,
    intervalSonetLoPath15minUAS Unsigned32,
    intervalSonetLoPath15minCV Counter64String,
    intervalSonetLoPath15minValidFlag TruthValue,
    intervalSonetLoPath15minTimeStamp DateAndTime }

intervalSonetLoPath15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalSonetLoPath15minEntry 1 }

intervalSonetLoPath15minES OBJECT-TYPE
    SYNTAX      Unsigned32
    MAX-ACCESS  read-only
    STATUS      current
    DESCRIPTION
        "Path Low Order Errored Seconds" 
    ::=  { intervalSonetLoPath15minEntry 2 }

intervalSonetLoPath15minSES OBJECT-TYPE
    SYNTAX      Unsigned32
    MAX-ACCESS  read-only
    STATUS      current
    DESCRIPTION
        "Path Low Order Severely Errored Seconds" 
    ::=  { intervalSonetLoPath15minEntry 3 }

intervalSonetLoPath15minUAS OBJECT-TYPE
    SYNTAX      Unsigned32
    MAX-ACCESS  read-only
    STATUS      current
    DESCRIPTION
        "Path Low Order Unavailable Seconds" 
    ::=  { intervalSonetLoPath15minEntry 4 }

intervalSonetLoPath15minCV OBJECT-TYPE
    SYNTAX      Counter64String
    MAX-ACCESS  read-only
    STATUS      current
    DESCRIPTION
        "Path Low Order Coding Violations" 
    ::=  { intervalSonetLoPath15minEntry 5 }

intervalSonetLoPath15minValidFlag OBJECT-TYPE
    SYNTAX      TruthValue
    MAX-ACCESS  read-only
    STATUS      current
    DESCRIPTION
        "Valid Flag" 
    ::=  { intervalSonetLoPath15minEntry 6 }

intervalSonetLoPath15minTimeStamp OBJECT-TYPE
    SYNTAX      DateAndTime
    MAX-ACCESS  read-only
    STATUS      current
    DESCRIPTION
        "Timestamp" 
    ::=  { intervalSonetLoPath15minEntry 7 }

intervalSonetLoPath1dayTable OBJECT-TYPE
    SYNTAX      SEQUENCE OF IntervalSonetLoPath1dayEntry
    MAX-ACCESS  not-accessible
    STATUS      current
    DESCRIPTION   ""
    ::=  { performanceMonitoring 32 }

intervalSonetLoPath1dayEntry OBJECT-TYPE
    SYNTAX      IntervalSonetLoPath1dayEntry
    MAX-ACCESS  not-accessible
    STATUS      current
    DESCRIPTION   ""
    INDEX       {
                  entityIndex,
                  intervalSonetLoPath1dayNumber
                }
    ::=  { intervalSonetLoPath1dayTable 1 }

IntervalSonetLoPath1dayEntry ::=  SEQUENCE
  { intervalSonetLoPath1dayNumber Integer32,
    intervalSonetLoPath1dayES Unsigned32,
    intervalSonetLoPath1daySES Unsigned32,
    intervalSonetLoPath1dayUAS Unsigned32,
    intervalSonetLoPath1dayCV Counter64String,
    intervalSonetLoPath1dayValidFlag TruthValue,
    intervalSonetLoPath1dayTimeStamp DateAndTime }

intervalSonetLoPath1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalSonetLoPath1dayEntry 1 }

intervalSonetLoPath1dayES OBJECT-TYPE
    SYNTAX      Unsigned32
    MAX-ACCESS  read-only
    STATUS      current
    DESCRIPTION
        "Path Low Order Errored Seconds" 
    ::=  { intervalSonetLoPath1dayEntry 2 }

intervalSonetLoPath1daySES OBJECT-TYPE
    SYNTAX      Unsigned32
    MAX-ACCESS  read-only
    STATUS      current
    DESCRIPTION
        "Path Low Order Severely Errored Seconds" 
    ::=  { intervalSonetLoPath1dayEntry 3 }

intervalSonetLoPath1dayUAS OBJECT-TYPE
    SYNTAX      Unsigned32
    MAX-ACCESS  read-only
    STATUS      current
    DESCRIPTION
        "Path Low Order Unavailable Seconds" 
    ::=  { intervalSonetLoPath1dayEntry 4 }

intervalSonetLoPath1dayCV OBJECT-TYPE
    SYNTAX      Counter64String
    MAX-ACCESS  read-only
    STATUS      current
    DESCRIPTION
        "Path Low Order Coding Violations" 
    ::=  { intervalSonetLoPath1dayEntry 5 }

intervalSonetLoPath1dayValidFlag OBJECT-TYPE
    SYNTAX      TruthValue
    MAX-ACCESS  read-only
    STATUS      current
    DESCRIPTION
        "Valid Flag" 
    ::=  { intervalSonetLoPath1dayEntry 6 }

intervalSonetLoPath1dayTimeStamp OBJECT-TYPE
    SYNTAX      DateAndTime
    MAX-ACCESS  read-only
    STATUS      current
    DESCRIPTION
        "Timestamp" 
    ::=  { intervalSonetLoPath1dayEntry 7 }

intervalPhysPerfOpticalInputPwr15minTable OBJECT-TYPE
    SYNTAX      SEQUENCE OF IntervalPhysPerfOpticalInputPwr15minEntry
    MAX-ACCESS  not-accessible
    STATUS      current
    DESCRIPTION   ""
    ::=  { performanceMonitoring 33 }

intervalPhysPerfOpticalInputPwr15minEntry OBJECT-TYPE
    SYNTAX      IntervalPhysPerfOpticalInputPwr15minEntry
    MAX-ACCESS  not-accessible
    STATUS      current
    DESCRIPTION   ""
    INDEX       {
                  entityIndex,
                  intervalPhysPerfOpticalInputPwr15minNumber
                }
    ::=  { intervalPhysPerfOpticalInputPwr15minTable 1 }

IntervalPhysPerfOpticalInputPwr15minEntry ::=  SEQUENCE
  { intervalPhysPerfOpticalInputPwr15minNumber Integer32,
    intervalPhysPerfOpticalInputPwr15minLow Integer32,
    intervalPhysPerfOpticalInputPwr15minMean Integer32,
    intervalPhysPerfOpticalInputPwr15minHigh Integer32,
    intervalPhysPerfOpticalInputPwr15minValidFlag TruthValue,
    intervalPhysPerfOpticalInputPwr15minTimeStamp DateAndTime }

intervalPhysPerfOpticalInputPwr15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfOpticalInputPwr15minEntry 1 }

intervalPhysPerfOpticalInputPwr15minLow OBJECT-TYPE
    SYNTAX      Integer32 
    UNITS       "0.1 dBm"
    MAX-ACCESS  read-only
    STATUS      current
    DESCRIPTION
        "Optical Input Power Received" 
    ::=  { intervalPhysPerfOpticalInputPwr15minEntry 2 }

intervalPhysPerfOpticalInputPwr15minMean OBJECT-TYPE
    SYNTAX      Integer32 
    UNITS       "0.1 dBm"
    MAX-ACCESS  read-only
    STATUS      current
    DESCRIPTION
        "Optical Input Power Received" 
    ::=  { intervalPhysPerfOpticalInputPwr15minEntry 3 }

intervalPhysPerfOpticalInputPwr15minHigh OBJECT-TYPE
    SYNTAX      Integer32 
    UNITS       "0.1 dBm"
    MAX-ACCESS  read-only
    STATUS      current
    DESCRIPTION
        "Optical Input Power Received" 
    ::=  { intervalPhysPerfOpticalInputPwr15minEntry 4 }

intervalPhysPerfOpticalInputPwr15minValidFlag OBJECT-TYPE
    SYNTAX      TruthValue
    MAX-ACCESS  read-only
    STATUS      current
    DESCRIPTION
        "Valid Flag" 
    ::=  { intervalPhysPerfOpticalInputPwr15minEntry 5 }

intervalPhysPerfOpticalInputPwr15minTimeStamp OBJECT-TYPE
    SYNTAX      DateAndTime
    MAX-ACCESS  read-only
    STATUS      current
    DESCRIPTION
        "Timestamp" 
    ::=  { intervalPhysPerfOpticalInputPwr15minEntry 6 }

intervalPhysPerfOpticalInputPwr1dayTable OBJECT-TYPE
    SYNTAX      SEQUENCE OF IntervalPhysPerfOpticalInputPwr1dayEntry
    MAX-ACCESS  not-accessible
    STATUS      current
    DESCRIPTION   ""
    ::=  { performanceMonitoring 34 }

intervalPhysPerfOpticalInputPwr1dayEntry OBJECT-TYPE
    SYNTAX      IntervalPhysPerfOpticalInputPwr1dayEntry
    MAX-ACCESS  not-accessible
    STATUS      current
    DESCRIPTION   ""
    INDEX       {
                  entityIndex,
                  intervalPhysPerfOpticalInputPwr1dayNumber
                }
    ::=  { intervalPhysPerfOpticalInputPwr1dayTable 1 }

IntervalPhysPerfOpticalInputPwr1dayEntry ::=  SEQUENCE
  { intervalPhysPerfOpticalInputPwr1dayNumber Integer32,
    intervalPhysPerfOpticalInputPwr1dayLow Integer32,
    intervalPhysPerfOpticalInputPwr1dayMean Integer32,
    intervalPhysPerfOpticalInputPwr1dayHigh Integer32,
    intervalPhysPerfOpticalInputPwr1dayValidFlag TruthValue,
    intervalPhysPerfOpticalInputPwr1dayTimeStamp DateAndTime }

intervalPhysPerfOpticalInputPwr1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfOpticalInputPwr1dayEntry 1 }

intervalPhysPerfOpticalInputPwr1dayLow OBJECT-TYPE
    SYNTAX      Integer32 
    UNITS       "0.1 dBm"
    MAX-ACCESS  read-only
    STATUS      current
    DESCRIPTION
        "Optical Input Power Received" 
    ::=  { intervalPhysPerfOpticalInputPwr1dayEntry 2 }

intervalPhysPerfOpticalInputPwr1dayMean OBJECT-TYPE
    SYNTAX      Integer32 
    UNITS       "0.1 dBm"
    MAX-ACCESS  read-only
    STATUS      current
    DESCRIPTION
        "Optical Input Power Received" 
    ::=  { intervalPhysPerfOpticalInputPwr1dayEntry 3 }

intervalPhysPerfOpticalInputPwr1dayHigh OBJECT-TYPE
    SYNTAX      Integer32 
    UNITS       "0.1 dBm"
    MAX-ACCESS  read-only
    STATUS      current
    DESCRIPTION
        "Optical Input Power Received" 
    ::=  { intervalPhysPerfOpticalInputPwr1dayEntry 4 }

intervalPhysPerfOpticalInputPwr1dayValidFlag OBJECT-TYPE
    SYNTAX      TruthValue
    MAX-ACCESS  read-only
    STATUS      current
    DESCRIPTION
        "Valid Flag" 
    ::=  { intervalPhysPerfOpticalInputPwr1dayEntry 5 }

intervalPhysPerfOpticalInputPwr1dayTimeStamp OBJECT-TYPE
    SYNTAX      DateAndTime
    MAX-ACCESS  read-only
    STATUS      current
    DESCRIPTION
        "Timestamp" 
    ::=  { intervalPhysPerfOpticalInputPwr1dayEntry 6 }

intervalPhysPerfOpticalInputPwr1weekTable OBJECT-TYPE
    SYNTAX      SEQUENCE OF IntervalPhysPerfOpticalInputPwr1weekEntry
    MAX-ACCESS  not-accessible
    STATUS      current
    DESCRIPTION   ""
    ::=  { performanceMonitoring 35 }

intervalPhysPerfOpticalInputPwr1weekEntry OBJECT-TYPE
    SYNTAX      IntervalPhysPerfOpticalInputPwr1weekEntry
    MAX-ACCESS  not-accessible
    STATUS      current
    DESCRIPTION   ""
    INDEX       {
                  entityIndex,
                  intervalPhysPerfOpticalInputPwr1weekNumber
                }
    ::=  { intervalPhysPerfOpticalInputPwr1weekTable 1 }

IntervalPhysPerfOpticalInputPwr1weekEntry ::=  SEQUENCE
  { intervalPhysPerfOpticalInputPwr1weekNumber Integer32,
    intervalPhysPerfOpticalInputPwr1weekLow Integer32,
    intervalPhysPerfOpticalInputPwr1weekMean Integer32,
    intervalPhysPerfOpticalInputPwr1weekHigh Integer32,
    intervalPhysPerfOpticalInputPwr1weekValidFlag TruthValue,
    intervalPhysPerfOpticalInputPwr1weekTimeStamp DateAndTime }

intervalPhysPerfOpticalInputPwr1weekNumber OBJECT-TYPE
    SYNTAX      Integer32 (1..52)
    MAX-ACCESS  not-accessible
    STATUS      current
    DESCRIPTION
        "Number 1week" 
    ::=  { intervalPhysPerfOpticalInputPwr1weekEntry 1 }

intervalPhysPerfOpticalInputPwr1weekLow OBJECT-TYPE
    SYNTAX      Integer32 
    UNITS       "0.1 dBm"
    MAX-ACCESS  read-only
    STATUS      current
    DESCRIPTION
        "Optical Input Power Received" 
    ::=  { intervalPhysPerfOpticalInputPwr1weekEntry 2 }

intervalPhysPerfOpticalInputPwr1weekMean OBJECT-TYPE
    SYNTAX      Integer32 
    UNITS       "0.1 dBm"
    MAX-ACCESS  read-only
    STATUS      current
    DESCRIPTION
        "Optical Input Power Received" 
    ::=  { intervalPhysPerfOpticalInputPwr1weekEntry 3 }

intervalPhysPerfOpticalInputPwr1weekHigh OBJECT-TYPE
    SYNTAX      Integer32 
    UNITS       "0.1 dBm"
    MAX-ACCESS  read-only
    STATUS      current
    DESCRIPTION
        "Optical Input Power Received" 
    ::=  { intervalPhysPerfOpticalInputPwr1weekEntry 4 }

intervalPhysPerfOpticalInputPwr1weekValidFlag OBJECT-TYPE
    SYNTAX      TruthValue
    MAX-ACCESS  read-only
    STATUS      current
    DESCRIPTION
        "Valid Flag" 
    ::=  { intervalPhysPerfOpticalInputPwr1weekEntry 5 }

intervalPhysPerfOpticalInputPwr1weekTimeStamp OBJECT-TYPE
    SYNTAX      DateAndTime
    MAX-ACCESS  read-only
    STATUS      current
    DESCRIPTION
        "Timestamp" 
    ::=  { intervalPhysPerfOpticalInputPwr1weekEntry 6 }

intervalPhysPerfOpticalOutputPwr15minTable OBJECT-TYPE
    SYNTAX      SEQUENCE OF IntervalPhysPerfOpticalOutputPwr15minEntry
    MAX-ACCESS  not-accessible
    STATUS      current
    DESCRIPTION   ""
    ::=  { performanceMonitoring 36 }

intervalPhysPerfOpticalOutputPwr15minEntry OBJECT-TYPE
    SYNTAX      IntervalPhysPerfOpticalOutputPwr15minEntry
    MAX-ACCESS  not-accessible
    STATUS      current
    DESCRIPTION   ""
    INDEX       {
                  entityIndex,
                  intervalPhysPerfOpticalOutputPwr15minNumber
                }
    ::=  { intervalPhysPerfOpticalOutputPwr15minTable 1 }

IntervalPhysPerfOpticalOutputPwr15minEntry ::=  SEQUENCE
  { intervalPhysPerfOpticalOutputPwr15minNumber Integer32,
    intervalPhysPerfOpticalOutputPwr15minLow Integer32,
    intervalPhysPerfOpticalOutputPwr15minMean Integer32,
    intervalPhysPerfOpticalOutputPwr15minHigh Integer32,
    intervalPhysPerfOpticalOutputPwr15minValidFlag TruthValue,
    intervalPhysPerfOpticalOutputPwr15minTimeStamp DateAndTime }

intervalPhysPerfOpticalOutputPwr15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfOpticalOutputPwr15minEntry 1 }

intervalPhysPerfOpticalOutputPwr15minLow OBJECT-TYPE
    SYNTAX      Integer32 
    UNITS       "0.1 dBm"
    MAX-ACCESS  read-only
    STATUS      current
    DESCRIPTION
        "Optical Output Power Transmitted" 
    ::=  { intervalPhysPerfOpticalOutputPwr15minEntry 2 }

intervalPhysPerfOpticalOutputPwr15minMean OBJECT-TYPE
    SYNTAX      Integer32 
    UNITS       "0.1 dBm"
    MAX-ACCESS  read-only
    STATUS      current
    DESCRIPTION
        "Optical Output Power Transmitted" 
    ::=  { intervalPhysPerfOpticalOutputPwr15minEntry 3 }

intervalPhysPerfOpticalOutputPwr15minHigh OBJECT-TYPE
    SYNTAX      Integer32 
    UNITS       "0.1 dBm"
    MAX-ACCESS  read-only
    STATUS      current
    DESCRIPTION
        "Optical Output Power Transmitted" 
    ::=  { intervalPhysPerfOpticalOutputPwr15minEntry 4 }

intervalPhysPerfOpticalOutputPwr15minValidFlag OBJECT-TYPE
    SYNTAX      TruthValue
    MAX-ACCESS  read-only
    STATUS      current
    DESCRIPTION
        "Valid Flag" 
    ::=  { intervalPhysPerfOpticalOutputPwr15minEntry 5 }

intervalPhysPerfOpticalOutputPwr15minTimeStamp OBJECT-TYPE
    SYNTAX      DateAndTime
    MAX-ACCESS  read-only
    STATUS      current
    DESCRIPTION
        "Timestamp" 
    ::=  { intervalPhysPerfOpticalOutputPwr15minEntry 6 }

intervalPhysPerfOpticalOutputPwr1dayTable OBJECT-TYPE
    SYNTAX      SEQUENCE OF IntervalPhysPerfOpticalOutputPwr1dayEntry
    MAX-ACCESS  not-accessible
    STATUS      current
    DESCRIPTION   ""
    ::=  { performanceMonitoring 37 }

intervalPhysPerfOpticalOutputPwr1dayEntry OBJECT-TYPE
    SYNTAX      IntervalPhysPerfOpticalOutputPwr1dayEntry
    MAX-ACCESS  not-accessible
    STATUS      current
    DESCRIPTION   ""
    INDEX       {
                  entityIndex,
                  intervalPhysPerfOpticalOutputPwr1dayNumber
                }
    ::=  { intervalPhysPerfOpticalOutputPwr1dayTable 1 }

IntervalPhysPerfOpticalOutputPwr1dayEntry ::=  SEQUENCE
  { intervalPhysPerfOpticalOutputPwr1dayNumber Integer32,
    intervalPhysPerfOpticalOutputPwr1dayLow Integer32,
    intervalPhysPerfOpticalOutputPwr1dayMean Integer32,
    intervalPhysPerfOpticalOutputPwr1dayHigh Integer32,
    intervalPhysPerfOpticalOutputPwr1dayValidFlag TruthValue,
    intervalPhysPerfOpticalOutputPwr1dayTimeStamp DateAndTime }

intervalPhysPerfOpticalOutputPwr1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfOpticalOutputPwr1dayEntry 1 }

intervalPhysPerfOpticalOutputPwr1dayLow OBJECT-TYPE
    SYNTAX      Integer32 
    UNITS       "0.1 dBm"
    MAX-ACCESS  read-only
    STATUS      current
    DESCRIPTION
        "Optical Output Power Transmitted" 
    ::=  { intervalPhysPerfOpticalOutputPwr1dayEntry 2 }

intervalPhysPerfOpticalOutputPwr1dayMean OBJECT-TYPE
    SYNTAX      Integer32 
    UNITS       "0.1 dBm"
    MAX-ACCESS  read-only
    STATUS      current
    DESCRIPTION
        "Optical Output Power Transmitted" 
    ::=  { intervalPhysPerfOpticalOutputPwr1dayEntry 3 }

intervalPhysPerfOpticalOutputPwr1dayHigh OBJECT-TYPE
    SYNTAX      Integer32 
    UNITS       "0.1 dBm"
    MAX-ACCESS  read-only
    STATUS      current
    DESCRIPTION
        "Optical Output Power Transmitted" 
    ::=  { intervalPhysPerfOpticalOutputPwr1dayEntry 4 }

intervalPhysPerfOpticalOutputPwr1dayValidFlag OBJECT-TYPE
    SYNTAX      TruthValue
    MAX-ACCESS  read-only
    STATUS      current
    DESCRIPTION
        "Valid Flag" 
    ::=  { intervalPhysPerfOpticalOutputPwr1dayEntry 5 }

intervalPhysPerfOpticalOutputPwr1dayTimeStamp OBJECT-TYPE
    SYNTAX      DateAndTime
    MAX-ACCESS  read-only
    STATUS      current
    DESCRIPTION
        "Timestamp" 
    ::=  { intervalPhysPerfOpticalOutputPwr1dayEntry 6 }

intervalPhysPerfOpticalOutputPwr1weekTable OBJECT-TYPE
    SYNTAX      SEQUENCE OF IntervalPhysPerfOpticalOutputPwr1weekEntry
    MAX-ACCESS  not-accessible
    STATUS      current
    DESCRIPTION   ""
    ::=  { performanceMonitoring 38 }

intervalPhysPerfOpticalOutputPwr1weekEntry OBJECT-TYPE
    SYNTAX      IntervalPhysPerfOpticalOutputPwr1weekEntry
    MAX-ACCESS  not-accessible
    STATUS      current
    DESCRIPTION   ""
    INDEX       {
                  entityIndex,
                  intervalPhysPerfOpticalOutputPwr1weekNumber
                }
    ::=  { intervalPhysPerfOpticalOutputPwr1weekTable 1 }

IntervalPhysPerfOpticalOutputPwr1weekEntry ::=  SEQUENCE
  { intervalPhysPerfOpticalOutputPwr1weekNumber Integer32,
    intervalPhysPerfOpticalOutputPwr1weekLow Integer32,
    intervalPhysPerfOpticalOutputPwr1weekMean Integer32,
    intervalPhysPerfOpticalOutputPwr1weekHigh Integer32,
    intervalPhysPerfOpticalOutputPwr1weekValidFlag TruthValue,
    intervalPhysPerfOpticalOutputPwr1weekTimeStamp DateAndTime }

intervalPhysPerfOpticalOutputPwr1weekNumber OBJECT-TYPE
    SYNTAX      Integer32 (1..52)
    MAX-ACCESS  not-accessible
    STATUS      current
    DESCRIPTION
        "Number 1week" 
    ::=  { intervalPhysPerfOpticalOutputPwr1weekEntry 1 }

intervalPhysPerfOpticalOutputPwr1weekLow OBJECT-TYPE
    SYNTAX      Integer32 
    UNITS       "0.1 dBm"
    MAX-ACCESS  read-only
    STATUS      current
    DESCRIPTION
        "Optical Output Power Transmitted" 
    ::=  { intervalPhysPerfOpticalOutputPwr1weekEntry 2 }

intervalPhysPerfOpticalOutputPwr1weekMean OBJECT-TYPE
    SYNTAX      Integer32 
    UNITS       "0.1 dBm"
    MAX-ACCESS  read-only
    STATUS      current
    DESCRIPTION
        "Optical Output Power Transmitted" 
    ::=  { intervalPhysPerfOpticalOutputPwr1weekEntry 3 }

intervalPhysPerfOpticalOutputPwr1weekHigh OBJECT-TYPE
    SYNTAX      Integer32 
    UNITS       "0.1 dBm"
    MAX-ACCESS  read-only
    STATUS      current
    DESCRIPTION
        "Optical Output Power Transmitted" 
    ::=  { intervalPhysPerfOpticalOutputPwr1weekEntry 4 }

intervalPhysPerfOpticalOutputPwr1weekValidFlag OBJECT-TYPE
    SYNTAX      TruthValue
    MAX-ACCESS  read-only
    STATUS      current
    DESCRIPTION
        "Valid Flag" 
    ::=  { intervalPhysPerfOpticalOutputPwr1weekEntry 5 }

intervalPhysPerfOpticalOutputPwr1weekTimeStamp OBJECT-TYPE
    SYNTAX      DateAndTime
    MAX-ACCESS  read-only
    STATUS      current
    DESCRIPTION
        "Timestamp" 
    ::=  { intervalPhysPerfOpticalOutputPwr1weekEntry 6 }

intervalPhysPerfLaserBiasCurrentNormalized15minTable OBJECT-TYPE
    SYNTAX      SEQUENCE OF IntervalPhysPerfLaserBiasCurrentNormalized15minEntry
    MAX-ACCESS  not-accessible
    STATUS      current
    DESCRIPTION   ""
    ::=  { performanceMonitoring 39 }

intervalPhysPerfLaserBiasCurrentNormalized15minEntry OBJECT-TYPE
    SYNTAX      IntervalPhysPerfLaserBiasCurrentNormalized15minEntry
    MAX-ACCESS  not-accessible
    STATUS      current
    DESCRIPTION   ""
    INDEX       {
                  entityIndex,
                  intervalPhysPerfLaserBiasCurrentNormalized15minNumber
                }
    ::=  { intervalPhysPerfLaserBiasCurrentNormalized15minTable 1 }

IntervalPhysPerfLaserBiasCurrentNormalized15minEntry ::=  SEQUENCE
  { intervalPhysPerfLaserBiasCurrentNormalized15minNumber Integer32,
    intervalPhysPerfLaserBiasCurrentNormalized15minLow Unsigned32,
    intervalPhysPerfLaserBiasCurrentNormalized15minMean Unsigned32,
    intervalPhysPerfLaserBiasCurrentNormalized15minHigh Unsigned32,
    intervalPhysPerfLaserBiasCurrentNormalized15minValidFlag TruthValue,
    intervalPhysPerfLaserBiasCurrentNormalized15minTimeStamp DateAndTime }

intervalPhysPerfLaserBiasCurrentNormalized15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfLaserBiasCurrentNormalized15minEntry 1 }

intervalPhysPerfLaserBiasCurrentNormalized15minLow OBJECT-TYPE
    SYNTAX      Unsigned32 
    UNITS       "%"
    MAX-ACCESS  read-only
    STATUS      current
    DESCRIPTION
        "Laser Bias Current Normalized" 
    ::=  { intervalPhysPerfLaserBiasCurrentNormalized15minEntry 2 }

intervalPhysPerfLaserBiasCurrentNormalized15minMean OBJECT-TYPE
    SYNTAX      Unsigned32 
    UNITS       "%"
    MAX-ACCESS  read-only
    STATUS      current
    DESCRIPTION
        "Laser Bias Current Normalized" 
    ::=  { intervalPhysPerfLaserBiasCurrentNormalized15minEntry 3 }

intervalPhysPerfLaserBiasCurrentNormalized15minHigh OBJECT-TYPE
    SYNTAX      Unsigned32 
    UNITS       "%"
    MAX-ACCESS  read-only
    STATUS      current
    DESCRIPTION
        "Laser Bias Current Normalized" 
    ::=  { intervalPhysPerfLaserBiasCurrentNormalized15minEntry 4 }

intervalPhysPerfLaserBiasCurrentNormalized15minValidFlag OBJECT-TYPE
    SYNTAX      TruthValue
    MAX-ACCESS  read-only
    STATUS      current
    DESCRIPTION
        "Valid Flag" 
    ::=  { intervalPhysPerfLaserBiasCurrentNormalized15minEntry 5 }

intervalPhysPerfLaserBiasCurrentNormalized15minTimeStamp OBJECT-TYPE
    SYNTAX      DateAndTime
    MAX-ACCESS  read-only
    STATUS      current
    DESCRIPTION
        "Timestamp" 
    ::=  { intervalPhysPerfLaserBiasCurrentNormalized15minEntry 6 }

intervalPhysPerfLaserBiasCurrentNormalized1dayTable OBJECT-TYPE
    SYNTAX      SEQUENCE OF IntervalPhysPerfLaserBiasCurrentNormalized1dayEntry
    MAX-ACCESS  not-accessible
    STATUS      current
    DESCRIPTION   ""
    ::=  { performanceMonitoring 40 }

intervalPhysPerfLaserBiasCurrentNormalized1dayEntry OBJECT-TYPE
    SYNTAX      IntervalPhysPerfLaserBiasCurrentNormalized1dayEntry
    MAX-ACCESS  not-accessible
    STATUS      current
    DESCRIPTION   ""
    INDEX       {
                  entityIndex,
                  intervalPhysPerfLaserBiasCurrentNormalized1dayNumber
                }
    ::=  { intervalPhysPerfLaserBiasCurrentNormalized1dayTable 1 }

IntervalPhysPerfLaserBiasCurrentNormalized1dayEntry ::=  SEQUENCE
  { intervalPhysPerfLaserBiasCurrentNormalized1dayNumber Integer32,
    intervalPhysPerfLaserBiasCurrentNormalized1dayLow Unsigned32,
    intervalPhysPerfLaserBiasCurrentNormalized1dayMean Unsigned32,
    intervalPhysPerfLaserBiasCurrentNormalized1dayHigh Unsigned32,
    intervalPhysPerfLaserBiasCurrentNormalized1dayValidFlag TruthValue,
    intervalPhysPerfLaserBiasCurrentNormalized1dayTimeStamp DateAndTime }

intervalPhysPerfLaserBiasCurrentNormalized1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfLaserBiasCurrentNormalized1dayEntry 1 }

intervalPhysPerfLaserBiasCurrentNormalized1dayLow OBJECT-TYPE
    SYNTAX      Unsigned32 
    UNITS       "%"
    MAX-ACCESS  read-only
    STATUS      current
    DESCRIPTION
        "Laser Bias Current Normalized" 
    ::=  { intervalPhysPerfLaserBiasCurrentNormalized1dayEntry 2 }

intervalPhysPerfLaserBiasCurrentNormalized1dayMean OBJECT-TYPE
    SYNTAX      Unsigned32 
    UNITS       "%"
    MAX-ACCESS  read-only
    STATUS      current
    DESCRIPTION
        "Laser Bias Current Normalized" 
    ::=  { intervalPhysPerfLaserBiasCurrentNormalized1dayEntry 3 }

intervalPhysPerfLaserBiasCurrentNormalized1dayHigh OBJECT-TYPE
    SYNTAX      Unsigned32 
    UNITS       "%"
    MAX-ACCESS  read-only
    STATUS      current
    DESCRIPTION
        "Laser Bias Current Normalized" 
    ::=  { intervalPhysPerfLaserBiasCurrentNormalized1dayEntry 4 }

intervalPhysPerfLaserBiasCurrentNormalized1dayValidFlag OBJECT-TYPE
    SYNTAX      TruthValue
    MAX-ACCESS  read-only
    STATUS      current
    DESCRIPTION
        "Valid Flag" 
    ::=  { intervalPhysPerfLaserBiasCurrentNormalized1dayEntry 5 }

intervalPhysPerfLaserBiasCurrentNormalized1dayTimeStamp OBJECT-TYPE
    SYNTAX      DateAndTime
    MAX-ACCESS  read-only
    STATUS      current
    DESCRIPTION
        "Timestamp" 
    ::=  { intervalPhysPerfLaserBiasCurrentNormalized1dayEntry 6 }

intervalPhysPerfLaserBiasCurrentNormalized1weekTable OBJECT-TYPE
    SYNTAX      SEQUENCE OF IntervalPhysPerfLaserBiasCurrentNormalized1weekEntry
    MAX-ACCESS  not-accessible
    STATUS      current
    DESCRIPTION   ""
    ::=  { performanceMonitoring 41 }

intervalPhysPerfLaserBiasCurrentNormalized1weekEntry OBJECT-TYPE
    SYNTAX      IntervalPhysPerfLaserBiasCurrentNormalized1weekEntry
    MAX-ACCESS  not-accessible
    STATUS      current
    DESCRIPTION   ""
    INDEX       {
                  entityIndex,
                  intervalPhysPerfLaserBiasCurrentNormalized1weekNumber
                }
    ::=  { intervalPhysPerfLaserBiasCurrentNormalized1weekTable 1 }

IntervalPhysPerfLaserBiasCurrentNormalized1weekEntry ::=  SEQUENCE
  { intervalPhysPerfLaserBiasCurrentNormalized1weekNumber Integer32,
    intervalPhysPerfLaserBiasCurrentNormalized1weekLow Unsigned32,
    intervalPhysPerfLaserBiasCurrentNormalized1weekMean Unsigned32,
    intervalPhysPerfLaserBiasCurrentNormalized1weekHigh Unsigned32,
    intervalPhysPerfLaserBiasCurrentNormalized1weekValidFlag TruthValue,
    intervalPhysPerfLaserBiasCurrentNormalized1weekTimeStamp DateAndTime }

intervalPhysPerfLaserBiasCurrentNormalized1weekNumber OBJECT-TYPE
    SYNTAX      Integer32 (1..52)
    MAX-ACCESS  not-accessible
    STATUS      current
    DESCRIPTION
        "Number 1week" 
    ::=  { intervalPhysPerfLaserBiasCurrentNormalized1weekEntry 1 }

intervalPhysPerfLaserBiasCurrentNormalized1weekLow OBJECT-TYPE
    SYNTAX      Unsigned32 
    UNITS       "%"
    MAX-ACCESS  read-only
    STATUS      current
    DESCRIPTION
        "Laser Bias Current Normalized" 
    ::=  { intervalPhysPerfLaserBiasCurrentNormalized1weekEntry 2 }

intervalPhysPerfLaserBiasCurrentNormalized1weekMean OBJECT-TYPE
    SYNTAX      Unsigned32 
    UNITS       "%"
    MAX-ACCESS  read-only
    STATUS      current
    DESCRIPTION
        "Laser Bias Current Normalized" 
    ::=  { intervalPhysPerfLaserBiasCurrentNormalized1weekEntry 3 }

intervalPhysPerfLaserBiasCurrentNormalized1weekHigh OBJECT-TYPE
    SYNTAX      Unsigned32 
    UNITS       "%"
    MAX-ACCESS  read-only
    STATUS      current
    DESCRIPTION
        "Laser Bias Current Normalized" 
    ::=  { intervalPhysPerfLaserBiasCurrentNormalized1weekEntry 4 }

intervalPhysPerfLaserBiasCurrentNormalized1weekValidFlag OBJECT-TYPE
    SYNTAX      TruthValue
    MAX-ACCESS  read-only
    STATUS      current
    DESCRIPTION
        "Valid Flag" 
    ::=  { intervalPhysPerfLaserBiasCurrentNormalized1weekEntry 5 }

intervalPhysPerfLaserBiasCurrentNormalized1weekTimeStamp OBJECT-TYPE
    SYNTAX      DateAndTime
    MAX-ACCESS  read-only
    STATUS      current
    DESCRIPTION
        "Timestamp" 
    ::=  { intervalPhysPerfLaserBiasCurrentNormalized1weekEntry 6 }

intervalPhysPerfOlmRxLineAtt15minTable OBJECT-TYPE
    SYNTAX      SEQUENCE OF IntervalPhysPerfOlmRxLineAtt15minEntry
    MAX-ACCESS  not-accessible
    STATUS      current
    DESCRIPTION   ""
    ::=  { performanceMonitoring 42 }

intervalPhysPerfOlmRxLineAtt15minEntry OBJECT-TYPE
    SYNTAX      IntervalPhysPerfOlmRxLineAtt15minEntry
    MAX-ACCESS  not-accessible
    STATUS      current
    DESCRIPTION   ""
    INDEX       {
                  entityIndex,
                  intervalPhysPerfOlmRxLineAtt15minNumber
                }
    ::=  { intervalPhysPerfOlmRxLineAtt15minTable 1 }

IntervalPhysPerfOlmRxLineAtt15minEntry ::=  SEQUENCE
  { intervalPhysPerfOlmRxLineAtt15minNumber Integer32,
    intervalPhysPerfOlmRxLineAtt15minLow Integer32,
    intervalPhysPerfOlmRxLineAtt15minMean Integer32,
    intervalPhysPerfOlmRxLineAtt15minHigh Integer32,
    intervalPhysPerfOlmRxLineAtt15minValidFlag TruthValue,
    intervalPhysPerfOlmRxLineAtt15minTimeStamp DateAndTime }

intervalPhysPerfOlmRxLineAtt15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfOlmRxLineAtt15minEntry 1 }

intervalPhysPerfOlmRxLineAtt15minLow OBJECT-TYPE
    SYNTAX      Integer32 
    UNITS       "0.1 dB"
    MAX-ACCESS  read-only
    STATUS      current
    DESCRIPTION
        "Low Attenuation on Receive Fiber" 
    ::=  { intervalPhysPerfOlmRxLineAtt15minEntry 2 }

intervalPhysPerfOlmRxLineAtt15minMean OBJECT-TYPE
    SYNTAX      Integer32 
    UNITS       "0.1 dB"
    MAX-ACCESS  read-only
    STATUS      current
    DESCRIPTION
        "Mean Attenuation on Receive Fiber" 
    ::=  { intervalPhysPerfOlmRxLineAtt15minEntry 3 }

intervalPhysPerfOlmRxLineAtt15minHigh OBJECT-TYPE
    SYNTAX      Integer32 
    UNITS       "0.1 dB"
    MAX-ACCESS  read-only
    STATUS      current
    DESCRIPTION
        "High Attenuation on Receive Fiber" 
    ::=  { intervalPhysPerfOlmRxLineAtt15minEntry 4 }

intervalPhysPerfOlmRxLineAtt15minValidFlag OBJECT-TYPE
    SYNTAX      TruthValue
    MAX-ACCESS  read-only
    STATUS      current
    DESCRIPTION
        "Valid Flag" 
    ::=  { intervalPhysPerfOlmRxLineAtt15minEntry 5 }

intervalPhysPerfOlmRxLineAtt15minTimeStamp OBJECT-TYPE
    SYNTAX      DateAndTime
    MAX-ACCESS  read-only
    STATUS      current
    DESCRIPTION
        "Timestamp" 
    ::=  { intervalPhysPerfOlmRxLineAtt15minEntry 6 }

intervalPhysPerfOlmRxLineAtt1dayTable OBJECT-TYPE
    SYNTAX      SEQUENCE OF IntervalPhysPerfOlmRxLineAtt1dayEntry
    MAX-ACCESS  not-accessible
    STATUS      current
    DESCRIPTION   ""
    ::=  { performanceMonitoring 43 }

intervalPhysPerfOlmRxLineAtt1dayEntry OBJECT-TYPE
    SYNTAX      IntervalPhysPerfOlmRxLineAtt1dayEntry
    MAX-ACCESS  not-accessible
    STATUS      current
    DESCRIPTION   ""
    INDEX       {
                  entityIndex,
                  intervalPhysPerfOlmRxLineAtt1dayNumber
                }
    ::=  { intervalPhysPerfOlmRxLineAtt1dayTable 1 }

IntervalPhysPerfOlmRxLineAtt1dayEntry ::=  SEQUENCE
  { intervalPhysPerfOlmRxLineAtt1dayNumber Integer32,
    intervalPhysPerfOlmRxLineAtt1dayLow Integer32,
    intervalPhysPerfOlmRxLineAtt1dayMean Integer32,
    intervalPhysPerfOlmRxLineAtt1dayHigh Integer32,
    intervalPhysPerfOlmRxLineAtt1dayValidFlag TruthValue,
    intervalPhysPerfOlmRxLineAtt1dayTimeStamp DateAndTime }

intervalPhysPerfOlmRxLineAtt1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfOlmRxLineAtt1dayEntry 1 }

intervalPhysPerfOlmRxLineAtt1dayLow OBJECT-TYPE
    SYNTAX      Integer32 
    UNITS       "0.1 dB"
    MAX-ACCESS  read-only
    STATUS      current
    DESCRIPTION
        "Low Attenuation on Receive Fiber" 
    ::=  { intervalPhysPerfOlmRxLineAtt1dayEntry 2 }

intervalPhysPerfOlmRxLineAtt1dayMean OBJECT-TYPE
    SYNTAX      Integer32 
    UNITS       "0.1 dB"
    MAX-ACCESS  read-only
    STATUS      current
    DESCRIPTION
        "Mean Attenuation on Receive Fiber" 
    ::=  { intervalPhysPerfOlmRxLineAtt1dayEntry 3 }

intervalPhysPerfOlmRxLineAtt1dayHigh OBJECT-TYPE
    SYNTAX      Integer32 
    UNITS       "0.1 dB"
    MAX-ACCESS  read-only
    STATUS      current
    DESCRIPTION
        "High Attenuation on Receive Fiber" 
    ::=  { intervalPhysPerfOlmRxLineAtt1dayEntry 4 }

intervalPhysPerfOlmRxLineAtt1dayValidFlag OBJECT-TYPE
    SYNTAX      TruthValue
    MAX-ACCESS  read-only
    STATUS      current
    DESCRIPTION
        "Valid Flag" 
    ::=  { intervalPhysPerfOlmRxLineAtt1dayEntry 5 }

intervalPhysPerfOlmRxLineAtt1dayTimeStamp OBJECT-TYPE
    SYNTAX      DateAndTime
    MAX-ACCESS  read-only
    STATUS      current
    DESCRIPTION
        "Timestamp" 
    ::=  { intervalPhysPerfOlmRxLineAtt1dayEntry 6 }

intervalPhysPerfOlmRxLineAtt1weekTable OBJECT-TYPE
    SYNTAX      SEQUENCE OF IntervalPhysPerfOlmRxLineAtt1weekEntry
    MAX-ACCESS  not-accessible
    STATUS      current
    DESCRIPTION   ""
    ::=  { performanceMonitoring 44 }

intervalPhysPerfOlmRxLineAtt1weekEntry OBJECT-TYPE
    SYNTAX      IntervalPhysPerfOlmRxLineAtt1weekEntry
    MAX-ACCESS  not-accessible
    STATUS      current
    DESCRIPTION   ""
    INDEX       {
                  entityIndex,
                  intervalPhysPerfOlmRxLineAtt1weekNumber
                }
    ::=  { intervalPhysPerfOlmRxLineAtt1weekTable 1 }

IntervalPhysPerfOlmRxLineAtt1weekEntry ::=  SEQUENCE
  { intervalPhysPerfOlmRxLineAtt1weekNumber Integer32,
    intervalPhysPerfOlmRxLineAtt1weekLow Integer32,
    intervalPhysPerfOlmRxLineAtt1weekMean Integer32,
    intervalPhysPerfOlmRxLineAtt1weekHigh Integer32,
    intervalPhysPerfOlmRxLineAtt1weekValidFlag TruthValue,
    intervalPhysPerfOlmRxLineAtt1weekTimeStamp DateAndTime }

intervalPhysPerfOlmRxLineAtt1weekNumber OBJECT-TYPE
    SYNTAX      Integer32 (1..52)
    MAX-ACCESS  not-accessible
    STATUS      current
    DESCRIPTION
        "Number 1week" 
    ::=  { intervalPhysPerfOlmRxLineAtt1weekEntry 1 }

intervalPhysPerfOlmRxLineAtt1weekLow OBJECT-TYPE
    SYNTAX      Integer32 
    UNITS       "0.1 dB"
    MAX-ACCESS  read-only
    STATUS      current
    DESCRIPTION
        "Low Attenuation on Receive Fiber" 
    ::=  { intervalPhysPerfOlmRxLineAtt1weekEntry 2 }

intervalPhysPerfOlmRxLineAtt1weekMean OBJECT-TYPE
    SYNTAX      Integer32 
    UNITS       "0.1 dB"
    MAX-ACCESS  read-only
    STATUS      current
    DESCRIPTION
        "Mean Attenuation on Receive Fiber" 
    ::=  { intervalPhysPerfOlmRxLineAtt1weekEntry 3 }

intervalPhysPerfOlmRxLineAtt1weekHigh OBJECT-TYPE
    SYNTAX      Integer32 
    UNITS       "0.1 dB"
    MAX-ACCESS  read-only
    STATUS      current
    DESCRIPTION
        "High Attenuation on Receive Fiber" 
    ::=  { intervalPhysPerfOlmRxLineAtt1weekEntry 4 }

intervalPhysPerfOlmRxLineAtt1weekValidFlag OBJECT-TYPE
    SYNTAX      TruthValue
    MAX-ACCESS  read-only
    STATUS      current
    DESCRIPTION
        "Valid Flag" 
    ::=  { intervalPhysPerfOlmRxLineAtt1weekEntry 5 }

intervalPhysPerfOlmRxLineAtt1weekTimeStamp OBJECT-TYPE
    SYNTAX      DateAndTime
    MAX-ACCESS  read-only
    STATUS      current
    DESCRIPTION
        "Timestamp" 
    ::=  { intervalPhysPerfOlmRxLineAtt1weekEntry 6 }

intervalPhysPerfOlmTxLineAtt15minTable OBJECT-TYPE
    SYNTAX      SEQUENCE OF IntervalPhysPerfOlmTxLineAtt15minEntry
    MAX-ACCESS  not-accessible
    STATUS      current
    DESCRIPTION   ""
    ::=  { performanceMonitoring 45 }

intervalPhysPerfOlmTxLineAtt15minEntry OBJECT-TYPE
    SYNTAX      IntervalPhysPerfOlmTxLineAtt15minEntry
    MAX-ACCESS  not-accessible
    STATUS      current
    DESCRIPTION   ""
    INDEX       {
                  entityIndex,
                  intervalPhysPerfOlmTxLineAtt15minNumber
                }
    ::=  { intervalPhysPerfOlmTxLineAtt15minTable 1 }

IntervalPhysPerfOlmTxLineAtt15minEntry ::=  SEQUENCE
  { intervalPhysPerfOlmTxLineAtt15minNumber Integer32,
    intervalPhysPerfOlmTxLineAtt15minLow Integer32,
    intervalPhysPerfOlmTxLineAtt15minHigh Integer32,
    intervalPhysPerfOlmTxLineAtt15minMean Integer32,
    intervalPhysPerfOlmTxLineAtt15minValidFlag TruthValue,
    intervalPhysPerfOlmTxLineAtt15minTimeStamp DateAndTime }

intervalPhysPerfOlmTxLineAtt15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfOlmTxLineAtt15minEntry 1 }

intervalPhysPerfOlmTxLineAtt15minLow OBJECT-TYPE
    SYNTAX      Integer32 
    UNITS       "0.1 dB"
    MAX-ACCESS  read-only
    STATUS      current
    DESCRIPTION
        "Low Attenuation on Transmit Fiber" 
    ::=  { intervalPhysPerfOlmTxLineAtt15minEntry 2 }

intervalPhysPerfOlmTxLineAtt15minHigh OBJECT-TYPE
    SYNTAX      Integer32 
    UNITS       "0.1 dB"
    MAX-ACCESS  read-only
    STATUS      current
    DESCRIPTION
        "High Attenuation on Transmit Fiber" 
    ::=  { intervalPhysPerfOlmTxLineAtt15minEntry 3 }

intervalPhysPerfOlmTxLineAtt15minMean OBJECT-TYPE
    SYNTAX      Integer32 
    UNITS       "0.1 dB"
    MAX-ACCESS  read-only
    STATUS      current
    DESCRIPTION
        "Mean Attenuation on Transmit Fiber" 
    ::=  { intervalPhysPerfOlmTxLineAtt15minEntry 4 }

intervalPhysPerfOlmTxLineAtt15minValidFlag OBJECT-TYPE
    SYNTAX      TruthValue
    MAX-ACCESS  read-only
    STATUS      current
    DESCRIPTION
        "Valid Flag" 
    ::=  { intervalPhysPerfOlmTxLineAtt15minEntry 5 }

intervalPhysPerfOlmTxLineAtt15minTimeStamp OBJECT-TYPE
    SYNTAX      DateAndTime
    MAX-ACCESS  read-only
    STATUS      current
    DESCRIPTION
        "Timestamp" 
    ::=  { intervalPhysPerfOlmTxLineAtt15minEntry 6 }

intervalPhysPerfOlmTxLineAtt1dayTable OBJECT-TYPE
    SYNTAX      SEQUENCE OF IntervalPhysPerfOlmTxLineAtt1dayEntry
    MAX-ACCESS  not-accessible
    STATUS      current
    DESCRIPTION   ""
    ::=  { performanceMonitoring 46 }

intervalPhysPerfOlmTxLineAtt1dayEntry OBJECT-TYPE
    SYNTAX      IntervalPhysPerfOlmTxLineAtt1dayEntry
    MAX-ACCESS  not-accessible
    STATUS      current
    DESCRIPTION   ""
    INDEX       {
                  entityIndex,
                  intervalPhysPerfOlmTxLineAtt1dayNumber
                }
    ::=  { intervalPhysPerfOlmTxLineAtt1dayTable 1 }

IntervalPhysPerfOlmTxLineAtt1dayEntry ::=  SEQUENCE
  { intervalPhysPerfOlmTxLineAtt1dayNumber Integer32,
    intervalPhysPerfOlmTxLineAtt1dayLow Integer32,
    intervalPhysPerfOlmTxLineAtt1dayHigh Integer32,
    intervalPhysPerfOlmTxLineAtt1dayMean Integer32,
    intervalPhysPerfOlmTxLineAtt1dayValidFlag TruthValue,
    intervalPhysPerfOlmTxLineAtt1dayTimeStamp DateAndTime }

intervalPhysPerfOlmTxLineAtt1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfOlmTxLineAtt1dayEntry 1 }

intervalPhysPerfOlmTxLineAtt1dayLow OBJECT-TYPE
    SYNTAX      Integer32 
    UNITS       "0.1 dB"
    MAX-ACCESS  read-only
    STATUS      current
    DESCRIPTION
        "Low Attenuation on Transmit Fiber" 
    ::=  { intervalPhysPerfOlmTxLineAtt1dayEntry 2 }

intervalPhysPerfOlmTxLineAtt1dayHigh OBJECT-TYPE
    SYNTAX      Integer32 
    UNITS       "0.1 dB"
    MAX-ACCESS  read-only
    STATUS      current
    DESCRIPTION
        "High Attenuation on Transmit Fiber" 
    ::=  { intervalPhysPerfOlmTxLineAtt1dayEntry 3 }

intervalPhysPerfOlmTxLineAtt1dayMean OBJECT-TYPE
    SYNTAX      Integer32 
    UNITS       "0.1 dB"
    MAX-ACCESS  read-only
    STATUS      current
    DESCRIPTION
        "Mean Attenuation on Transmit Fiber" 
    ::=  { intervalPhysPerfOlmTxLineAtt1dayEntry 4 }

intervalPhysPerfOlmTxLineAtt1dayValidFlag OBJECT-TYPE
    SYNTAX      TruthValue
    MAX-ACCESS  read-only
    STATUS      current
    DESCRIPTION
        "Valid Flag" 
    ::=  { intervalPhysPerfOlmTxLineAtt1dayEntry 5 }

intervalPhysPerfOlmTxLineAtt1dayTimeStamp OBJECT-TYPE
    SYNTAX      DateAndTime
    MAX-ACCESS  read-only
    STATUS      current
    DESCRIPTION
        "Timestamp" 
    ::=  { intervalPhysPerfOlmTxLineAtt1dayEntry 6 }

intervalPhysPerfOlmTxLineAtt1weekTable OBJECT-TYPE
    SYNTAX      SEQUENCE OF IntervalPhysPerfOlmTxLineAtt1weekEntry
    MAX-ACCESS  not-accessible
    STATUS      current
    DESCRIPTION   ""
    ::=  { performanceMonitoring 47 }

intervalPhysPerfOlmTxLineAtt1weekEntry OBJECT-TYPE
    SYNTAX      IntervalPhysPerfOlmTxLineAtt1weekEntry
    MAX-ACCESS  not-accessible
    STATUS      current
    DESCRIPTION   ""
    INDEX       {
                  entityIndex,
                  intervalPhysPerfOlmTxLineAtt1weekNumber
                }
    ::=  { intervalPhysPerfOlmTxLineAtt1weekTable 1 }

IntervalPhysPerfOlmTxLineAtt1weekEntry ::=  SEQUENCE
  { intervalPhysPerfOlmTxLineAtt1weekNumber Integer32,
    intervalPhysPerfOlmTxLineAtt1weekLow Integer32,
    intervalPhysPerfOlmTxLineAtt1weekHigh Integer32,
    intervalPhysPerfOlmTxLineAtt1weekMean Integer32,
    intervalPhysPerfOlmTxLineAtt1weekValidFlag TruthValue,
    intervalPhysPerfOlmTxLineAtt1weekTimeStamp DateAndTime }

intervalPhysPerfOlmTxLineAtt1weekNumber OBJECT-TYPE
    SYNTAX      Integer32 (1..52)
    MAX-ACCESS  not-accessible
    STATUS      current
    DESCRIPTION
        "Number 1week" 
    ::=  { intervalPhysPerfOlmTxLineAtt1weekEntry 1 }

intervalPhysPerfOlmTxLineAtt1weekLow OBJECT-TYPE
    SYNTAX      Integer32 
    UNITS       "0.1 dB"
    MAX-ACCESS  read-only
    STATUS      current
    DESCRIPTION
        "Low Attenuation on Transmit Fiber" 
    ::=  { intervalPhysPerfOlmTxLineAtt1weekEntry 2 }

intervalPhysPerfOlmTxLineAtt1weekHigh OBJECT-TYPE
    SYNTAX      Integer32 
    UNITS       "0.1 dB"
    MAX-ACCESS  read-only
    STATUS      current
    DESCRIPTION
        "High Attenuation on Transmit Fiber" 
    ::=  { intervalPhysPerfOlmTxLineAtt1weekEntry 3 }

intervalPhysPerfOlmTxLineAtt1weekMean OBJECT-TYPE
    SYNTAX      Integer32 
    UNITS       "0.1 dB"
    MAX-ACCESS  read-only
    STATUS      current
    DESCRIPTION
        "Mean Attenuation on Transmit Fiber" 
    ::=  { intervalPhysPerfOlmTxLineAtt1weekEntry 4 }

intervalPhysPerfOlmTxLineAtt1weekValidFlag OBJECT-TYPE
    SYNTAX      TruthValue
    MAX-ACCESS  read-only
    STATUS      current
    DESCRIPTION
        "Valid Flag" 
    ::=  { intervalPhysPerfOlmTxLineAtt1weekEntry 5 }

intervalPhysPerfOlmTxLineAtt1weekTimeStamp OBJECT-TYPE
    SYNTAX      DateAndTime
    MAX-ACCESS  read-only
    STATUS      current
    DESCRIPTION
        "Timestamp" 
    ::=  { intervalPhysPerfOlmTxLineAtt1weekEntry 6 }

currentPhysConv15minTable OBJECT-TYPE
    SYNTAX      SEQUENCE OF CurrentPhysConv15minEntry
    MAX-ACCESS  not-accessible
    STATUS      current
    DESCRIPTION   ""
    ::=  { performanceMonitoring 48 }

currentPhysConv15minEntry OBJECT-TYPE
    SYNTAX      CurrentPhysConv15minEntry
    MAX-ACCESS  not-accessible
    STATUS      current
    DESCRIPTION   ""
    INDEX       {
                  entityIndex
                }
    ::=  { currentPhysConv15minTable 1 }

CurrentPhysConv15minEntry ::=  SEQUENCE
  { currentPhysConv15minES Unsigned32,
    currentPhysConv15minDE Unsigned32,
    currentPhysConv15minCV Counter64String,
    currentPhysConv15minElapsedTime Integer32 }

currentPhysConv15minES OBJECT-TYPE
    SYNTAX      Unsigned32
    MAX-ACCESS  read-only
    STATUS      current
    DESCRIPTION
        "Physical Coding Layer Errored Seconds" 
    ::=  { currentPhysConv15minEntry 1 }

currentPhysConv15minDE OBJECT-TYPE
    SYNTAX      Unsigned32
    MAX-ACCESS  read-only
    STATUS      current
    DESCRIPTION
        "Physical Coding Layer Disparity Errors" 
    ::=  { currentPhysConv15minEntry 2 }

currentPhysConv15minCV OBJECT-TYPE
    SYNTAX      Counter64String
    MAX-ACCESS  read-only
    STATUS      current
    DESCRIPTION
        "Physical Coding Layer Coding Violations" 
    ::=  { currentPhysConv15minEntry 3 }

currentPhysConv15minElapsedTime OBJECT-TYPE
    SYNTAX      Integer32 (0..9000 | -2147483648)
    MAX-ACCESS  read-only
    STATUS      current
    DESCRIPTION
        "Elapsed 15Min" 
    ::=  { currentPhysConv15minEntry 4 }

currentPhysConv1dayTable OBJECT-TYPE
    SYNTAX      SEQUENCE OF CurrentPhysConv1dayEntry
    MAX-ACCESS  not-accessible
    STATUS      current
    DESCRIPTION   ""
    ::=  { performanceMonitoring 49 }

currentPhysConv1dayEntry OBJECT-TYPE
    SYNTAX      CurrentPhysConv1dayEntry
    MAX-ACCESS  not-accessible
    STATUS      current
    DESCRIPTION   ""
    INDEX       {
                  entityIndex
                }
    ::=  { currentPhysConv1dayTable 1 }

CurrentPhysConv1dayEntry ::=  SEQUENCE
  { currentPhysConv1dayES Unsigned32,
    currentPhysConv1dayDE Unsigned32,
    currentPhysConv1dayCV Counter64String,
    currentPhysConv1dayElapsedTime Integer32 }

currentPhysConv1dayES OBJECT-TYPE
    SYNTAX      Unsigned32
    MAX-ACCESS  read-only
    STATUS      current
    DESCRIPTION
        "Physical Coding Layer Errored Seconds" 
    ::=  { currentPhysConv1dayEntry 1 }

currentPhysConv1dayDE OBJECT-TYPE
    SYNTAX      Unsigned32
    MAX-ACCESS  read-only
    STATUS      current
    DESCRIPTION
        "Physical Coding Layer Disparity Errors" 
    ::=  { currentPhysConv1dayEntry 2 }

currentPhysConv1dayCV OBJECT-TYPE
    SYNTAX      Counter64String
    MAX-ACCESS  read-only
    STATUS      current
    DESCRIPTION
        "Physical Coding Layer Coding Violations" 
    ::=  { currentPhysConv1dayEntry 3 }

currentPhysConv1dayElapsedTime OBJECT-TYPE
    SYNTAX      Integer32 (0..86400 | -2147483648)
    MAX-ACCESS  read-only
    STATUS      current
    DESCRIPTION
        "Elapsed 1Day" 
    ::=  { currentPhysConv1dayEntry 4 }

intervalPhysConv15minTable OBJECT-TYPE
    SYNTAX      SEQUENCE OF IntervalPhysConv15minEntry
    MAX-ACCESS  not-accessible
    STATUS      current
    DESCRIPTION   ""
    ::=  { performanceMonitoring 50 }

intervalPhysConv15minEntry OBJECT-TYPE
    SYNTAX      IntervalPhysConv15minEntry
    MAX-ACCESS  not-accessible
    STATUS      current
    DESCRIPTION   ""
    INDEX       {
                  entityIndex,
                  intervalPhysConv15minNumber
                }
    ::=  { intervalPhysConv15minTable 1 }

IntervalPhysConv15minEntry ::=  SEQUENCE
  { intervalPhysConv15minNumber Integer32,
    intervalPhysConv15minES Unsigned32,
    intervalPhysConv15minDE Unsigned32,
    intervalPhysConv15minCV Counter64String,
    intervalPhysConv15minValidFlag TruthValue,
    intervalPhysConv15minTimeStamp DateAndTime }

intervalPhysConv15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysConv15minEntry 1 }

intervalPhysConv15minES OBJECT-TYPE
    SYNTAX      Unsigned32
    MAX-ACCESS  read-only
    STATUS      current
    DESCRIPTION
        "Physical Coding Layer Errored Seconds" 
    ::=  { intervalPhysConv15minEntry 2 }

intervalPhysConv15minDE OBJECT-TYPE
    SYNTAX      Unsigned32
    MAX-ACCESS  read-only
    STATUS      current
    DESCRIPTION
        "Physical Coding Layer Disparity Errors" 
    ::=  { intervalPhysConv15minEntry 3 }

intervalPhysConv15minCV OBJECT-TYPE
    SYNTAX      Counter64String
    MAX-ACCESS  read-only
    STATUS      current
    DESCRIPTION
        "Physical Coding Layer Coding Violations" 
    ::=  { intervalPhysConv15minEntry 4 }

intervalPhysConv15minValidFlag OBJECT-TYPE
    SYNTAX      TruthValue
    MAX-ACCESS  read-only
    STATUS      current
    DESCRIPTION
        "Valid Flag" 
    ::=  { intervalPhysConv15minEntry 5 }

intervalPhysConv15minTimeStamp OBJECT-TYPE
    SYNTAX      DateAndTime
    MAX-ACCESS  read-only
    STATUS      current
    DESCRIPTION
        "Timestamp" 
    ::=  { intervalPhysConv15minEntry 6 }

intervalPhysConv1dayTable OBJECT-TYPE
    SYNTAX      SEQUENCE OF IntervalPhysConv1dayEntry
    MAX-ACCESS  not-accessible
    STATUS      current
    DESCRIPTION   ""
    ::=  { performanceMonitoring 51 }

intervalPhysConv1dayEntry OBJECT-TYPE
    SYNTAX      IntervalPhysConv1dayEntry
    MAX-ACCESS  not-accessible
    STATUS      current
    DESCRIPTION   ""
    INDEX       {
                  entityIndex,
                  intervalPhysConv1dayNumber
                }
    ::=  { intervalPhysConv1dayTable 1 }

IntervalPhysConv1dayEntry ::=  SEQUENCE
  { intervalPhysConv1dayNumber Integer32,
    intervalPhysConv1dayES Unsigned32,
    intervalPhysConv1dayDE Unsigned32,
    intervalPhysConv1dayCV Counter64String,
    intervalPhysConv1dayValidFlag TruthValue,
    intervalPhysConv1dayTimeStamp DateAndTime }

intervalPhysConv1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysConv1dayEntry 1 }

intervalPhysConv1dayES OBJECT-TYPE
    SYNTAX      Unsigned32
    MAX-ACCESS  read-only
    STATUS      current
    DESCRIPTION
        "Physical Coding Layer Errored Seconds" 
    ::=  { intervalPhysConv1dayEntry 2 }

intervalPhysConv1dayDE OBJECT-TYPE
    SYNTAX      Unsigned32
    MAX-ACCESS  read-only
    STATUS      current
    DESCRIPTION
        "Physical Coding Layer Disparity Errors" 
    ::=  { intervalPhysConv1dayEntry 3 }

intervalPhysConv1dayCV OBJECT-TYPE
    SYNTAX      Counter64String
    MAX-ACCESS  read-only
    STATUS      current
    DESCRIPTION
        "Physical Coding Layer Coding Violations" 
    ::=  { intervalPhysConv1dayEntry 4 }

intervalPhysConv1dayValidFlag OBJECT-TYPE
    SYNTAX      TruthValue
    MAX-ACCESS  read-only
    STATUS      current
    DESCRIPTION
        "Valid Flag" 
    ::=  { intervalPhysConv1dayEntry 5 }

intervalPhysConv1dayTimeStamp OBJECT-TYPE
    SYNTAX      DateAndTime
    MAX-ACCESS  read-only
    STATUS      current
    DESCRIPTION
        "Timestamp" 
    ::=  { intervalPhysConv1dayEntry 6 }

currentEthRx15minTable OBJECT-TYPE
    SYNTAX      SEQUENCE OF CurrentEthRx15minEntry
    MAX-ACCESS  not-accessible
    STATUS      current
    DESCRIPTION   ""
    ::=  { performanceMonitoring 52 }

currentEthRx15minEntry OBJECT-TYPE
    SYNTAX      CurrentEthRx15minEntry
    MAX-ACCESS  not-accessible
    STATUS      current
    DESCRIPTION   ""
    INDEX       {
                  entityIndex
                }
    ::=  { currentEthRx15minTable 1 }

CurrentEthRx15minEntry ::=  SEQUENCE
  { currentEthRx15minGoodFrames Counter64String,
    currentEthRx15minPauseFrames Counter64String,
    currentEthRx15minCrcFrames Counter64String,
    currentEthRx15minDiscardedFrames Counter64String,
    currentEthRx15minBytes Counter64String,
    currentEthRx15minElapsedTime Integer32 }

currentEthRx15minGoodFrames OBJECT-TYPE
    SYNTAX      Counter64String
    MAX-ACCESS  read-only
    STATUS      current
    DESCRIPTION
        "Frames Received" 
    ::=  { currentEthRx15minEntry 1 }

currentEthRx15minPauseFrames OBJECT-TYPE
    SYNTAX      Counter64String
    MAX-ACCESS  read-only
    STATUS      current
    DESCRIPTION
        "Pause Frames Received" 
    ::=  { currentEthRx15minEntry 2 }

currentEthRx15minCrcFrames OBJECT-TYPE
    SYNTAX      Counter64String
    MAX-ACCESS  read-only
    STATUS      current
    DESCRIPTION
        "Received CRC Errors" 
    ::=  { currentEthRx15minEntry 3 }

currentEthRx15minDiscardedFrames OBJECT-TYPE
    SYNTAX      Counter64String
    MAX-ACCESS  read-only
    STATUS      current
    DESCRIPTION
        "Received Frames Discarded" 
    ::=  { currentEthRx15minEntry 4 }

currentEthRx15minBytes OBJECT-TYPE
    SYNTAX      Counter64String
    MAX-ACCESS  read-only
    STATUS      current
    DESCRIPTION
        "Bytes Received" 
    ::=  { currentEthRx15minEntry 5 }

currentEthRx15minElapsedTime OBJECT-TYPE
    SYNTAX      Integer32 (0..9000 | -2147483648)
    MAX-ACCESS  read-only
    STATUS      current
    DESCRIPTION
        "Elapsed 15Min" 
    ::=  { currentEthRx15minEntry 6 }

currentEthRx1dayTable OBJECT-TYPE
    SYNTAX      SEQUENCE OF CurrentEthRx1dayEntry
    MAX-ACCESS  not-accessible
    STATUS      current
    DESCRIPTION   ""
    ::=  { performanceMonitoring 53 }

currentEthRx1dayEntry OBJECT-TYPE
    SYNTAX      CurrentEthRx1dayEntry
    MAX-ACCESS  not-accessible
    STATUS      current
    DESCRIPTION   ""
    INDEX       {
                  entityIndex
                }
    ::=  { currentEthRx1dayTable 1 }

CurrentEthRx1dayEntry ::=  SEQUENCE
  { currentEthRx1dayGoodFrames Counter64String,
    currentEthRx1dayPauseFrames Counter64String,
    currentEthRx1dayCrcFrames Counter64String,
    currentEthRx1dayDiscardedFrames Counter64String,
    currentEthRx1dayBytes Counter64String,
    currentEthRx1dayElapsedTime Integer32 }

currentEthRx1dayGoodFrames OBJECT-TYPE
    SYNTAX      Counter64String
    MAX-ACCESS  read-only
    STATUS      current
    DESCRIPTION
        "Frames Received" 
    ::=  { currentEthRx1dayEntry 1 }

currentEthRx1dayPauseFrames OBJECT-TYPE
    SYNTAX      Counter64String
    MAX-ACCESS  read-only
    STATUS      current
    DESCRIPTION
        "Pause Frames Received" 
    ::=  { currentEthRx1dayEntry 2 }

currentEthRx1dayCrcFrames OBJECT-TYPE
    SYNTAX      Counter64String
    MAX-ACCESS  read-only
    STATUS      current
    DESCRIPTION
        "Received CRC Errors" 
    ::=  { currentEthRx1dayEntry 3 }

currentEthRx1dayDiscardedFrames OBJECT-TYPE
    SYNTAX      Counter64String
    MAX-ACCESS  read-only
    STATUS      current
    DESCRIPTION
        "Received Frames Discarded" 
    ::=  { currentEthRx1dayEntry 4 }

currentEthRx1dayBytes OBJECT-TYPE
    SYNTAX      Counter64String
    MAX-ACCESS  read-only
    STATUS      current
    DESCRIPTION
        "Bytes Received" 
    ::=  { currentEthRx1dayEntry 5 }

currentEthRx1dayElapsedTime OBJECT-TYPE
    SYNTAX      Integer32 (0..86400 | -2147483648)
    MAX-ACCESS  read-only
    STATUS      current
    DESCRIPTION
        "Elapsed 1Day" 
    ::=  { currentEthRx1dayEntry 6 }

intervalEthRx15minTable OBJECT-TYPE
    SYNTAX      SEQUENCE OF IntervalEthRx15minEntry
    MAX-ACCESS  not-accessible
    STATUS      current
    DESCRIPTION   ""
    ::=  { performanceMonitoring 54 }

intervalEthRx15minEntry OBJECT-TYPE
    SYNTAX      IntervalEthRx15minEntry
    MAX-ACCESS  not-accessible
    STATUS      current
    DESCRIPTION   ""
    INDEX       {
                  entityIndex,
                  intervalEthRx15minNumber
                }
    ::=  { intervalEthRx15minTable 1 }

IntervalEthRx15minEntry ::=  SEQUENCE
  { intervalEthRx15minNumber Integer32,
    intervalEthRx15minGoodFrames Counter64String,
    intervalEthRx15minPauseFrames Counter64String,
    intervalEthRx15minCrcFrames Counter64String,
    intervalEthRx15minDiscardedFrames Counter64String,
    intervalEthRx15minBytes Counter64String,
    intervalEthRx15minValidFlag TruthValue,
    intervalEthRx15minTimeStamp DateAndTime }

intervalEthRx15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalEthRx15minEntry 1 }

intervalEthRx15minGoodFrames OBJECT-TYPE
    SYNTAX      Counter64String
    MAX-ACCESS  read-only
    STATUS      current
    DESCRIPTION
        "Frames Received" 
    ::=  { intervalEthRx15minEntry 2 }

intervalEthRx15minPauseFrames OBJECT-TYPE
    SYNTAX      Counter64String
    MAX-ACCESS  read-only
    STATUS      current
    DESCRIPTION
        "Pause Frames Received" 
    ::=  { intervalEthRx15minEntry 3 }

intervalEthRx15minCrcFrames OBJECT-TYPE
    SYNTAX      Counter64String
    MAX-ACCESS  read-only
    STATUS      current
    DESCRIPTION
        "Received CRC Errors" 
    ::=  { intervalEthRx15minEntry 4 }

intervalEthRx15minDiscardedFrames OBJECT-TYPE
    SYNTAX      Counter64String
    MAX-ACCESS  read-only
    STATUS      current
    DESCRIPTION
        "Received Frames Discarded" 
    ::=  { intervalEthRx15minEntry 5 }

intervalEthRx15minBytes OBJECT-TYPE
    SYNTAX      Counter64String
    MAX-ACCESS  read-only
    STATUS      current
    DESCRIPTION
        "Bytes Received" 
    ::=  { intervalEthRx15minEntry 6 }

intervalEthRx15minValidFlag OBJECT-TYPE
    SYNTAX      TruthValue
    MAX-ACCESS  read-only
    STATUS      current
    DESCRIPTION
        "Valid Flag" 
    ::=  { intervalEthRx15minEntry 7 }

intervalEthRx15minTimeStamp OBJECT-TYPE
    SYNTAX      DateAndTime
    MAX-ACCESS  read-only
    STATUS      current
    DESCRIPTION
        "Timestamp" 
    ::=  { intervalEthRx15minEntry 8 }

intervalEthRx1dayTable OBJECT-TYPE
    SYNTAX      SEQUENCE OF IntervalEthRx1dayEntry
    MAX-ACCESS  not-accessible
    STATUS      current
    DESCRIPTION   ""
    ::=  { performanceMonitoring 55 }

intervalEthRx1dayEntry OBJECT-TYPE
    SYNTAX      IntervalEthRx1dayEntry
    MAX-ACCESS  not-accessible
    STATUS      current
    DESCRIPTION   ""
    INDEX       {
                  entityIndex,
                  intervalEthRx1dayNumber
                }
    ::=  { intervalEthRx1dayTable 1 }

IntervalEthRx1dayEntry ::=  SEQUENCE
  { intervalEthRx1dayNumber Integer32,
    intervalEthRx1dayGoodFrames Counter64String,
    intervalEthRx1dayPauseFrames Counter64String,
    intervalEthRx1dayCrcFrames Counter64String,
    intervalEthRx1dayDiscardedFrames Counter64String,
    intervalEthRx1dayBytes Counter64String,
    intervalEthRx1dayValidFlag TruthValue,
    intervalEthRx1dayTimeStamp DateAndTime }

intervalEthRx1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalEthRx1dayEntry 1 }

intervalEthRx1dayGoodFrames OBJECT-TYPE
    SYNTAX      Counter64String
    MAX-ACCESS  read-only
    STATUS      current
    DESCRIPTION
        "Frames Received" 
    ::=  { intervalEthRx1dayEntry 2 }

intervalEthRx1dayPauseFrames OBJECT-TYPE
    SYNTAX      Counter64String
    MAX-ACCESS  read-only
    STATUS      current
    DESCRIPTION
        "Pause Frames Received" 
    ::=  { intervalEthRx1dayEntry 3 }

intervalEthRx1dayCrcFrames OBJECT-TYPE
    SYNTAX      Counter64String
    MAX-ACCESS  read-only
    STATUS      current
    DESCRIPTION
        "Received CRC Errors" 
    ::=  { intervalEthRx1dayEntry 4 }

intervalEthRx1dayDiscardedFrames OBJECT-TYPE
    SYNTAX      Counter64String
    MAX-ACCESS  read-only
    STATUS      current
    DESCRIPTION
        "Received Frames Discarded" 
    ::=  { intervalEthRx1dayEntry 5 }

intervalEthRx1dayBytes OBJECT-TYPE
    SYNTAX      Counter64String
    MAX-ACCESS  read-only
    STATUS      current
    DESCRIPTION
        "Bytes Received" 
    ::=  { intervalEthRx1dayEntry 6 }

intervalEthRx1dayValidFlag OBJECT-TYPE
    SYNTAX      TruthValue
    MAX-ACCESS  read-only
    STATUS      current
    DESCRIPTION
        "Valid Flag" 
    ::=  { intervalEthRx1dayEntry 7 }

intervalEthRx1dayTimeStamp OBJECT-TYPE
    SYNTAX      DateAndTime
    MAX-ACCESS  read-only
    STATUS      current
    DESCRIPTION
        "Timestamp" 
    ::=  { intervalEthRx1dayEntry 8 }

currentEthTx15minTable OBJECT-TYPE
    SYNTAX      SEQUENCE OF CurrentEthTx15minEntry
    MAX-ACCESS  not-accessible
    STATUS      current
    DESCRIPTION   ""
    ::=  { performanceMonitoring 56 }

currentEthTx15minEntry OBJECT-TYPE
    SYNTAX      CurrentEthTx15minEntry
    MAX-ACCESS  not-accessible
    STATUS      current
    DESCRIPTION   ""
    INDEX       {
                  entityIndex
                }
    ::=  { currentEthTx15minTable 1 }

CurrentEthTx15minEntry ::=  SEQUENCE
  { currentEthTx15minGoodFramesx Counter64String,
    currentEthTx15minPauseFrames Counter64String,
    currentEthTx15minBytes Counter64String,
    currentEthTx15minCrcFramesEgress Counter64String,
    currentEthTx15minElapsedTime Integer32 }

currentEthTx15minGoodFramesx OBJECT-TYPE
    SYNTAX      Counter64String
    MAX-ACCESS  read-only
    STATUS      current
    DESCRIPTION
        "Frames Transmitted" 
    ::=  { currentEthTx15minEntry 1 }

currentEthTx15minPauseFrames OBJECT-TYPE
    SYNTAX      Counter64String
    MAX-ACCESS  read-only
    STATUS      current
    DESCRIPTION
        "Pause Frames Transmitted" 
    ::=  { currentEthTx15minEntry 2 }

currentEthTx15minBytes OBJECT-TYPE
    SYNTAX      Counter64String
    MAX-ACCESS  read-only
    STATUS      current
    DESCRIPTION
        "Bytes Transmitted" 
    ::=  { currentEthTx15minEntry 3 }

currentEthTx15minCrcFramesEgress OBJECT-TYPE
    SYNTAX      Counter64String
    MAX-ACCESS  read-only
    STATUS      current
    DESCRIPTION
        "Egress CRC Errored Frames" 
    ::=  { currentEthTx15minEntry 4 }

currentEthTx15minElapsedTime OBJECT-TYPE
    SYNTAX      Integer32 (0..9000 | -2147483648)
    MAX-ACCESS  read-only
    STATUS      current
    DESCRIPTION
        "Elapsed 15Min" 
    ::=  { currentEthTx15minEntry 5 }

currentEthTx1dayTable OBJECT-TYPE
    SYNTAX      SEQUENCE OF CurrentEthTx1dayEntry
    MAX-ACCESS  not-accessible
    STATUS      current
    DESCRIPTION   ""
    ::=  { performanceMonitoring 57 }

currentEthTx1dayEntry OBJECT-TYPE
    SYNTAX      CurrentEthTx1dayEntry
    MAX-ACCESS  not-accessible
    STATUS      current
    DESCRIPTION   ""
    INDEX       {
                  entityIndex
                }
    ::=  { currentEthTx1dayTable 1 }

CurrentEthTx1dayEntry ::=  SEQUENCE
  { currentEthTx1dayGoodFramesx Counter64String,
    currentEthTx1dayPauseFrames Counter64String,
    currentEthTx1dayBytes Counter64String,
    currentEthTx1dayCrcFramesEgress Counter64String,
    currentEthTx1dayElapsedTime Integer32 }

currentEthTx1dayGoodFramesx OBJECT-TYPE
    SYNTAX      Counter64String
    MAX-ACCESS  read-only
    STATUS      current
    DESCRIPTION
        "Frames Transmitted" 
    ::=  { currentEthTx1dayEntry 1 }

currentEthTx1dayPauseFrames OBJECT-TYPE
    SYNTAX      Counter64String
    MAX-ACCESS  read-only
    STATUS      current
    DESCRIPTION
        "Pause Frames Transmitted" 
    ::=  { currentEthTx1dayEntry 2 }

currentEthTx1dayBytes OBJECT-TYPE
    SYNTAX      Counter64String
    MAX-ACCESS  read-only
    STATUS      current
    DESCRIPTION
        "Bytes Transmitted" 
    ::=  { currentEthTx1dayEntry 3 }

currentEthTx1dayCrcFramesEgress OBJECT-TYPE
    SYNTAX      Counter64String
    MAX-ACCESS  read-only
    STATUS      current
    DESCRIPTION
        "Egress CRC Errored Frames" 
    ::=  { currentEthTx1dayEntry 4 }

currentEthTx1dayElapsedTime OBJECT-TYPE
    SYNTAX      Integer32 (0..86400 | -2147483648)
    MAX-ACCESS  read-only
    STATUS      current
    DESCRIPTION
        "Elapsed 1Day" 
    ::=  { currentEthTx1dayEntry 5 }

intervalEthTx15minTable OBJECT-TYPE
    SYNTAX      SEQUENCE OF IntervalEthTx15minEntry
    MAX-ACCESS  not-accessible
    STATUS      current
    DESCRIPTION   ""
    ::=  { performanceMonitoring 58 }

intervalEthTx15minEntry OBJECT-TYPE
    SYNTAX      IntervalEthTx15minEntry
    MAX-ACCESS  not-accessible
    STATUS      current
    DESCRIPTION   ""
    INDEX       {
                  entityIndex,
                  intervalEthTx15minNumber
                }
    ::=  { intervalEthTx15minTable 1 }

IntervalEthTx15minEntry ::=  SEQUENCE
  { intervalEthTx15minNumber Integer32,
    intervalEthTx15minGoodFramesx Counter64String,
    intervalEthTx15minPauseFrames Counter64String,
    intervalEthTx15minBytes Counter64String,
    intervalEthTx15minCrcFramesEgress Counter64String,
    intervalEthTx15minValidFlag TruthValue,
    intervalEthTx15minTimeStamp DateAndTime }

intervalEthTx15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalEthTx15minEntry 1 }

intervalEthTx15minGoodFramesx OBJECT-TYPE
    SYNTAX      Counter64String
    MAX-ACCESS  read-only
    STATUS      current
    DESCRIPTION
        "Frames Transmitted" 
    ::=  { intervalEthTx15minEntry 2 }

intervalEthTx15minPauseFrames OBJECT-TYPE
    SYNTAX      Counter64String
    MAX-ACCESS  read-only
    STATUS      current
    DESCRIPTION
        "Pause Frames Transmitted" 
    ::=  { intervalEthTx15minEntry 3 }

intervalEthTx15minBytes OBJECT-TYPE
    SYNTAX      Counter64String
    MAX-ACCESS  read-only
    STATUS      current
    DESCRIPTION
        "Bytes Transmitted" 
    ::=  { intervalEthTx15minEntry 4 }

intervalEthTx15minCrcFramesEgress OBJECT-TYPE
    SYNTAX      Counter64String
    MAX-ACCESS  read-only
    STATUS      current
    DESCRIPTION
        "Egress CRC Errored Frames" 
    ::=  { intervalEthTx15minEntry 5 }

intervalEthTx15minValidFlag OBJECT-TYPE
    SYNTAX      TruthValue
    MAX-ACCESS  read-only
    STATUS      current
    DESCRIPTION
        "Valid Flag" 
    ::=  { intervalEthTx15minEntry 6 }

intervalEthTx15minTimeStamp OBJECT-TYPE
    SYNTAX      DateAndTime
    MAX-ACCESS  read-only
    STATUS      current
    DESCRIPTION
        "Timestamp" 
    ::=  { intervalEthTx15minEntry 7 }

intervalEthTx1dayTable OBJECT-TYPE
    SYNTAX      SEQUENCE OF IntervalEthTx1dayEntry
    MAX-ACCESS  not-accessible
    STATUS      current
    DESCRIPTION   ""
    ::=  { performanceMonitoring 59 }

intervalEthTx1dayEntry OBJECT-TYPE
    SYNTAX      IntervalEthTx1dayEntry
    MAX-ACCESS  not-accessible
    STATUS      current
    DESCRIPTION   ""
    INDEX       {
                  entityIndex,
                  intervalEthTx1dayNumber
                }
    ::=  { intervalEthTx1dayTable 1 }

IntervalEthTx1dayEntry ::=  SEQUENCE
  { intervalEthTx1dayNumber Integer32,
    intervalEthTx1dayGoodFramesx Counter64String,
    intervalEthTx1dayPauseFrames Counter64String,
    intervalEthTx1dayBytes Counter64String,
    intervalEthTx1dayCrcFramesEgress Counter64String,
    intervalEthTx1dayValidFlag TruthValue,
    intervalEthTx1dayTimeStamp DateAndTime }

intervalEthTx1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalEthTx1dayEntry 1 }

intervalEthTx1dayGoodFramesx OBJECT-TYPE
    SYNTAX      Counter64String
    MAX-ACCESS  read-only
    STATUS      current
    DESCRIPTION
        "Frames Transmitted" 
    ::=  { intervalEthTx1dayEntry 2 }

intervalEthTx1dayPauseFrames OBJECT-TYPE
    SYNTAX      Counter64String
    MAX-ACCESS  read-only
    STATUS      current
    DESCRIPTION
        "Pause Frames Transmitted" 
    ::=  { intervalEthTx1dayEntry 3 }

intervalEthTx1dayBytes OBJECT-TYPE
    SYNTAX      Counter64String
    MAX-ACCESS  read-only
    STATUS      current
    DESCRIPTION
        "Bytes Transmitted" 
    ::=  { intervalEthTx1dayEntry 4 }

intervalEthTx1dayCrcFramesEgress OBJECT-TYPE
    SYNTAX      Counter64String
    MAX-ACCESS  read-only
    STATUS      current
    DESCRIPTION
        "Egress CRC Errored Frames" 
    ::=  { intervalEthTx1dayEntry 5 }

intervalEthTx1dayValidFlag OBJECT-TYPE
    SYNTAX      TruthValue
    MAX-ACCESS  read-only
    STATUS      current
    DESCRIPTION
        "Valid Flag" 
    ::=  { intervalEthTx1dayEntry 6 }

intervalEthTx1dayTimeStamp OBJECT-TYPE
    SYNTAX      DateAndTime
    MAX-ACCESS  read-only
    STATUS      current
    DESCRIPTION
        "Timestamp" 
    ::=  { intervalEthTx1dayEntry 7 }

currentGfp15minTable OBJECT-TYPE
    SYNTAX      SEQUENCE OF CurrentGfp15minEntry
    MAX-ACCESS  not-accessible
    STATUS      deprecated
    DESCRIPTION   ""
    ::=  { performanceMonitoring 60 }

currentGfp15minEntry OBJECT-TYPE
    SYNTAX      CurrentGfp15minEntry
    MAX-ACCESS  not-accessible
    STATUS      deprecated
    DESCRIPTION   ""
    INDEX       {
                  entityIndex
                }
    ::=  { currentGfp15minTable 1 }

CurrentGfp15minEntry ::=  SEQUENCE
  { currentGfp15minCoreHecCorrectedFrames Unsigned32,
    currentGfp15minTypeHecCorrectedFrames Unsigned32,
    currentGfp15minTypeHecDiscardedFrames Unsigned32,
    currentGfp15minElapsedTime Integer32 }

currentGfp15minCoreHecCorrectedFrames OBJECT-TYPE
    SYNTAX      Unsigned32
    MAX-ACCESS  read-only
    STATUS      deprecated
    DESCRIPTION
        "Core HEC Corrected Frames" 
    ::=  { currentGfp15minEntry 1 }

currentGfp15minTypeHecCorrectedFrames OBJECT-TYPE
    SYNTAX      Unsigned32
    MAX-ACCESS  read-only
    STATUS      deprecated
    DESCRIPTION
        "Type Field HEC Corrected Frames" 
    ::=  { currentGfp15minEntry 2 }

currentGfp15minTypeHecDiscardedFrames OBJECT-TYPE
    SYNTAX      Unsigned32
    MAX-ACCESS  read-only
    STATUS      deprecated
    DESCRIPTION
        "Type Field HEC Discarded Frames" 
    ::=  { currentGfp15minEntry 3 }

currentGfp15minElapsedTime OBJECT-TYPE
    SYNTAX      Integer32 (0..9000 | -2147483648)
    MAX-ACCESS  read-only
    STATUS      deprecated
    DESCRIPTION
        "Elapsed 15Min" 
    ::=  { currentGfp15minEntry 4 }

currentGfp1dayTable OBJECT-TYPE
    SYNTAX      SEQUENCE OF CurrentGfp1dayEntry
    MAX-ACCESS  not-accessible
    STATUS      deprecated
    DESCRIPTION   ""
    ::=  { performanceMonitoring 61 }

currentGfp1dayEntry OBJECT-TYPE
    SYNTAX      CurrentGfp1dayEntry
    MAX-ACCESS  not-accessible
    STATUS      deprecated
    DESCRIPTION   ""
    INDEX       {
                  entityIndex
                }
    ::=  { currentGfp1dayTable 1 }

CurrentGfp1dayEntry ::=  SEQUENCE
  { currentGfp1dayCoreHecCorrectedFrames Unsigned32,
    currentGfp1dayTypeHecCorrectedFrames Unsigned32,
    currentGfp1dayTypeHecDiscardedFrames Unsigned32,
    currentGfp1dayElapsedTime Integer32 }

currentGfp1dayCoreHecCorrectedFrames OBJECT-TYPE
    SYNTAX      Unsigned32
    MAX-ACCESS  read-only
    STATUS      deprecated
    DESCRIPTION
        "Core HEC Corrected Frames" 
    ::=  { currentGfp1dayEntry 1 }

currentGfp1dayTypeHecCorrectedFrames OBJECT-TYPE
    SYNTAX      Unsigned32
    MAX-ACCESS  read-only
    STATUS      deprecated
    DESCRIPTION
        "Type Field HEC Corrected Frames" 
    ::=  { currentGfp1dayEntry 2 }

currentGfp1dayTypeHecDiscardedFrames OBJECT-TYPE
    SYNTAX      Unsigned32
    MAX-ACCESS  read-only
    STATUS      deprecated
    DESCRIPTION
        "Type Field HEC Discarded Frames" 
    ::=  { currentGfp1dayEntry 3 }

currentGfp1dayElapsedTime OBJECT-TYPE
    SYNTAX      Integer32 (0..86400 | -2147483648)
    MAX-ACCESS  read-only
    STATUS      deprecated
    DESCRIPTION
        "Elapsed 1Day" 
    ::=  { currentGfp1dayEntry 4 }

intervalGfp15minTable OBJECT-TYPE
    SYNTAX      SEQUENCE OF IntervalGfp15minEntry
    MAX-ACCESS  not-accessible
    STATUS      deprecated
    DESCRIPTION   ""
    ::=  { performanceMonitoring 62 }

intervalGfp15minEntry OBJECT-TYPE
    SYNTAX      IntervalGfp15minEntry
    MAX-ACCESS  not-accessible
    STATUS      deprecated
    DESCRIPTION   ""
    INDEX       {
                  entityIndex,
                  intervalGfp15minNumber
                }
    ::=  { intervalGfp15minTable 1 }

IntervalGfp15minEntry ::=  SEQUENCE
  { intervalGfp15minNumber Integer32,
    intervalGfp15minCoreHecCorrectedFrames Unsigned32,
    intervalGfp15minTypeHecCorrectedFrames Unsigned32,
    intervalGfp15minTypeHecDiscardedFrames Unsigned32,
    intervalGfp15minValidFlag TruthValue,
    intervalGfp15minTimeStamp DateAndTime }

intervalGfp15minNumber OBJECT-TYPE
    SYNTAX      Integer32 (1..96)
    MAX-ACCESS  not-accessible
    STATUS      deprecated
    DESCRIPTION
        "A number between 1 and 96, which identifies the interval for
         which the set of statistics is available. The interval
         identified by 1 is the most recently completed 15 minute
         interval, and the interval identified by N is the interval
         immediately preceding the one identified by N-1." 
    ::=  { intervalGfp15minEntry 1 }

intervalGfp15minCoreHecCorrectedFrames OBJECT-TYPE
    SYNTAX      Unsigned32
    MAX-ACCESS  read-only
    STATUS      deprecated
    DESCRIPTION
        "Core HEC Corrected Frames" 
    ::=  { intervalGfp15minEntry 2 }

intervalGfp15minTypeHecCorrectedFrames OBJECT-TYPE
    SYNTAX      Unsigned32
    MAX-ACCESS  read-only
    STATUS      deprecated
    DESCRIPTION
        "Type Field HEC Corrected Frames" 
    ::=  { intervalGfp15minEntry 3 }

intervalGfp15minTypeHecDiscardedFrames OBJECT-TYPE
    SYNTAX      Unsigned32
    MAX-ACCESS  read-only
    STATUS      deprecated
    DESCRIPTION
        "Type Field HEC Discarded Frames" 
    ::=  { intervalGfp15minEntry 4 }

intervalGfp15minValidFlag OBJECT-TYPE
    SYNTAX      TruthValue
    MAX-ACCESS  read-only
    STATUS      deprecated
    DESCRIPTION
        "Valid Flag" 
    ::=  { intervalGfp15minEntry 5 }

intervalGfp15minTimeStamp OBJECT-TYPE
    SYNTAX      DateAndTime
    MAX-ACCESS  read-only
    STATUS      deprecated
    DESCRIPTION
        "Timestamp" 
    ::=  { intervalGfp15minEntry 6 }

intervalGfp1dayTable OBJECT-TYPE
    SYNTAX      SEQUENCE OF IntervalGfp1dayEntry
    MAX-ACCESS  not-accessible
    STATUS      deprecated
    DESCRIPTION   ""
    ::=  { performanceMonitoring 63 }

intervalGfp1dayEntry OBJECT-TYPE
    SYNTAX      IntervalGfp1dayEntry
    MAX-ACCESS  not-accessible
    STATUS      deprecated
    DESCRIPTION   ""
    INDEX       {
                  entityIndex,
                  intervalGfp1dayNumber
                }
    ::=  { intervalGfp1dayTable 1 }

IntervalGfp1dayEntry ::=  SEQUENCE
  { intervalGfp1dayNumber Integer32,
    intervalGfp1dayCoreHecCorrectedFrames Unsigned32,
    intervalGfp1dayTypeHecCorrectedFrames Unsigned32,
    intervalGfp1dayTypeHecDiscardedFrames Unsigned32,
    intervalGfp1dayValidFlag TruthValue,
    intervalGfp1dayTimeStamp DateAndTime }

intervalGfp1dayNumber OBJECT-TYPE
    SYNTAX      Integer32 (1..31)
    MAX-ACCESS  not-accessible
    STATUS      deprecated
    DESCRIPTION
        "A number, which identifies the interval for
         which the set of statistics is available. The interval
         identified by 1 is the most recently completed 1 day
         interval." 
    ::=  { intervalGfp1dayEntry 1 }

intervalGfp1dayCoreHecCorrectedFrames OBJECT-TYPE
    SYNTAX      Unsigned32
    MAX-ACCESS  read-only
    STATUS      deprecated
    DESCRIPTION
        "Core HEC Corrected Frames" 
    ::=  { intervalGfp1dayEntry 2 }

intervalGfp1dayTypeHecCorrectedFrames OBJECT-TYPE
    SYNTAX      Unsigned32
    MAX-ACCESS  read-only
    STATUS      deprecated
    DESCRIPTION
        "Type Field HEC Corrected Frames" 
    ::=  { intervalGfp1dayEntry 3 }

intervalGfp1dayTypeHecDiscardedFrames OBJECT-TYPE
    SYNTAX      Unsigned32
    MAX-ACCESS  read-only
    STATUS      deprecated
    DESCRIPTION
        "Type Field HEC Discarded Frames" 
    ::=  { intervalGfp1dayEntry 4 }

intervalGfp1dayValidFlag OBJECT-TYPE
    SYNTAX      TruthValue
    MAX-ACCESS  read-only
    STATUS      deprecated
    DESCRIPTION
        "Valid Flag" 
    ::=  { intervalGfp1dayEntry 5 }

intervalGfp1dayTimeStamp OBJECT-TYPE
    SYNTAX      DateAndTime
    MAX-ACCESS  read-only
    STATUS      deprecated
    DESCRIPTION
        "Timestamp" 
    ::=  { intervalGfp1dayEntry 6 }

currentOtuFec15minTable OBJECT-TYPE
    SYNTAX      SEQUENCE OF CurrentOtuFec15minEntry
    MAX-ACCESS  not-accessible
    STATUS      current
    DESCRIPTION   ""
    ::=  { performanceMonitoring 68 }

currentOtuFec15minEntry OBJECT-TYPE
    SYNTAX      CurrentOtuFec15minEntry
    MAX-ACCESS  not-accessible
    STATUS      current
    DESCRIPTION   ""
    INDEX       {
                  entityIndex
                }
    ::=  { currentOtuFec15minTable 1 }

CurrentOtuFec15minEntry ::=  SEQUENCE
  { currentOtuFec15minES Unsigned32,
    currentOtuFec15minSES Unsigned32,
    currentOtuFec15minCE Counter64String,
    currentOtuFec15minUBE Counter64String,
    currentOtuFec15minElapsedTime Integer32,
    currentOtuFec15minBERCE Counter64String }

currentOtuFec15minES OBJECT-TYPE
    SYNTAX      Unsigned32
    MAX-ACCESS  read-only
    STATUS      current
    DESCRIPTION
        "OTU FEC Errored Seconds" 
    ::=  { currentOtuFec15minEntry 1 }

currentOtuFec15minSES OBJECT-TYPE
    SYNTAX      Unsigned32
    MAX-ACCESS  read-only
    STATUS      current
    DESCRIPTION
        "OTU FEC Severely Errored Seconds" 
    ::=  { currentOtuFec15minEntry 2 }

currentOtuFec15minCE OBJECT-TYPE
    SYNTAX      Counter64String
    MAX-ACCESS  read-only
    STATUS      current
    DESCRIPTION
        "OTU FEC Corrected Errors" 
    ::=  { currentOtuFec15minEntry 3 }

currentOtuFec15minUBE OBJECT-TYPE
    SYNTAX      Counter64String
    MAX-ACCESS  read-only
    STATUS      current
    DESCRIPTION
        "OTU FEC Uncorrected Block Errors" 
    ::=  { currentOtuFec15minEntry 4 }

currentOtuFec15minElapsedTime OBJECT-TYPE
    SYNTAX      Integer32 (0..9000 | -2147483648)
    MAX-ACCESS  read-only
    STATUS      current
    DESCRIPTION
        "Elapsed 15Min" 
    ::=  { currentOtuFec15minEntry 5 }

currentOtuFec15minBERCE OBJECT-TYPE
    SYNTAX      Counter64String 
    UNITS       "1.0E-18"
    MAX-ACCESS  read-only
    STATUS      current
    DESCRIPTION
        "Bit Error Rate before Foward Error Correction (FEC) calculated from corrected errors" 
    ::=  { currentOtuFec15minEntry 6 }

currentOtuFec1dayTable OBJECT-TYPE
    SYNTAX      SEQUENCE OF CurrentOtuFec1dayEntry
    MAX-ACCESS  not-accessible
    STATUS      current
    DESCRIPTION   ""
    ::=  { performanceMonitoring 69 }

currentOtuFec1dayEntry OBJECT-TYPE
    SYNTAX      CurrentOtuFec1dayEntry
    MAX-ACCESS  not-accessible
    STATUS      current
    DESCRIPTION   ""
    INDEX       {
                  entityIndex
                }
    ::=  { currentOtuFec1dayTable 1 }

CurrentOtuFec1dayEntry ::=  SEQUENCE
  { currentOtuFec1dayES Unsigned32,
    currentOtuFec1daySES Unsigned32,
    currentOtuFec1dayCE Counter64String,
    currentOtuFec1dayUBE Counter64String,
    currentOtuFec1dayElapsedTime Integer32,
    currentOtuFec1dayBERCE Counter64String }

currentOtuFec1dayES OBJECT-TYPE
    SYNTAX      Unsigned32
    MAX-ACCESS  read-only
    STATUS      current
    DESCRIPTION
        "OTU FEC Errored Seconds" 
    ::=  { currentOtuFec1dayEntry 1 }

currentOtuFec1daySES OBJECT-TYPE
    SYNTAX      Unsigned32
    MAX-ACCESS  read-only
    STATUS      current
    DESCRIPTION
        "OTU FEC Severely Errored Seconds" 
    ::=  { currentOtuFec1dayEntry 2 }

currentOtuFec1dayCE OBJECT-TYPE
    SYNTAX      Counter64String
    MAX-ACCESS  read-only
    STATUS      current
    DESCRIPTION
        "OTU FEC Corrected Errors" 
    ::=  { currentOtuFec1dayEntry 3 }

currentOtuFec1dayUBE OBJECT-TYPE
    SYNTAX      Counter64String
    MAX-ACCESS  read-only
    STATUS      current
    DESCRIPTION
        "OTU FEC Uncorrected Block Errors" 
    ::=  { currentOtuFec1dayEntry 4 }

currentOtuFec1dayElapsedTime OBJECT-TYPE
    SYNTAX      Integer32 (0..86400 | -2147483648)
    MAX-ACCESS  read-only
    STATUS      current
    DESCRIPTION
        "Elapsed 1Day" 
    ::=  { currentOtuFec1dayEntry 5 }

currentOtuFec1dayBERCE OBJECT-TYPE
    SYNTAX      Counter64String 
    UNITS       "1.0E-18"
    MAX-ACCESS  read-only
    STATUS      current
    DESCRIPTION
        "Bit Error Rate before Foward Error Correction (FEC) calculated from corrected errors" 
    ::=  { currentOtuFec1dayEntry 6 }

intervalOtuFec15minTable OBJECT-TYPE
    SYNTAX      SEQUENCE OF IntervalOtuFec15minEntry
    MAX-ACCESS  not-accessible
    STATUS      current
    DESCRIPTION   ""
    ::=  { performanceMonitoring 70 }

intervalOtuFec15minEntry OBJECT-TYPE
    SYNTAX      IntervalOtuFec15minEntry
    MAX-ACCESS  not-accessible
    STATUS      current
    DESCRIPTION   ""
    INDEX       {
                  entityIndex,
                  intervalOtuFec15minNumber
                }
    ::=  { intervalOtuFec15minTable 1 }

IntervalOtuFec15minEntry ::=  SEQUENCE
  { intervalOtuFec15minNumber Integer32,
    intervalOtuFec15minES Unsigned32,
    intervalOtuFec15minSES Unsigned32,
    intervalOtuFec15minCE Counter64String,
    intervalOtuFec15minUBE Counter64String,
    intervalOtuFec15minValidFlag TruthValue,
    intervalOtuFec15minTimeStamp DateAndTime,
    intervalOtuFec15minBERCE Counter64String }

intervalOtuFec15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalOtuFec15minEntry 1 }

intervalOtuFec15minES OBJECT-TYPE
    SYNTAX      Unsigned32
    MAX-ACCESS  read-only
    STATUS      current
    DESCRIPTION
        "OTU FEC Errored Seconds" 
    ::=  { intervalOtuFec15minEntry 2 }

intervalOtuFec15minSES OBJECT-TYPE
    SYNTAX      Unsigned32
    MAX-ACCESS  read-only
    STATUS      current
    DESCRIPTION
        "OTU FEC Severely Errored Seconds" 
    ::=  { intervalOtuFec15minEntry 3 }

intervalOtuFec15minCE OBJECT-TYPE
    SYNTAX      Counter64String
    MAX-ACCESS  read-only
    STATUS      current
    DESCRIPTION
        "OTU FEC Corrected Errors" 
    ::=  { intervalOtuFec15minEntry 4 }

intervalOtuFec15minUBE OBJECT-TYPE
    SYNTAX      Counter64String
    MAX-ACCESS  read-only
    STATUS      current
    DESCRIPTION
        "OTU FEC Uncorrected Block Errors" 
    ::=  { intervalOtuFec15minEntry 5 }

intervalOtuFec15minValidFlag OBJECT-TYPE
    SYNTAX      TruthValue
    MAX-ACCESS  read-only
    STATUS      current
    DESCRIPTION
        "Valid Flag" 
    ::=  { intervalOtuFec15minEntry 6 }

intervalOtuFec15minTimeStamp OBJECT-TYPE
    SYNTAX      DateAndTime
    MAX-ACCESS  read-only
    STATUS      current
    DESCRIPTION
        "Timestamp" 
    ::=  { intervalOtuFec15minEntry 7 }

intervalOtuFec15minBERCE OBJECT-TYPE
    SYNTAX      Counter64String 
    UNITS       "1.0E-18"
    MAX-ACCESS  read-only
    STATUS      current
    DESCRIPTION
        "Bit Error Rate before Foward Error Correction (FEC) calculated from corrected errors" 
    ::=  { intervalOtuFec15minEntry 8 }

intervalOtuFec1dayTable OBJECT-TYPE
    SYNTAX      SEQUENCE OF IntervalOtuFec1dayEntry
    MAX-ACCESS  not-accessible
    STATUS      current
    DESCRIPTION   ""
    ::=  { performanceMonitoring 71 }

intervalOtuFec1dayEntry OBJECT-TYPE
    SYNTAX      IntervalOtuFec1dayEntry
    MAX-ACCESS  not-accessible
    STATUS      current
    DESCRIPTION   ""
    INDEX       {
                  entityIndex,
                  intervalOtuFec1dayNumber
                }
    ::=  { intervalOtuFec1dayTable 1 }

IntervalOtuFec1dayEntry ::=  SEQUENCE
  { intervalOtuFec1dayNumber Integer32,
    intervalOtuFec1dayES Unsigned32,
    intervalOtuFec1daySES Unsigned32,
    intervalOtuFec1dayCE Counter64String,
    intervalOtuFec1dayUBE Counter64String,
    intervalOtuFec1dayValidFlag TruthValue,
    intervalOtuFec1dayTimeStamp DateAndTime,
    intervalOtuFec1dayBERCE Counter64String }

intervalOtuFec1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalOtuFec1dayEntry 1 }

intervalOtuFec1dayES OBJECT-TYPE
    SYNTAX      Unsigned32
    MAX-ACCESS  read-only
    STATUS      current
    DESCRIPTION
        "OTU FEC Errored Seconds" 
    ::=  { intervalOtuFec1dayEntry 2 }

intervalOtuFec1daySES OBJECT-TYPE
    SYNTAX      Unsigned32
    MAX-ACCESS  read-only
    STATUS      current
    DESCRIPTION
        "OTU FEC Severely Errored Seconds" 
    ::=  { intervalOtuFec1dayEntry 3 }

intervalOtuFec1dayCE OBJECT-TYPE
    SYNTAX      Counter64String
    MAX-ACCESS  read-only
    STATUS      current
    DESCRIPTION
        "OTU FEC Corrected Errors" 
    ::=  { intervalOtuFec1dayEntry 4 }

intervalOtuFec1dayUBE OBJECT-TYPE
    SYNTAX      Counter64String
    MAX-ACCESS  read-only
    STATUS      current
    DESCRIPTION
        "OTU FEC Uncorrected Block Errors" 
    ::=  { intervalOtuFec1dayEntry 5 }

intervalOtuFec1dayValidFlag OBJECT-TYPE
    SYNTAX      TruthValue
    MAX-ACCESS  read-only
    STATUS      current
    DESCRIPTION
        "Valid Flag" 
    ::=  { intervalOtuFec1dayEntry 6 }

intervalOtuFec1dayTimeStamp OBJECT-TYPE
    SYNTAX      DateAndTime
    MAX-ACCESS  read-only
    STATUS      current
    DESCRIPTION
        "Timestamp" 
    ::=  { intervalOtuFec1dayEntry 7 }

intervalOtuFec1dayBERCE OBJECT-TYPE
    SYNTAX      Counter64String 
    UNITS       "1.0E-18"
    MAX-ACCESS  read-only
    STATUS      current
    DESCRIPTION
        "Bit Error Rate before Foward Error Correction (FEC) calculated from corrected errors" 
    ::=  { intervalOtuFec1dayEntry 8 }

currentGfpt15minTable OBJECT-TYPE
    SYNTAX      SEQUENCE OF CurrentGfpt15minEntry
    MAX-ACCESS  not-accessible
    STATUS      current
    DESCRIPTION   ""
    ::=  { performanceMonitoring 72 }

currentGfpt15minEntry OBJECT-TYPE
    SYNTAX      CurrentGfpt15minEntry
    MAX-ACCESS  not-accessible
    STATUS      current
    DESCRIPTION   ""
    INDEX       {
                  entityIndex
                }
    ::=  { currentGfpt15minTable 1 }

CurrentGfpt15minEntry ::=  SEQUENCE
  { currentGfpt15minDiscardedSuperblocks Unsigned32,
    currentGfpt15minElapsedTime Integer32 }

currentGfpt15minDiscardedSuperblocks OBJECT-TYPE
    SYNTAX      Unsigned32
    MAX-ACCESS  read-only
    STATUS      current
    DESCRIPTION
        "Discarded Super Blocks" 
    ::=  { currentGfpt15minEntry 1 }

currentGfpt15minElapsedTime OBJECT-TYPE
    SYNTAX      Integer32 (0..9000 | -2147483648)
    MAX-ACCESS  read-only
    STATUS      current
    DESCRIPTION
        "Elapsed 15Min" 
    ::=  { currentGfpt15minEntry 2 }

currentGfpt1dayTable OBJECT-TYPE
    SYNTAX      SEQUENCE OF CurrentGfpt1dayEntry
    MAX-ACCESS  not-accessible
    STATUS      current
    DESCRIPTION   ""
    ::=  { performanceMonitoring 73 }

currentGfpt1dayEntry OBJECT-TYPE
    SYNTAX      CurrentGfpt1dayEntry
    MAX-ACCESS  not-accessible
    STATUS      current
    DESCRIPTION   ""
    INDEX       {
                  entityIndex
                }
    ::=  { currentGfpt1dayTable 1 }

CurrentGfpt1dayEntry ::=  SEQUENCE
  { currentGfpt1dayDiscardedSuperblocks Unsigned32,
    currentGfpt1dayElapsedTime Integer32 }

currentGfpt1dayDiscardedSuperblocks OBJECT-TYPE
    SYNTAX      Unsigned32
    MAX-ACCESS  read-only
    STATUS      current
    DESCRIPTION
        "Discarded Super Blocks" 
    ::=  { currentGfpt1dayEntry 1 }

currentGfpt1dayElapsedTime OBJECT-TYPE
    SYNTAX      Integer32 (0..86400 | -2147483648)
    MAX-ACCESS  read-only
    STATUS      current
    DESCRIPTION
        "Elapsed 1Day" 
    ::=  { currentGfpt1dayEntry 2 }

intervalGfpt15minTable OBJECT-TYPE
    SYNTAX      SEQUENCE OF IntervalGfpt15minEntry
    MAX-ACCESS  not-accessible
    STATUS      current
    DESCRIPTION   ""
    ::=  { performanceMonitoring 74 }

intervalGfpt15minEntry OBJECT-TYPE
    SYNTAX      IntervalGfpt15minEntry
    MAX-ACCESS  not-accessible
    STATUS      current
    DESCRIPTION   ""
    INDEX       {
                  entityIndex,
                  intervalGfpt15minNumber
                }
    ::=  { intervalGfpt15minTable 1 }

IntervalGfpt15minEntry ::=  SEQUENCE
  { intervalGfpt15minNumber Integer32,
    intervalGfpt15minDiscardedSuperblocks Unsigned32,
    intervalGfpt15minValidFlag TruthValue,
    intervalGfpt15minTimeStamp DateAndTime }

intervalGfpt15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalGfpt15minEntry 1 }

intervalGfpt15minDiscardedSuperblocks OBJECT-TYPE
    SYNTAX      Unsigned32
    MAX-ACCESS  read-only
    STATUS      current
    DESCRIPTION
        "Discarded Super Blocks" 
    ::=  { intervalGfpt15minEntry 2 }

intervalGfpt15minValidFlag OBJECT-TYPE
    SYNTAX      TruthValue
    MAX-ACCESS  read-only
    STATUS      current
    DESCRIPTION
        "Valid Flag" 
    ::=  { intervalGfpt15minEntry 3 }

intervalGfpt15minTimeStamp OBJECT-TYPE
    SYNTAX      DateAndTime
    MAX-ACCESS  read-only
    STATUS      current
    DESCRIPTION
        "Timestamp" 
    ::=  { intervalGfpt15minEntry 4 }

intervalGfpt1dayTable OBJECT-TYPE
    SYNTAX      SEQUENCE OF IntervalGfpt1dayEntry
    MAX-ACCESS  not-accessible
    STATUS      current
    DESCRIPTION   ""
    ::=  { performanceMonitoring 75 }

intervalGfpt1dayEntry OBJECT-TYPE
    SYNTAX      IntervalGfpt1dayEntry
    MAX-ACCESS  not-accessible
    STATUS      current
    DESCRIPTION   ""
    INDEX       {
                  entityIndex,
                  intervalGfpt1dayNumber
                }
    ::=  { intervalGfpt1dayTable 1 }

IntervalGfpt1dayEntry ::=  SEQUENCE
  { intervalGfpt1dayNumber Integer32,
    intervalGfpt1dayDiscardedSuperblocks Unsigned32,
    intervalGfpt1dayValidFlag TruthValue,
    intervalGfpt1dayTimeStamp DateAndTime }

intervalGfpt1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalGfpt1dayEntry 1 }

intervalGfpt1dayDiscardedSuperblocks OBJECT-TYPE
    SYNTAX      Unsigned32
    MAX-ACCESS  read-only
    STATUS      current
    DESCRIPTION
        "Discarded Super Blocks" 
    ::=  { intervalGfpt1dayEntry 2 }

intervalGfpt1dayValidFlag OBJECT-TYPE
    SYNTAX      TruthValue
    MAX-ACCESS  read-only
    STATUS      current
    DESCRIPTION
        "Valid Flag" 
    ::=  { intervalGfpt1dayEntry 3 }

intervalGfpt1dayTimeStamp OBJECT-TYPE
    SYNTAX      DateAndTime
    MAX-ACCESS  read-only
    STATUS      current
    DESCRIPTION
        "Timestamp" 
    ::=  { intervalGfpt1dayEntry 4 }

currentSubAggregate15minTable OBJECT-TYPE
    SYNTAX      SEQUENCE OF CurrentSubAggregate15minEntry
    MAX-ACCESS  not-accessible
    STATUS      current
    DESCRIPTION   ""
    ::=  { performanceMonitoring 76 }

currentSubAggregate15minEntry OBJECT-TYPE
    SYNTAX      CurrentSubAggregate15minEntry
    MAX-ACCESS  not-accessible
    STATUS      current
    DESCRIPTION   ""
    INDEX       {
                  entityIndex
                }
    ::=  { currentSubAggregate15minTable 1 }

CurrentSubAggregate15minEntry ::=  SEQUENCE
  { currentSubAggregate15minES Unsigned32,
    currentSubAggregate15minSES Unsigned32,
    currentSubAggregate15minElapsedTime Integer32,
    currentSubAggregate15minCrc Unsigned32 }

currentSubAggregate15minES OBJECT-TYPE
    SYNTAX      Unsigned32
    MAX-ACCESS  read-only
    STATUS      current
    DESCRIPTION
        "Multiplexer Errored Seconds" 
    ::=  { currentSubAggregate15minEntry 1 }

currentSubAggregate15minSES OBJECT-TYPE
    SYNTAX      Unsigned32
    MAX-ACCESS  read-only
    STATUS      current
    DESCRIPTION
        "Multiplexer Severely Errored Seconds" 
    ::=  { currentSubAggregate15minEntry 2 }

currentSubAggregate15minElapsedTime OBJECT-TYPE
    SYNTAX      Integer32 (0..9000 | -2147483648)
    MAX-ACCESS  read-only
    STATUS      current
    DESCRIPTION
        "Elapsed 15Min" 
    ::=  { currentSubAggregate15minEntry 3 }

currentSubAggregate15minCrc OBJECT-TYPE
    SYNTAX      Unsigned32
    MAX-ACCESS  read-only
    STATUS      current
    DESCRIPTION
        "Multiplexer Cyclic Redundancy Check Errors" 
    ::=  { currentSubAggregate15minEntry 4 }

currentSubAggregate1dayTable OBJECT-TYPE
    SYNTAX      SEQUENCE OF CurrentSubAggregate1dayEntry
    MAX-ACCESS  not-accessible
    STATUS      current
    DESCRIPTION   ""
    ::=  { performanceMonitoring 77 }

currentSubAggregate1dayEntry OBJECT-TYPE
    SYNTAX      CurrentSubAggregate1dayEntry
    MAX-ACCESS  not-accessible
    STATUS      current
    DESCRIPTION   ""
    INDEX       {
                  entityIndex
                }
    ::=  { currentSubAggregate1dayTable 1 }

CurrentSubAggregate1dayEntry ::=  SEQUENCE
  { currentSubAggregate1dayES Unsigned32,
    currentSubAggregate1daySES Unsigned32,
    currentSubAggregate1dayElapsedTime Integer32,
    currentSubAggregate1dayCrc Unsigned32 }

currentSubAggregate1dayES OBJECT-TYPE
    SYNTAX      Unsigned32
    MAX-ACCESS  read-only
    STATUS      current
    DESCRIPTION
        "Multiplexer Errored Seconds" 
    ::=  { currentSubAggregate1dayEntry 1 }

currentSubAggregate1daySES OBJECT-TYPE
    SYNTAX      Unsigned32
    MAX-ACCESS  read-only
    STATUS      current
    DESCRIPTION
        "Multiplexer Severely Errored Seconds" 
    ::=  { currentSubAggregate1dayEntry 2 }

currentSubAggregate1dayElapsedTime OBJECT-TYPE
    SYNTAX      Integer32 (0..86400 | -2147483648)
    MAX-ACCESS  read-only
    STATUS      current
    DESCRIPTION
        "Elapsed 1Day" 
    ::=  { currentSubAggregate1dayEntry 3 }

currentSubAggregate1dayCrc OBJECT-TYPE
    SYNTAX      Unsigned32
    MAX-ACCESS  read-only
    STATUS      current
    DESCRIPTION
        "Multiplexer Cyclic Redundancy Check Errors" 
    ::=  { currentSubAggregate1dayEntry 4 }

intervalSubAggregate15minTable OBJECT-TYPE
    SYNTAX      SEQUENCE OF IntervalSubAggregate15minEntry
    MAX-ACCESS  not-accessible
    STATUS      current
    DESCRIPTION   ""
    ::=  { performanceMonitoring 78 }

intervalSubAggregate15minEntry OBJECT-TYPE
    SYNTAX      IntervalSubAggregate15minEntry
    MAX-ACCESS  not-accessible
    STATUS      current
    DESCRIPTION   ""
    INDEX       {
                  entityIndex,
                  intervalSubAggregate15minNumber
                }
    ::=  { intervalSubAggregate15minTable 1 }

IntervalSubAggregate15minEntry ::=  SEQUENCE
  { intervalSubAggregate15minNumber Integer32,
    intervalSubAggregate15minES Unsigned32,
    intervalSubAggregate15minSES Unsigned32,
    intervalSubAggregate15minValidFlag TruthValue,
    intervalSubAggregate15minTimeStamp DateAndTime,
    intervalSubAggregate15minCrc Unsigned32 }

intervalSubAggregate15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalSubAggregate15minEntry 1 }

intervalSubAggregate15minES OBJECT-TYPE
    SYNTAX      Unsigned32
    MAX-ACCESS  read-only
    STATUS      current
    DESCRIPTION
        "Multiplexer Errored Seconds" 
    ::=  { intervalSubAggregate15minEntry 2 }

intervalSubAggregate15minSES OBJECT-TYPE
    SYNTAX      Unsigned32
    MAX-ACCESS  read-only
    STATUS      current
    DESCRIPTION
        "Multiplexer Severely Errored Seconds" 
    ::=  { intervalSubAggregate15minEntry 3 }

intervalSubAggregate15minValidFlag OBJECT-TYPE
    SYNTAX      TruthValue
    MAX-ACCESS  read-only
    STATUS      current
    DESCRIPTION
        "Valid Flag" 
    ::=  { intervalSubAggregate15minEntry 4 }

intervalSubAggregate15minTimeStamp OBJECT-TYPE
    SYNTAX      DateAndTime
    MAX-ACCESS  read-only
    STATUS      current
    DESCRIPTION
        "Timestamp" 
    ::=  { intervalSubAggregate15minEntry 5 }

intervalSubAggregate15minCrc OBJECT-TYPE
    SYNTAX      Unsigned32
    MAX-ACCESS  read-only
    STATUS      current
    DESCRIPTION
        "Multiplexer Cyclic Redundancy Check Errors" 
    ::=  { intervalSubAggregate15minEntry 6 }

intervalSubAggregate1dayTable OBJECT-TYPE
    SYNTAX      SEQUENCE OF IntervalSubAggregate1dayEntry
    MAX-ACCESS  not-accessible
    STATUS      current
    DESCRIPTION   ""
    ::=  { performanceMonitoring 79 }

intervalSubAggregate1dayEntry OBJECT-TYPE
    SYNTAX      IntervalSubAggregate1dayEntry
    MAX-ACCESS  not-accessible
    STATUS      current
    DESCRIPTION   ""
    INDEX       {
                  entityIndex,
                  intervalSubAggregate1dayNumber
                }
    ::=  { intervalSubAggregate1dayTable 1 }

IntervalSubAggregate1dayEntry ::=  SEQUENCE
  { intervalSubAggregate1dayNumber Integer32,
    intervalSubAggregate1dayES Unsigned32,
    intervalSubAggregate1daySES Unsigned32,
    intervalSubAggregate1dayValidFlag TruthValue,
    intervalSubAggregate1dayTimeStamp DateAndTime,
    intervalSubAggregate1dayCrc Unsigned32 }

intervalSubAggregate1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalSubAggregate1dayEntry 1 }

intervalSubAggregate1dayES OBJECT-TYPE
    SYNTAX      Unsigned32
    MAX-ACCESS  read-only
    STATUS      current
    DESCRIPTION
        "Multiplexer Errored Seconds" 
    ::=  { intervalSubAggregate1dayEntry 2 }

intervalSubAggregate1daySES OBJECT-TYPE
    SYNTAX      Unsigned32
    MAX-ACCESS  read-only
    STATUS      current
    DESCRIPTION
        "Multiplexer Severely Errored Seconds" 
    ::=  { intervalSubAggregate1dayEntry 3 }

intervalSubAggregate1dayValidFlag OBJECT-TYPE
    SYNTAX      TruthValue
    MAX-ACCESS  read-only
    STATUS      current
    DESCRIPTION
        "Valid Flag" 
    ::=  { intervalSubAggregate1dayEntry 4 }

intervalSubAggregate1dayTimeStamp OBJECT-TYPE
    SYNTAX      DateAndTime
    MAX-ACCESS  read-only
    STATUS      current
    DESCRIPTION
        "Timestamp" 
    ::=  { intervalSubAggregate1dayEntry 5 }

intervalSubAggregate1dayCrc OBJECT-TYPE
    SYNTAX      Unsigned32
    MAX-ACCESS  read-only
    STATUS      current
    DESCRIPTION
        "Multiplexer Cyclic Redundancy Check Errors" 
    ::=  { intervalSubAggregate1dayEntry 6 }

currentOduTcmC15minTable OBJECT-TYPE
    SYNTAX      SEQUENCE OF CurrentOduTcmC15minEntry
    MAX-ACCESS  not-accessible
    STATUS      current
    DESCRIPTION   ""
    ::=  { performanceMonitoring 80 }

currentOduTcmC15minEntry OBJECT-TYPE
    SYNTAX      CurrentOduTcmC15minEntry
    MAX-ACCESS  not-accessible
    STATUS      current
    DESCRIPTION   ""
    INDEX       {
                  entityIndex
                }
    ::=  { currentOduTcmC15minTable 1 }

CurrentOduTcmC15minEntry ::=  SEQUENCE
  { currentOduTcmC15minES Unsigned32,
    currentOduTcmC15minSES Unsigned32,
    currentOduTcmC15minBbe Counter64String,
    currentOduTcmC15minUAS Unsigned32,
    currentOduTcmC15minElapsedTime Integer32 }

currentOduTcmC15minES OBJECT-TYPE
    SYNTAX      Unsigned32
    MAX-ACCESS  read-only
    STATUS      current
    DESCRIPTION
        "ODU Tandem Connection Monitoring C Errored Seconds" 
    ::=  { currentOduTcmC15minEntry 1 }

currentOduTcmC15minSES OBJECT-TYPE
    SYNTAX      Unsigned32
    MAX-ACCESS  read-only
    STATUS      current
    DESCRIPTION
        "ODU Tandem Connection Monitoring C Severely Errored Seconds" 
    ::=  { currentOduTcmC15minEntry 2 }

currentOduTcmC15minBbe OBJECT-TYPE
    SYNTAX      Counter64String
    MAX-ACCESS  read-only
    STATUS      current
    DESCRIPTION
        "ODU Tandem Connection Monitoring C Background Block Errors" 
    ::=  { currentOduTcmC15minEntry 3 }

currentOduTcmC15minUAS OBJECT-TYPE
    SYNTAX      Unsigned32
    MAX-ACCESS  read-only
    STATUS      current
    DESCRIPTION
        "ODU Tandem Connection Monitoring C Unavailable Seconds" 
    ::=  { currentOduTcmC15minEntry 4 }

currentOduTcmC15minElapsedTime OBJECT-TYPE
    SYNTAX      Integer32 (0..9000 | -2147483648)
    MAX-ACCESS  read-only
    STATUS      current
    DESCRIPTION
        "Elapsed 15Min" 
    ::=  { currentOduTcmC15minEntry 5 }

currentOduTcmC1dayTable OBJECT-TYPE
    SYNTAX      SEQUENCE OF CurrentOduTcmC1dayEntry
    MAX-ACCESS  not-accessible
    STATUS      current
    DESCRIPTION   ""
    ::=  { performanceMonitoring 81 }

currentOduTcmC1dayEntry OBJECT-TYPE
    SYNTAX      CurrentOduTcmC1dayEntry
    MAX-ACCESS  not-accessible
    STATUS      current
    DESCRIPTION   ""
    INDEX       {
                  entityIndex
                }
    ::=  { currentOduTcmC1dayTable 1 }

CurrentOduTcmC1dayEntry ::=  SEQUENCE
  { currentOduTcmC1dayES Unsigned32,
    currentOduTcmC1daySES Unsigned32,
    currentOduTcmC1dayBbe Counter64String,
    currentOduTcmC1dayUAS Unsigned32,
    currentOduTcmC1dayElapsedTime Integer32 }

currentOduTcmC1dayES OBJECT-TYPE
    SYNTAX      Unsigned32
    MAX-ACCESS  read-only
    STATUS      current
    DESCRIPTION
        "ODU Tandem Connection Monitoring C Errored Seconds" 
    ::=  { currentOduTcmC1dayEntry 1 }

currentOduTcmC1daySES OBJECT-TYPE
    SYNTAX      Unsigned32
    MAX-ACCESS  read-only
    STATUS      current
    DESCRIPTION
        "ODU Tandem Connection Monitoring C Severely Errored Seconds" 
    ::=  { currentOduTcmC1dayEntry 2 }

currentOduTcmC1dayBbe OBJECT-TYPE
    SYNTAX      Counter64String
    MAX-ACCESS  read-only
    STATUS      current
    DESCRIPTION
        "ODU Tandem Connection Monitoring C Background Block Errors" 
    ::=  { currentOduTcmC1dayEntry 3 }

currentOduTcmC1dayUAS OBJECT-TYPE
    SYNTAX      Unsigned32
    MAX-ACCESS  read-only
    STATUS      current
    DESCRIPTION
        "ODU Tandem Connection Monitoring C Unavailable Seconds" 
    ::=  { currentOduTcmC1dayEntry 4 }

currentOduTcmC1dayElapsedTime OBJECT-TYPE
    SYNTAX      Integer32 (0..86400 | -2147483648)
    MAX-ACCESS  read-only
    STATUS      current
    DESCRIPTION
        "Elapsed 1Day" 
    ::=  { currentOduTcmC1dayEntry 5 }

intervalOduTcmC15minTable OBJECT-TYPE
    SYNTAX      SEQUENCE OF IntervalOduTcmC15minEntry
    MAX-ACCESS  not-accessible
    STATUS      current
    DESCRIPTION   ""
    ::=  { performanceMonitoring 82 }

intervalOduTcmC15minEntry OBJECT-TYPE
    SYNTAX      IntervalOduTcmC15minEntry
    MAX-ACCESS  not-accessible
    STATUS      current
    DESCRIPTION   ""
    INDEX       {
                  entityIndex,
                  intervalOduTcmC15minNumber
                }
    ::=  { intervalOduTcmC15minTable 1 }

IntervalOduTcmC15minEntry ::=  SEQUENCE
  { intervalOduTcmC15minNumber Integer32,
    intervalOduTcmC15minES Unsigned32,
    intervalOduTcmC15minSES Unsigned32,
    intervalOduTcmC15minBbe Counter64String,
    intervalOduTcmC15minUAS Unsigned32,
    intervalOduTcmC15minValidFlag TruthValue,
    intervalOduTcmC15minTimeStamp DateAndTime }

intervalOduTcmC15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalOduTcmC15minEntry 1 }

intervalOduTcmC15minES OBJECT-TYPE
    SYNTAX      Unsigned32
    MAX-ACCESS  read-only
    STATUS      current
    DESCRIPTION
        "ODU Tandem Connection Monitoring C Errored Seconds" 
    ::=  { intervalOduTcmC15minEntry 2 }

intervalOduTcmC15minSES OBJECT-TYPE
    SYNTAX      Unsigned32
    MAX-ACCESS  read-only
    STATUS      current
    DESCRIPTION
        "ODU Tandem Connection Monitoring C Severely Errored Seconds" 
    ::=  { intervalOduTcmC15minEntry 3 }

intervalOduTcmC15minBbe OBJECT-TYPE
    SYNTAX      Counter64String
    MAX-ACCESS  read-only
    STATUS      current
    DESCRIPTION
        "ODU Tandem Connection Monitoring C Background Block Errors" 
    ::=  { intervalOduTcmC15minEntry 4 }

intervalOduTcmC15minUAS OBJECT-TYPE
    SYNTAX      Unsigned32
    MAX-ACCESS  read-only
    STATUS      current
    DESCRIPTION
        "ODU Tandem Connection Monitoring C Unavailable Seconds" 
    ::=  { intervalOduTcmC15minEntry 5 }

intervalOduTcmC15minValidFlag OBJECT-TYPE
    SYNTAX      TruthValue
    MAX-ACCESS  read-only
    STATUS      current
    DESCRIPTION
        "Valid Flag" 
    ::=  { intervalOduTcmC15minEntry 6 }

intervalOduTcmC15minTimeStamp OBJECT-TYPE
    SYNTAX      DateAndTime
    MAX-ACCESS  read-only
    STATUS      current
    DESCRIPTION
        "Timestamp" 
    ::=  { intervalOduTcmC15minEntry 7 }

intervalOduTcmC1dayTable OBJECT-TYPE
    SYNTAX      SEQUENCE OF IntervalOduTcmC1dayEntry
    MAX-ACCESS  not-accessible
    STATUS      current
    DESCRIPTION   ""
    ::=  { performanceMonitoring 83 }

intervalOduTcmC1dayEntry OBJECT-TYPE
    SYNTAX      IntervalOduTcmC1dayEntry
    MAX-ACCESS  not-accessible
    STATUS      current
    DESCRIPTION   ""
    INDEX       {
                  entityIndex,
                  intervalOduTcmC1dayNumber
                }
    ::=  { intervalOduTcmC1dayTable 1 }

IntervalOduTcmC1dayEntry ::=  SEQUENCE
  { intervalOduTcmC1dayNumber Integer32,
    intervalOduTcmC1dayES Unsigned32,
    intervalOduTcmC1daySES Unsigned32,
    intervalOduTcmC1dayBbe Counter64String,
    intervalOduTcmC1dayUAS Unsigned32,
    intervalOduTcmC1dayValidFlag TruthValue,
    intervalOduTcmC1dayTimeStamp DateAndTime }

intervalOduTcmC1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalOduTcmC1dayEntry 1 }

intervalOduTcmC1dayES OBJECT-TYPE
    SYNTAX      Unsigned32
    MAX-ACCESS  read-only
    STATUS      current
    DESCRIPTION
        "ODU Tandem Connection Monitoring C Errored Seconds" 
    ::=  { intervalOduTcmC1dayEntry 2 }

intervalOduTcmC1daySES OBJECT-TYPE
    SYNTAX      Unsigned32
    MAX-ACCESS  read-only
    STATUS      current
    DESCRIPTION
        "ODU Tandem Connection Monitoring C Severely Errored Seconds" 
    ::=  { intervalOduTcmC1dayEntry 3 }

intervalOduTcmC1dayBbe OBJECT-TYPE
    SYNTAX      Counter64String
    MAX-ACCESS  read-only
    STATUS      current
    DESCRIPTION
        "ODU Tandem Connection Monitoring C Background Block Errors" 
    ::=  { intervalOduTcmC1dayEntry 4 }

intervalOduTcmC1dayUAS OBJECT-TYPE
    SYNTAX      Unsigned32
    MAX-ACCESS  read-only
    STATUS      current
    DESCRIPTION
        "ODU Tandem Connection Monitoring C Unavailable Seconds" 
    ::=  { intervalOduTcmC1dayEntry 5 }

intervalOduTcmC1dayValidFlag OBJECT-TYPE
    SYNTAX      TruthValue
    MAX-ACCESS  read-only
    STATUS      current
    DESCRIPTION
        "Valid Flag" 
    ::=  { intervalOduTcmC1dayEntry 6 }

intervalOduTcmC1dayTimeStamp OBJECT-TYPE
    SYNTAX      DateAndTime
    MAX-ACCESS  read-only
    STATUS      current
    DESCRIPTION
        "Timestamp" 
    ::=  { intervalOduTcmC1dayEntry 7 }

currentPhysConvHighSpeed15minTable OBJECT-TYPE
    SYNTAX      SEQUENCE OF CurrentPhysConvHighSpeed15minEntry
    MAX-ACCESS  not-accessible
    STATUS      current
    DESCRIPTION   ""
    ::=  { performanceMonitoring 84 }

currentPhysConvHighSpeed15minEntry OBJECT-TYPE
    SYNTAX      CurrentPhysConvHighSpeed15minEntry
    MAX-ACCESS  not-accessible
    STATUS      current
    DESCRIPTION   ""
    INDEX       {
                  entityIndex
                }
    ::=  { currentPhysConvHighSpeed15minTable 1 }

CurrentPhysConvHighSpeed15minEntry ::=  SEQUENCE
  { currentPhysConvHighSpeed15minES Unsigned32,
    currentPhysConvHighSpeed15minCV Counter64String,
    currentPhysConvHighSpeed15minSE Unsigned32,
    currentPhysConvHighSpeed15minElapsedTime Integer32 }

currentPhysConvHighSpeed15minES OBJECT-TYPE
    SYNTAX      Unsigned32
    MAX-ACCESS  read-only
    STATUS      current
    DESCRIPTION
        "Physical Coding Layer Errored Seconds" 
    ::=  { currentPhysConvHighSpeed15minEntry 1 }

currentPhysConvHighSpeed15minCV OBJECT-TYPE
    SYNTAX      Counter64String
    MAX-ACCESS  read-only
    STATUS      current
    DESCRIPTION
        "Physical Coding Layer Coding Violations" 
    ::=  { currentPhysConvHighSpeed15minEntry 2 }

currentPhysConvHighSpeed15minSE OBJECT-TYPE
    SYNTAX      Unsigned32
    MAX-ACCESS  read-only
    STATUS      current
    DESCRIPTION
        "Sync Header Errors Physical Coding Layer" 
    ::=  { currentPhysConvHighSpeed15minEntry 3 }

currentPhysConvHighSpeed15minElapsedTime OBJECT-TYPE
    SYNTAX      Integer32 (0..9000 | -2147483648)
    MAX-ACCESS  read-only
    STATUS      current
    DESCRIPTION
        "Elapsed 15Min" 
    ::=  { currentPhysConvHighSpeed15minEntry 4 }

currentPhysConvHighSpeed1dayTable OBJECT-TYPE
    SYNTAX      SEQUENCE OF CurrentPhysConvHighSpeed1dayEntry
    MAX-ACCESS  not-accessible
    STATUS      current
    DESCRIPTION   ""
    ::=  { performanceMonitoring 85 }

currentPhysConvHighSpeed1dayEntry OBJECT-TYPE
    SYNTAX      CurrentPhysConvHighSpeed1dayEntry
    MAX-ACCESS  not-accessible
    STATUS      current
    DESCRIPTION   ""
    INDEX       {
                  entityIndex
                }
    ::=  { currentPhysConvHighSpeed1dayTable 1 }

CurrentPhysConvHighSpeed1dayEntry ::=  SEQUENCE
  { currentPhysConvHighSpeed1dayES Unsigned32,
    currentPhysConvHighSpeed1dayCV Counter64String,
    currentPhysConvHighSpeed1daySE Unsigned32,
    currentPhysConvHighSpeed1dayElapsedTime Integer32 }

currentPhysConvHighSpeed1dayES OBJECT-TYPE
    SYNTAX      Unsigned32
    MAX-ACCESS  read-only
    STATUS      current
    DESCRIPTION
        "Physical Coding Layer Errored Seconds" 
    ::=  { currentPhysConvHighSpeed1dayEntry 1 }

currentPhysConvHighSpeed1dayCV OBJECT-TYPE
    SYNTAX      Counter64String
    MAX-ACCESS  read-only
    STATUS      current
    DESCRIPTION
        "Physical Coding Layer Coding Violations" 
    ::=  { currentPhysConvHighSpeed1dayEntry 2 }

currentPhysConvHighSpeed1daySE OBJECT-TYPE
    SYNTAX      Unsigned32
    MAX-ACCESS  read-only
    STATUS      current
    DESCRIPTION
        "Sync Header Errors Physical Coding Layer" 
    ::=  { currentPhysConvHighSpeed1dayEntry 3 }

currentPhysConvHighSpeed1dayElapsedTime OBJECT-TYPE
    SYNTAX      Integer32 (0..86400 | -2147483648)
    MAX-ACCESS  read-only
    STATUS      current
    DESCRIPTION
        "Elapsed 1Day" 
    ::=  { currentPhysConvHighSpeed1dayEntry 4 }

intervalPhysConvHighSpeed15minTable OBJECT-TYPE
    SYNTAX      SEQUENCE OF IntervalPhysConvHighSpeed15minEntry
    MAX-ACCESS  not-accessible
    STATUS      current
    DESCRIPTION   ""
    ::=  { performanceMonitoring 86 }

intervalPhysConvHighSpeed15minEntry OBJECT-TYPE
    SYNTAX      IntervalPhysConvHighSpeed15minEntry
    MAX-ACCESS  not-accessible
    STATUS      current
    DESCRIPTION   ""
    INDEX       {
                  entityIndex,
                  intervalPhysConvHighSpeed15minNumber
                }
    ::=  { intervalPhysConvHighSpeed15minTable 1 }

IntervalPhysConvHighSpeed15minEntry ::=  SEQUENCE
  { intervalPhysConvHighSpeed15minNumber Integer32,
    intervalPhysConvHighSpeed15minES Unsigned32,
    intervalPhysConvHighSpeed15minCV Counter64String,
    intervalPhysConvHighSpeed15minSE Unsigned32,
    intervalPhysConvHighSpeed15minValidFlag TruthValue,
    intervalPhysConvHighSpeed15minTimeStamp DateAndTime }

intervalPhysConvHighSpeed15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysConvHighSpeed15minEntry 1 }

intervalPhysConvHighSpeed15minES OBJECT-TYPE
    SYNTAX      Unsigned32
    MAX-ACCESS  read-only
    STATUS      current
    DESCRIPTION
        "Physical Coding Layer Errored Seconds" 
    ::=  { intervalPhysConvHighSpeed15minEntry 2 }

intervalPhysConvHighSpeed15minCV OBJECT-TYPE
    SYNTAX      Counter64String
    MAX-ACCESS  read-only
    STATUS      current
    DESCRIPTION
        "Physical Coding Layer Coding Violations" 
    ::=  { intervalPhysConvHighSpeed15minEntry 3 }

intervalPhysConvHighSpeed15minSE OBJECT-TYPE
    SYNTAX      Unsigned32
    MAX-ACCESS  read-only
    STATUS      current
    DESCRIPTION
        "Sync Header Errors Physical Coding Layer" 
    ::=  { intervalPhysConvHighSpeed15minEntry 4 }

intervalPhysConvHighSpeed15minValidFlag OBJECT-TYPE
    SYNTAX      TruthValue
    MAX-ACCESS  read-only
    STATUS      current
    DESCRIPTION
        "Valid Flag" 
    ::=  { intervalPhysConvHighSpeed15minEntry 5 }

intervalPhysConvHighSpeed15minTimeStamp OBJECT-TYPE
    SYNTAX      DateAndTime
    MAX-ACCESS  read-only
    STATUS      current
    DESCRIPTION
        "Timestamp" 
    ::=  { intervalPhysConvHighSpeed15minEntry 6 }

intervalPhysConvHighSpeed1dayTable OBJECT-TYPE
    SYNTAX      SEQUENCE OF IntervalPhysConvHighSpeed1dayEntry
    MAX-ACCESS  not-accessible
    STATUS      current
    DESCRIPTION   ""
    ::=  { performanceMonitoring 87 }

intervalPhysConvHighSpeed1dayEntry OBJECT-TYPE
    SYNTAX      IntervalPhysConvHighSpeed1dayEntry
    MAX-ACCESS  not-accessible
    STATUS      current
    DESCRIPTION   ""
    INDEX       {
                  entityIndex,
                  intervalPhysConvHighSpeed1dayNumber
                }
    ::=  { intervalPhysConvHighSpeed1dayTable 1 }

IntervalPhysConvHighSpeed1dayEntry ::=  SEQUENCE
  { intervalPhysConvHighSpeed1dayNumber Integer32,
    intervalPhysConvHighSpeed1dayES Unsigned32,
    intervalPhysConvHighSpeed1dayCV Counter64String,
    intervalPhysConvHighSpeed1daySE Unsigned32,
    intervalPhysConvHighSpeed1dayValidFlag TruthValue,
    intervalPhysConvHighSpeed1dayTimeStamp DateAndTime }

intervalPhysConvHighSpeed1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysConvHighSpeed1dayEntry 1 }

intervalPhysConvHighSpeed1dayES OBJECT-TYPE
    SYNTAX      Unsigned32
    MAX-ACCESS  read-only
    STATUS      current
    DESCRIPTION
        "Physical Coding Layer Errored Seconds" 
    ::=  { intervalPhysConvHighSpeed1dayEntry 2 }

intervalPhysConvHighSpeed1dayCV OBJECT-TYPE
    SYNTAX      Counter64String
    MAX-ACCESS  read-only
    STATUS      current
    DESCRIPTION
        "Physical Coding Layer Coding Violations" 
    ::=  { intervalPhysConvHighSpeed1dayEntry 3 }

intervalPhysConvHighSpeed1daySE OBJECT-TYPE
    SYNTAX      Unsigned32
    MAX-ACCESS  read-only
    STATUS      current
    DESCRIPTION
        "Sync Header Errors Physical Coding Layer" 
    ::=  { intervalPhysConvHighSpeed1dayEntry 4 }

intervalPhysConvHighSpeed1dayValidFlag OBJECT-TYPE
    SYNTAX      TruthValue
    MAX-ACCESS  read-only
    STATUS      current
    DESCRIPTION
        "Valid Flag" 
    ::=  { intervalPhysConvHighSpeed1dayEntry 5 }

intervalPhysConvHighSpeed1dayTimeStamp OBJECT-TYPE
    SYNTAX      DateAndTime
    MAX-ACCESS  read-only
    STATUS      current
    DESCRIPTION
        "Timestamp" 
    ::=  { intervalPhysConvHighSpeed1dayEntry 6 }

currentEthRxHighSpeed15minTable OBJECT-TYPE
    SYNTAX      SEQUENCE OF CurrentEthRxHighSpeed15minEntry
    MAX-ACCESS  not-accessible
    STATUS      current
    DESCRIPTION   ""
    ::=  { performanceMonitoring 88 }

currentEthRxHighSpeed15minEntry OBJECT-TYPE
    SYNTAX      CurrentEthRxHighSpeed15minEntry
    MAX-ACCESS  not-accessible
    STATUS      current
    DESCRIPTION   ""
    INDEX       {
                  entityIndex
                }
    ::=  { currentEthRxHighSpeed15minTable 1 }

CurrentEthRxHighSpeed15minEntry ::=  SEQUENCE
  { currentEthRxHighSpeed15minGoodFrames Counter64String,
    currentEthRxHighSpeed15minPauseFrames Counter64String,
    currentEthRxHighSpeed15minCrcFrames Counter64String,
    currentEthRxHighSpeed15minBytes Counter64String,
    currentEthRxHighSpeed15minElapsedTime Integer32 }

currentEthRxHighSpeed15minGoodFrames OBJECT-TYPE
    SYNTAX      Counter64String
    MAX-ACCESS  read-only
    STATUS      current
    DESCRIPTION
        "Frames Received" 
    ::=  { currentEthRxHighSpeed15minEntry 1 }

currentEthRxHighSpeed15minPauseFrames OBJECT-TYPE
    SYNTAX      Counter64String
    MAX-ACCESS  read-only
    STATUS      current
    DESCRIPTION
        "Pause Frames Received" 
    ::=  { currentEthRxHighSpeed15minEntry 2 }

currentEthRxHighSpeed15minCrcFrames OBJECT-TYPE
    SYNTAX      Counter64String
    MAX-ACCESS  read-only
    STATUS      current
    DESCRIPTION
        "Received CRC Errors" 
    ::=  { currentEthRxHighSpeed15minEntry 3 }

currentEthRxHighSpeed15minBytes OBJECT-TYPE
    SYNTAX      Counter64String
    MAX-ACCESS  read-only
    STATUS      current
    DESCRIPTION
        "Bytes Received" 
    ::=  { currentEthRxHighSpeed15minEntry 4 }

currentEthRxHighSpeed15minElapsedTime OBJECT-TYPE
    SYNTAX      Integer32 (0..9000 | -2147483648)
    MAX-ACCESS  read-only
    STATUS      current
    DESCRIPTION
        "Elapsed 15Min" 
    ::=  { currentEthRxHighSpeed15minEntry 5 }

currentEthRxHighSpeed1dayTable OBJECT-TYPE
    SYNTAX      SEQUENCE OF CurrentEthRxHighSpeed1dayEntry
    MAX-ACCESS  not-accessible
    STATUS      current
    DESCRIPTION   ""
    ::=  { performanceMonitoring 89 }

currentEthRxHighSpeed1dayEntry OBJECT-TYPE
    SYNTAX      CurrentEthRxHighSpeed1dayEntry
    MAX-ACCESS  not-accessible
    STATUS      current
    DESCRIPTION   ""
    INDEX       {
                  entityIndex
                }
    ::=  { currentEthRxHighSpeed1dayTable 1 }

CurrentEthRxHighSpeed1dayEntry ::=  SEQUENCE
  { currentEthRxHighSpeed1dayGoodFrames Counter64String,
    currentEthRxHighSpeed1dayPauseFrames Counter64String,
    currentEthRxHighSpeed1dayCrcFrames Counter64String,
    currentEthRxHighSpeed1dayBytes Counter64String,
    currentEthRxHighSpeed1dayElapsedTime Integer32 }

currentEthRxHighSpeed1dayGoodFrames OBJECT-TYPE
    SYNTAX      Counter64String
    MAX-ACCESS  read-only
    STATUS      current
    DESCRIPTION
        "Frames Received" 
    ::=  { currentEthRxHighSpeed1dayEntry 1 }

currentEthRxHighSpeed1dayPauseFrames OBJECT-TYPE
    SYNTAX      Counter64String
    MAX-ACCESS  read-only
    STATUS      current
    DESCRIPTION
        "Pause Frames Received" 
    ::=  { currentEthRxHighSpeed1dayEntry 2 }

currentEthRxHighSpeed1dayCrcFrames OBJECT-TYPE
    SYNTAX      Counter64String
    MAX-ACCESS  read-only
    STATUS      current
    DESCRIPTION
        "Received CRC Errors" 
    ::=  { currentEthRxHighSpeed1dayEntry 3 }

currentEthRxHighSpeed1dayBytes OBJECT-TYPE
    SYNTAX      Counter64String
    MAX-ACCESS  read-only
    STATUS      current
    DESCRIPTION
        "Bytes Received" 
    ::=  { currentEthRxHighSpeed1dayEntry 4 }

currentEthRxHighSpeed1dayElapsedTime OBJECT-TYPE
    SYNTAX      Integer32 (0..86400 | -2147483648)
    MAX-ACCESS  read-only
    STATUS      current
    DESCRIPTION
        "Elapsed 1Day" 
    ::=  { currentEthRxHighSpeed1dayEntry 5 }

intervalEthRxHighSpeed15minTable OBJECT-TYPE
    SYNTAX      SEQUENCE OF IntervalEthRxHighSpeed15minEntry
    MAX-ACCESS  not-accessible
    STATUS      current
    DESCRIPTION   ""
    ::=  { performanceMonitoring 90 }

intervalEthRxHighSpeed15minEntry OBJECT-TYPE
    SYNTAX      IntervalEthRxHighSpeed15minEntry
    MAX-ACCESS  not-accessible
    STATUS      current
    DESCRIPTION   ""
    INDEX       {
                  entityIndex,
                  intervalEthRxHighSpeed15minNumber
                }
    ::=  { intervalEthRxHighSpeed15minTable 1 }

IntervalEthRxHighSpeed15minEntry ::=  SEQUENCE
  { intervalEthRxHighSpeed15minNumber Integer32,
    intervalEthRxHighSpeed15minGoodFrames Counter64String,
    intervalEthRxHighSpeed15minPauseFrames Counter64String,
    intervalEthRxHighSpeed15minCrcFrames Counter64String,
    intervalEthRxHighSpeed15minBytes Counter64String,
    intervalEthRxHighSpeed15minValidFlag TruthValue,
    intervalEthRxHighSpeed15minTimeStamp DateAndTime }

intervalEthRxHighSpeed15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalEthRxHighSpeed15minEntry 1 }

intervalEthRxHighSpeed15minGoodFrames OBJECT-TYPE
    SYNTAX      Counter64String
    MAX-ACCESS  read-only
    STATUS      current
    DESCRIPTION
        "Frames Received" 
    ::=  { intervalEthRxHighSpeed15minEntry 2 }

intervalEthRxHighSpeed15minPauseFrames OBJECT-TYPE
    SYNTAX      Counter64String
    MAX-ACCESS  read-only
    STATUS      current
    DESCRIPTION
        "Pause Frames Received" 
    ::=  { intervalEthRxHighSpeed15minEntry 3 }

intervalEthRxHighSpeed15minCrcFrames OBJECT-TYPE
    SYNTAX      Counter64String
    MAX-ACCESS  read-only
    STATUS      current
    DESCRIPTION
        "Received CRC Errors" 
    ::=  { intervalEthRxHighSpeed15minEntry 4 }

intervalEthRxHighSpeed15minBytes OBJECT-TYPE
    SYNTAX      Counter64String
    MAX-ACCESS  read-only
    STATUS      current
    DESCRIPTION
        "Bytes Received" 
    ::=  { intervalEthRxHighSpeed15minEntry 5 }

intervalEthRxHighSpeed15minValidFlag OBJECT-TYPE
    SYNTAX      TruthValue
    MAX-ACCESS  read-only
    STATUS      current
    DESCRIPTION
        "Valid Flag" 
    ::=  { intervalEthRxHighSpeed15minEntry 6 }

intervalEthRxHighSpeed15minTimeStamp OBJECT-TYPE
    SYNTAX      DateAndTime
    MAX-ACCESS  read-only
    STATUS      current
    DESCRIPTION
        "Timestamp" 
    ::=  { intervalEthRxHighSpeed15minEntry 7 }

intervalEthRxHighSpeed1dayTable OBJECT-TYPE
    SYNTAX      SEQUENCE OF IntervalEthRxHighSpeed1dayEntry
    MAX-ACCESS  not-accessible
    STATUS      current
    DESCRIPTION   ""
    ::=  { performanceMonitoring 91 }

intervalEthRxHighSpeed1dayEntry OBJECT-TYPE
    SYNTAX      IntervalEthRxHighSpeed1dayEntry
    MAX-ACCESS  not-accessible
    STATUS      current
    DESCRIPTION   ""
    INDEX       {
                  entityIndex,
                  intervalEthRxHighSpeed1dayNumber
                }
    ::=  { intervalEthRxHighSpeed1dayTable 1 }

IntervalEthRxHighSpeed1dayEntry ::=  SEQUENCE
  { intervalEthRxHighSpeed1dayNumber Integer32,
    intervalEthRxHighSpeed1dayGoodFrames Counter64String,
    intervalEthRxHighSpeed1dayPauseFrames Counter64String,
    intervalEthRxHighSpeed1dayCrcFrames Counter64String,
    intervalEthRxHighSpeed1dayBytes Counter64String,
    intervalEthRxHighSpeed1dayValidFlag TruthValue,
    intervalEthRxHighSpeed1dayTimeStamp DateAndTime }

intervalEthRxHighSpeed1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalEthRxHighSpeed1dayEntry 1 }

intervalEthRxHighSpeed1dayGoodFrames OBJECT-TYPE
    SYNTAX      Counter64String
    MAX-ACCESS  read-only
    STATUS      current
    DESCRIPTION
        "Frames Received" 
    ::=  { intervalEthRxHighSpeed1dayEntry 2 }

intervalEthRxHighSpeed1dayPauseFrames OBJECT-TYPE
    SYNTAX      Counter64String
    MAX-ACCESS  read-only
    STATUS      current
    DESCRIPTION
        "Pause Frames Received" 
    ::=  { intervalEthRxHighSpeed1dayEntry 3 }

intervalEthRxHighSpeed1dayCrcFrames OBJECT-TYPE
    SYNTAX      Counter64String
    MAX-ACCESS  read-only
    STATUS      current
    DESCRIPTION
        "Received CRC Errors" 
    ::=  { intervalEthRxHighSpeed1dayEntry 4 }

intervalEthRxHighSpeed1dayBytes OBJECT-TYPE
    SYNTAX      Counter64String
    MAX-ACCESS  read-only
    STATUS      current
    DESCRIPTION
        "Bytes Received" 
    ::=  { intervalEthRxHighSpeed1dayEntry 5 }

intervalEthRxHighSpeed1dayValidFlag OBJECT-TYPE
    SYNTAX      TruthValue
    MAX-ACCESS  read-only
    STATUS      current
    DESCRIPTION
        "Valid Flag" 
    ::=  { intervalEthRxHighSpeed1dayEntry 6 }

intervalEthRxHighSpeed1dayTimeStamp OBJECT-TYPE
    SYNTAX      DateAndTime
    MAX-ACCESS  read-only
    STATUS      current
    DESCRIPTION
        "Timestamp" 
    ::=  { intervalEthRxHighSpeed1dayEntry 7 }

currentGfpfr15minTable OBJECT-TYPE
    SYNTAX      SEQUENCE OF CurrentGfpfr15minEntry
    MAX-ACCESS  not-accessible
    STATUS      deprecated
    DESCRIPTION   ""
    ::=  { performanceMonitoring 92 }

currentGfpfr15minEntry OBJECT-TYPE
    SYNTAX      CurrentGfpfr15minEntry
    MAX-ACCESS  not-accessible
    STATUS      deprecated
    DESCRIPTION   ""
    INDEX       {
                  entityIndex
                }
    ::=  { currentGfpfr15minTable 1 }

CurrentGfpfr15minEntry ::=  SEQUENCE
  { currentGfpfr15minGoodFrames Unsigned32,
    currentGfpfr15minCHecDiscardedFrames Unsigned32,
    currentGfpfr15minTHecDiscardedFrames Unsigned32,
    currentGfpfr15minElapsedTime Integer32 }

currentGfpfr15minGoodFrames OBJECT-TYPE
    SYNTAX      Unsigned32
    MAX-ACCESS  read-only
    STATUS      deprecated
    DESCRIPTION
        "GFP Good Frames" 
    ::=  { currentGfpfr15minEntry 1 }

currentGfpfr15minCHecDiscardedFrames OBJECT-TYPE
    SYNTAX      Unsigned32
    MAX-ACCESS  read-only
    STATUS      deprecated
    DESCRIPTION
        "Core Hec Discarded Frames" 
    ::=  { currentGfpfr15minEntry 2 }

currentGfpfr15minTHecDiscardedFrames OBJECT-TYPE
    SYNTAX      Unsigned32
    MAX-ACCESS  read-only
    STATUS      deprecated
    DESCRIPTION
        "Type Field HEC Discarded Frames" 
    ::=  { currentGfpfr15minEntry 3 }

currentGfpfr15minElapsedTime OBJECT-TYPE
    SYNTAX      Integer32 (0..9000 | -2147483648)
    MAX-ACCESS  read-only
    STATUS      deprecated
    DESCRIPTION
        "Elapsed 15Min" 
    ::=  { currentGfpfr15minEntry 4 }

currentGfpfr1dayTable OBJECT-TYPE
    SYNTAX      SEQUENCE OF CurrentGfpfr1dayEntry
    MAX-ACCESS  not-accessible
    STATUS      deprecated
    DESCRIPTION   ""
    ::=  { performanceMonitoring 93 }

currentGfpfr1dayEntry OBJECT-TYPE
    SYNTAX      CurrentGfpfr1dayEntry
    MAX-ACCESS  not-accessible
    STATUS      deprecated
    DESCRIPTION   ""
    INDEX       {
                  entityIndex
                }
    ::=  { currentGfpfr1dayTable 1 }

CurrentGfpfr1dayEntry ::=  SEQUENCE
  { currentGfpfr1dayGoodFrames Unsigned32,
    currentGfpfr1dayCHecDiscardedFrames Unsigned32,
    currentGfpfr1dayTHecDiscardedFrames Unsigned32,
    currentGfpfr1dayElapsedTime Integer32 }

currentGfpfr1dayGoodFrames OBJECT-TYPE
    SYNTAX      Unsigned32
    MAX-ACCESS  read-only
    STATUS      deprecated
    DESCRIPTION
        "GFP Good Frames" 
    ::=  { currentGfpfr1dayEntry 1 }

currentGfpfr1dayCHecDiscardedFrames OBJECT-TYPE
    SYNTAX      Unsigned32
    MAX-ACCESS  read-only
    STATUS      deprecated
    DESCRIPTION
        "Core Hec Discarded Frames" 
    ::=  { currentGfpfr1dayEntry 2 }

currentGfpfr1dayTHecDiscardedFrames OBJECT-TYPE
    SYNTAX      Unsigned32
    MAX-ACCESS  read-only
    STATUS      deprecated
    DESCRIPTION
        "Type Field HEC Discarded Frames" 
    ::=  { currentGfpfr1dayEntry 3 }

currentGfpfr1dayElapsedTime OBJECT-TYPE
    SYNTAX      Integer32 (0..86400 | -2147483648)
    MAX-ACCESS  read-only
    STATUS      deprecated
    DESCRIPTION
        "Elapsed 1Day" 
    ::=  { currentGfpfr1dayEntry 4 }

intervalGfpfr15minTable OBJECT-TYPE
    SYNTAX      SEQUENCE OF IntervalGfpfr15minEntry
    MAX-ACCESS  not-accessible
    STATUS      deprecated
    DESCRIPTION   ""
    ::=  { performanceMonitoring 94 }

intervalGfpfr15minEntry OBJECT-TYPE
    SYNTAX      IntervalGfpfr15minEntry
    MAX-ACCESS  not-accessible
    STATUS      deprecated
    DESCRIPTION   ""
    INDEX       {
                  entityIndex,
                  intervalGfpfr15minNumber
                }
    ::=  { intervalGfpfr15minTable 1 }

IntervalGfpfr15minEntry ::=  SEQUENCE
  { intervalGfpfr15minNumber Integer32,
    intervalGfpfr15minGoodFrames Unsigned32,
    intervalGfpfr15minCHecDiscardedFrames Unsigned32,
    intervalGfpfr15minTHecDiscardedFrames Unsigned32,
    intervalGfpfr15minValidFlag TruthValue,
    intervalGfpfr15minTimeStamp DateAndTime }

intervalGfpfr15minNumber OBJECT-TYPE
    SYNTAX      Integer32 (1..96)
    MAX-ACCESS  not-accessible
    STATUS      deprecated
    DESCRIPTION
        "A number between 1 and 96, which identifies the interval for
         which the set of statistics is available. The interval
         identified by 1 is the most recently completed 15 minute
         interval, and the interval identified by N is the interval
         immediately preceding the one identified by N-1." 
    ::=  { intervalGfpfr15minEntry 1 }

intervalGfpfr15minGoodFrames OBJECT-TYPE
    SYNTAX      Unsigned32
    MAX-ACCESS  read-only
    STATUS      deprecated
    DESCRIPTION
        "GFP Good Frames" 
    ::=  { intervalGfpfr15minEntry 2 }

intervalGfpfr15minCHecDiscardedFrames OBJECT-TYPE
    SYNTAX      Unsigned32
    MAX-ACCESS  read-only
    STATUS      deprecated
    DESCRIPTION
        "Core Hec Discarded Frames" 
    ::=  { intervalGfpfr15minEntry 3 }

intervalGfpfr15minTHecDiscardedFrames OBJECT-TYPE
    SYNTAX      Unsigned32
    MAX-ACCESS  read-only
    STATUS      deprecated
    DESCRIPTION
        "Type Field HEC Discarded Frames" 
    ::=  { intervalGfpfr15minEntry 4 }

intervalGfpfr15minValidFlag OBJECT-TYPE
    SYNTAX      TruthValue
    MAX-ACCESS  read-only
    STATUS      deprecated
    DESCRIPTION
        "Valid Flag" 
    ::=  { intervalGfpfr15minEntry 5 }

intervalGfpfr15minTimeStamp OBJECT-TYPE
    SYNTAX      DateAndTime
    MAX-ACCESS  read-only
    STATUS      deprecated
    DESCRIPTION
        "Timestamp" 
    ::=  { intervalGfpfr15minEntry 6 }

intervalGfpfr1dayTable OBJECT-TYPE
    SYNTAX      SEQUENCE OF IntervalGfpfr1dayEntry
    MAX-ACCESS  not-accessible
    STATUS      deprecated
    DESCRIPTION   ""
    ::=  { performanceMonitoring 95 }

intervalGfpfr1dayEntry OBJECT-TYPE
    SYNTAX      IntervalGfpfr1dayEntry
    MAX-ACCESS  not-accessible
    STATUS      deprecated
    DESCRIPTION   ""
    INDEX       {
                  entityIndex,
                  intervalGfpfr1dayNumber
                }
    ::=  { intervalGfpfr1dayTable 1 }

IntervalGfpfr1dayEntry ::=  SEQUENCE
  { intervalGfpfr1dayNumber Integer32,
    intervalGfpfr1dayGoodFrames Unsigned32,
    intervalGfpfr1dayCHecDiscardedFrames Unsigned32,
    intervalGfpfr1dayTHecDiscardedFrames Unsigned32,
    intervalGfpfr1dayValidFlag TruthValue,
    intervalGfpfr1dayTimeStamp DateAndTime }

intervalGfpfr1dayNumber OBJECT-TYPE
    SYNTAX      Integer32 (1..31)
    MAX-ACCESS  not-accessible
    STATUS      deprecated
    DESCRIPTION
        "A number, which identifies the interval for
         which the set of statistics is available. The interval
         identified by 1 is the most recently completed 1 day
         interval." 
    ::=  { intervalGfpfr1dayEntry 1 }

intervalGfpfr1dayGoodFrames OBJECT-TYPE
    SYNTAX      Unsigned32
    MAX-ACCESS  read-only
    STATUS      deprecated
    DESCRIPTION
        "GFP Good Frames" 
    ::=  { intervalGfpfr1dayEntry 2 }

intervalGfpfr1dayCHecDiscardedFrames OBJECT-TYPE
    SYNTAX      Unsigned32
    MAX-ACCESS  read-only
    STATUS      deprecated
    DESCRIPTION
        "Core Hec Discarded Frames" 
    ::=  { intervalGfpfr1dayEntry 3 }

intervalGfpfr1dayTHecDiscardedFrames OBJECT-TYPE
    SYNTAX      Unsigned32
    MAX-ACCESS  read-only
    STATUS      deprecated
    DESCRIPTION
        "Type Field HEC Discarded Frames" 
    ::=  { intervalGfpfr1dayEntry 4 }

intervalGfpfr1dayValidFlag OBJECT-TYPE
    SYNTAX      TruthValue
    MAX-ACCESS  read-only
    STATUS      deprecated
    DESCRIPTION
        "Valid Flag" 
    ::=  { intervalGfpfr1dayEntry 5 }

intervalGfpfr1dayTimeStamp OBJECT-TYPE
    SYNTAX      DateAndTime
    MAX-ACCESS  read-only
    STATUS      deprecated
    DESCRIPTION
        "Timestamp" 
    ::=  { intervalGfpfr1dayEntry 6 }

currentGfpSublayer15minTable OBJECT-TYPE
    SYNTAX      SEQUENCE OF CurrentGfpSublayer15minEntry
    MAX-ACCESS  not-accessible
    STATUS      current
    DESCRIPTION   ""
    ::=  { performanceMonitoring 96 }

currentGfpSublayer15minEntry OBJECT-TYPE
    SYNTAX      CurrentGfpSublayer15minEntry
    MAX-ACCESS  not-accessible
    STATUS      current
    DESCRIPTION   ""
    INDEX       {
                  entityIndex
                }
    ::=  { currentGfpSublayer15minTable 1 }

CurrentGfpSublayer15minEntry ::=  SEQUENCE
  { currentGfpSublayer15minCoreHecCorrectedFrames Unsigned32,
    currentGfpSublayer15minTypeHecCorrectedFrames Unsigned32,
    currentGfpSublayer15minTypeHecDiscardedFrames Counter64String,
    currentGfpSublayer15minElapsedTime Integer32 }

currentGfpSublayer15minCoreHecCorrectedFrames OBJECT-TYPE
    SYNTAX      Unsigned32
    MAX-ACCESS  read-only
    STATUS      current
    DESCRIPTION
        "Core HEC Corrected Frames" 
    ::=  { currentGfpSublayer15minEntry 1 }

currentGfpSublayer15minTypeHecCorrectedFrames OBJECT-TYPE
    SYNTAX      Unsigned32
    MAX-ACCESS  read-only
    STATUS      current
    DESCRIPTION
        "Type Field HEC Corrected Frames" 
    ::=  { currentGfpSublayer15minEntry 2 }

currentGfpSublayer15minTypeHecDiscardedFrames OBJECT-TYPE
    SYNTAX      Counter64String
    MAX-ACCESS  read-only
    STATUS      current
    DESCRIPTION
        "Type Field HEC Discarded Frames" 
    ::=  { currentGfpSublayer15minEntry 3 }

currentGfpSublayer15minElapsedTime OBJECT-TYPE
    SYNTAX      Integer32 (0..9000 | -2147483648)
    MAX-ACCESS  read-only
    STATUS      current
    DESCRIPTION
        "Elapsed 15Min" 
    ::=  { currentGfpSublayer15minEntry 4 }

currentGfpSublayer1dayTable OBJECT-TYPE
    SYNTAX      SEQUENCE OF CurrentGfpSublayer1dayEntry
    MAX-ACCESS  not-accessible
    STATUS      current
    DESCRIPTION   ""
    ::=  { performanceMonitoring 97 }

currentGfpSublayer1dayEntry OBJECT-TYPE
    SYNTAX      CurrentGfpSublayer1dayEntry
    MAX-ACCESS  not-accessible
    STATUS      current
    DESCRIPTION   ""
    INDEX       {
                  entityIndex
                }
    ::=  { currentGfpSublayer1dayTable 1 }

CurrentGfpSublayer1dayEntry ::=  SEQUENCE
  { currentGfpSublayer1dayCoreHecCorrectedFrames Unsigned32,
    currentGfpSublayer1dayTypeHecCorrectedFrames Unsigned32,
    currentGfpSublayer1dayTypeHecDiscardedFrames Counter64String,
    currentGfpSublayer1dayElapsedTime Integer32 }

currentGfpSublayer1dayCoreHecCorrectedFrames OBJECT-TYPE
    SYNTAX      Unsigned32
    MAX-ACCESS  read-only
    STATUS      current
    DESCRIPTION
        "Core HEC Corrected Frames" 
    ::=  { currentGfpSublayer1dayEntry 1 }

currentGfpSublayer1dayTypeHecCorrectedFrames OBJECT-TYPE
    SYNTAX      Unsigned32
    MAX-ACCESS  read-only
    STATUS      current
    DESCRIPTION
        "Type Field HEC Corrected Frames" 
    ::=  { currentGfpSublayer1dayEntry 2 }

currentGfpSublayer1dayTypeHecDiscardedFrames OBJECT-TYPE
    SYNTAX      Counter64String
    MAX-ACCESS  read-only
    STATUS      current
    DESCRIPTION
        "Type Field HEC Discarded Frames" 
    ::=  { currentGfpSublayer1dayEntry 3 }

currentGfpSublayer1dayElapsedTime OBJECT-TYPE
    SYNTAX      Integer32 (0..86400 | -2147483648)
    MAX-ACCESS  read-only
    STATUS      current
    DESCRIPTION
        "Elapsed 1Day" 
    ::=  { currentGfpSublayer1dayEntry 4 }

intervalGfpSublayer15minTable OBJECT-TYPE
    SYNTAX      SEQUENCE OF IntervalGfpSublayer15minEntry
    MAX-ACCESS  not-accessible
    STATUS      current
    DESCRIPTION   ""
    ::=  { performanceMonitoring 98 }

intervalGfpSublayer15minEntry OBJECT-TYPE
    SYNTAX      IntervalGfpSublayer15minEntry
    MAX-ACCESS  not-accessible
    STATUS      current
    DESCRIPTION   ""
    INDEX       {
                  entityIndex,
                  intervalGfpSublayer15minNumber
                }
    ::=  { intervalGfpSublayer15minTable 1 }

IntervalGfpSublayer15minEntry ::=  SEQUENCE
  { intervalGfpSublayer15minNumber Integer32,
    intervalGfpSublayer15minCoreHecCorrectedFrames Unsigned32,
    intervalGfpSublayer15minTypeHecCorrectedFrames Unsigned32,
    intervalGfpSublayer15minTypeHecDiscardedFrames Counter64String,
    intervalGfpSublayer15minValidFlag TruthValue,
    intervalGfpSublayer15minTimeStamp DateAndTime }

intervalGfpSublayer15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalGfpSublayer15minEntry 1 }

intervalGfpSublayer15minCoreHecCorrectedFrames OBJECT-TYPE
    SYNTAX      Unsigned32
    MAX-ACCESS  read-only
    STATUS      current
    DESCRIPTION
        "Core HEC Corrected Frames" 
    ::=  { intervalGfpSublayer15minEntry 2 }

intervalGfpSublayer15minTypeHecCorrectedFrames OBJECT-TYPE
    SYNTAX      Unsigned32
    MAX-ACCESS  read-only
    STATUS      current
    DESCRIPTION
        "Type Field HEC Corrected Frames" 
    ::=  { intervalGfpSublayer15minEntry 3 }

intervalGfpSublayer15minTypeHecDiscardedFrames OBJECT-TYPE
    SYNTAX      Counter64String
    MAX-ACCESS  read-only
    STATUS      current
    DESCRIPTION
        "Type Field HEC Discarded Frames" 
    ::=  { intervalGfpSublayer15minEntry 4 }

intervalGfpSublayer15minValidFlag OBJECT-TYPE
    SYNTAX      TruthValue
    MAX-ACCESS  read-only
    STATUS      current
    DESCRIPTION
        "Valid Flag" 
    ::=  { intervalGfpSublayer15minEntry 5 }

intervalGfpSublayer15minTimeStamp OBJECT-TYPE
    SYNTAX      DateAndTime
    MAX-ACCESS  read-only
    STATUS      current
    DESCRIPTION
        "Timestamp" 
    ::=  { intervalGfpSublayer15minEntry 6 }

intervalGfpSublayer1dayTable OBJECT-TYPE
    SYNTAX      SEQUENCE OF IntervalGfpSublayer1dayEntry
    MAX-ACCESS  not-accessible
    STATUS      current
    DESCRIPTION   ""
    ::=  { performanceMonitoring 99 }

intervalGfpSublayer1dayEntry OBJECT-TYPE
    SYNTAX      IntervalGfpSublayer1dayEntry
    MAX-ACCESS  not-accessible
    STATUS      current
    DESCRIPTION   ""
    INDEX       {
                  entityIndex,
                  intervalGfpSublayer1dayNumber
                }
    ::=  { intervalGfpSublayer1dayTable 1 }

IntervalGfpSublayer1dayEntry ::=  SEQUENCE
  { intervalGfpSublayer1dayNumber Integer32,
    intervalGfpSublayer1dayCoreHecCorrectedFrames Unsigned32,
    intervalGfpSublayer1dayTypeHecCorrectedFrames Unsigned32,
    intervalGfpSublayer1dayTypeHecDiscardedFrames Counter64String,
    intervalGfpSublayer1dayValidFlag TruthValue,
    intervalGfpSublayer1dayTimeStamp DateAndTime }

intervalGfpSublayer1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalGfpSublayer1dayEntry 1 }

intervalGfpSublayer1dayCoreHecCorrectedFrames OBJECT-TYPE
    SYNTAX      Unsigned32
    MAX-ACCESS  read-only
    STATUS      current
    DESCRIPTION
        "Core HEC Corrected Frames" 
    ::=  { intervalGfpSublayer1dayEntry 2 }

intervalGfpSublayer1dayTypeHecCorrectedFrames OBJECT-TYPE
    SYNTAX      Unsigned32
    MAX-ACCESS  read-only
    STATUS      current
    DESCRIPTION
        "Type Field HEC Corrected Frames" 
    ::=  { intervalGfpSublayer1dayEntry 3 }

intervalGfpSublayer1dayTypeHecDiscardedFrames OBJECT-TYPE
    SYNTAX      Counter64String
    MAX-ACCESS  read-only
    STATUS      current
    DESCRIPTION
        "Type Field HEC Discarded Frames" 
    ::=  { intervalGfpSublayer1dayEntry 4 }

intervalGfpSublayer1dayValidFlag OBJECT-TYPE
    SYNTAX      TruthValue
    MAX-ACCESS  read-only
    STATUS      current
    DESCRIPTION
        "Valid Flag" 
    ::=  { intervalGfpSublayer1dayEntry 5 }

intervalGfpSublayer1dayTimeStamp OBJECT-TYPE
    SYNTAX      DateAndTime
    MAX-ACCESS  read-only
    STATUS      current
    DESCRIPTION
        "Timestamp" 
    ::=  { intervalGfpSublayer1dayEntry 6 }

currentGfpfrSublayer15minTable OBJECT-TYPE
    SYNTAX      SEQUENCE OF CurrentGfpfrSublayer15minEntry
    MAX-ACCESS  not-accessible
    STATUS      current
    DESCRIPTION   ""
    ::=  { performanceMonitoring 100 }

currentGfpfrSublayer15minEntry OBJECT-TYPE
    SYNTAX      CurrentGfpfrSublayer15minEntry
    MAX-ACCESS  not-accessible
    STATUS      current
    DESCRIPTION   ""
    INDEX       {
                  entityIndex
                }
    ::=  { currentGfpfrSublayer15minTable 1 }

CurrentGfpfrSublayer15minEntry ::=  SEQUENCE
  { currentGfpfrSublayer15minGoodFrames Counter64String,
    currentGfpfrSublayer15minCHecDiscardedFrames Counter64String,
    currentGfpfrSublayer15minTHecDiscardedFrames Counter64String,
    currentGfpfrSublayer15minElapsedTime Integer32 }

currentGfpfrSublayer15minGoodFrames OBJECT-TYPE
    SYNTAX      Counter64String
    MAX-ACCESS  read-only
    STATUS      current
    DESCRIPTION
        "GFP Valid Frames" 
    ::=  { currentGfpfrSublayer15minEntry 1 }

currentGfpfrSublayer15minCHecDiscardedFrames OBJECT-TYPE
    SYNTAX      Counter64String
    MAX-ACCESS  read-only
    STATUS      current
    DESCRIPTION
        "Core HEC Discarded Frames" 
    ::=  { currentGfpfrSublayer15minEntry 2 }

currentGfpfrSublayer15minTHecDiscardedFrames OBJECT-TYPE
    SYNTAX      Counter64String
    MAX-ACCESS  read-only
    STATUS      current
    DESCRIPTION
        "Type Field HEC Discarded Frames" 
    ::=  { currentGfpfrSublayer15minEntry 3 }

currentGfpfrSublayer15minElapsedTime OBJECT-TYPE
    SYNTAX      Integer32 (0..9000 | -2147483648)
    MAX-ACCESS  read-only
    STATUS      current
    DESCRIPTION
        "Elapsed 15Min" 
    ::=  { currentGfpfrSublayer15minEntry 4 }

currentGfpfrSublayer1dayTable OBJECT-TYPE
    SYNTAX      SEQUENCE OF CurrentGfpfrSublayer1dayEntry
    MAX-ACCESS  not-accessible
    STATUS      current
    DESCRIPTION   ""
    ::=  { performanceMonitoring 101 }

currentGfpfrSublayer1dayEntry OBJECT-TYPE
    SYNTAX      CurrentGfpfrSublayer1dayEntry
    MAX-ACCESS  not-accessible
    STATUS      current
    DESCRIPTION   ""
    INDEX       {
                  entityIndex
                }
    ::=  { currentGfpfrSublayer1dayTable 1 }

CurrentGfpfrSublayer1dayEntry ::=  SEQUENCE
  { currentGfpfrSublayer1dayGoodFrames Counter64String,
    currentGfpfrSublayer1dayCHecDiscardedFrames Counter64String,
    currentGfpfrSublayer1dayTHecDiscardedFrames Counter64String,
    currentGfpfrSublayer1dayElapsedTime Integer32 }

currentGfpfrSublayer1dayGoodFrames OBJECT-TYPE
    SYNTAX      Counter64String
    MAX-ACCESS  read-only
    STATUS      current
    DESCRIPTION
        "GFP Valid Frames" 
    ::=  { currentGfpfrSublayer1dayEntry 1 }

currentGfpfrSublayer1dayCHecDiscardedFrames OBJECT-TYPE
    SYNTAX      Counter64String
    MAX-ACCESS  read-only
    STATUS      current
    DESCRIPTION
        "Core HEC Discarded Frames" 
    ::=  { currentGfpfrSublayer1dayEntry 2 }

currentGfpfrSublayer1dayTHecDiscardedFrames OBJECT-TYPE
    SYNTAX      Counter64String
    MAX-ACCESS  read-only
    STATUS      current
    DESCRIPTION
        "Type Field HEC Discarded Frames" 
    ::=  { currentGfpfrSublayer1dayEntry 3 }

currentGfpfrSublayer1dayElapsedTime OBJECT-TYPE
    SYNTAX      Integer32 (0..86400 | -2147483648)
    MAX-ACCESS  read-only
    STATUS      current
    DESCRIPTION
        "Elapsed 1Day" 
    ::=  { currentGfpfrSublayer1dayEntry 4 }

intervalGfpfrSublayer15minTable OBJECT-TYPE
    SYNTAX      SEQUENCE OF IntervalGfpfrSublayer15minEntry
    MAX-ACCESS  not-accessible
    STATUS      current
    DESCRIPTION   ""
    ::=  { performanceMonitoring 102 }

intervalGfpfrSublayer15minEntry OBJECT-TYPE
    SYNTAX      IntervalGfpfrSublayer15minEntry
    MAX-ACCESS  not-accessible
    STATUS      current
    DESCRIPTION   ""
    INDEX       {
                  entityIndex,
                  intervalGfpfrSublayer15minNumber
                }
    ::=  { intervalGfpfrSublayer15minTable 1 }

IntervalGfpfrSublayer15minEntry ::=  SEQUENCE
  { intervalGfpfrSublayer15minNumber Integer32,
    intervalGfpfrSublayer15minGoodFrames Counter64String,
    intervalGfpfrSublayer15minCHecDiscardedFrames Counter64String,
    intervalGfpfrSublayer15minTHecDiscardedFrames Counter64String,
    intervalGfpfrSublayer15minValidFlag TruthValue,
    intervalGfpfrSublayer15minTimeStamp DateAndTime }

intervalGfpfrSublayer15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalGfpfrSublayer15minEntry 1 }

intervalGfpfrSublayer15minGoodFrames OBJECT-TYPE
    SYNTAX      Counter64String
    MAX-ACCESS  read-only
    STATUS      current
    DESCRIPTION
        "GFP Valid Frames" 
    ::=  { intervalGfpfrSublayer15minEntry 2 }

intervalGfpfrSublayer15minCHecDiscardedFrames OBJECT-TYPE
    SYNTAX      Counter64String
    MAX-ACCESS  read-only
    STATUS      current
    DESCRIPTION
        "Core HEC Discarded Frames" 
    ::=  { intervalGfpfrSublayer15minEntry 3 }

intervalGfpfrSublayer15minTHecDiscardedFrames OBJECT-TYPE
    SYNTAX      Counter64String
    MAX-ACCESS  read-only
    STATUS      current
    DESCRIPTION
        "Type Field HEC Discarded Frames" 
    ::=  { intervalGfpfrSublayer15minEntry 4 }

intervalGfpfrSublayer15minValidFlag OBJECT-TYPE
    SYNTAX      TruthValue
    MAX-ACCESS  read-only
    STATUS      current
    DESCRIPTION
        "Valid Flag" 
    ::=  { intervalGfpfrSublayer15minEntry 5 }

intervalGfpfrSublayer15minTimeStamp OBJECT-TYPE
    SYNTAX      DateAndTime
    MAX-ACCESS  read-only
    STATUS      current
    DESCRIPTION
        "Timestamp" 
    ::=  { intervalGfpfrSublayer15minEntry 6 }

intervalGfpfrSublayer1dayTable OBJECT-TYPE
    SYNTAX      SEQUENCE OF IntervalGfpfrSublayer1dayEntry
    MAX-ACCESS  not-accessible
    STATUS      current
    DESCRIPTION   ""
    ::=  { performanceMonitoring 103 }

intervalGfpfrSublayer1dayEntry OBJECT-TYPE
    SYNTAX      IntervalGfpfrSublayer1dayEntry
    MAX-ACCESS  not-accessible
    STATUS      current
    DESCRIPTION   ""
    INDEX       {
                  entityIndex,
                  intervalGfpfrSublayer1dayNumber
                }
    ::=  { intervalGfpfrSublayer1dayTable 1 }

IntervalGfpfrSublayer1dayEntry ::=  SEQUENCE
  { intervalGfpfrSublayer1dayNumber Integer32,
    intervalGfpfrSublayer1dayGoodFrames Counter64String,
    intervalGfpfrSublayer1dayCHecDiscardedFrames Counter64String,
    intervalGfpfrSublayer1dayTHecDiscardedFrames Counter64String,
    intervalGfpfrSublayer1dayValidFlag TruthValue,
    intervalGfpfrSublayer1dayTimeStamp DateAndTime }

intervalGfpfrSublayer1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalGfpfrSublayer1dayEntry 1 }

intervalGfpfrSublayer1dayGoodFrames OBJECT-TYPE
    SYNTAX      Counter64String
    MAX-ACCESS  read-only
    STATUS      current
    DESCRIPTION
        "GFP Valid Frames" 
    ::=  { intervalGfpfrSublayer1dayEntry 2 }

intervalGfpfrSublayer1dayCHecDiscardedFrames OBJECT-TYPE
    SYNTAX      Counter64String
    MAX-ACCESS  read-only
    STATUS      current
    DESCRIPTION
        "Core HEC Discarded Frames" 
    ::=  { intervalGfpfrSublayer1dayEntry 3 }

intervalGfpfrSublayer1dayTHecDiscardedFrames OBJECT-TYPE
    SYNTAX      Counter64String
    MAX-ACCESS  read-only
    STATUS      current
    DESCRIPTION
        "Type Field HEC Discarded Frames" 
    ::=  { intervalGfpfrSublayer1dayEntry 4 }

intervalGfpfrSublayer1dayValidFlag OBJECT-TYPE
    SYNTAX      TruthValue
    MAX-ACCESS  read-only
    STATUS      current
    DESCRIPTION
        "Valid Flag" 
    ::=  { intervalGfpfrSublayer1dayEntry 5 }

intervalGfpfrSublayer1dayTimeStamp OBJECT-TYPE
    SYNTAX      DateAndTime
    MAX-ACCESS  read-only
    STATUS      current
    DESCRIPTION
        "Timestamp" 
    ::=  { intervalGfpfrSublayer1dayEntry 6 }

thresholdGfpSublayerTable OBJECT-TYPE
    SYNTAX      SEQUENCE OF ThresholdGfpSublayerEntry
    MAX-ACCESS  not-accessible
    STATUS      current
    DESCRIPTION   ""
    ::=  { performanceMonitoring 104 }

thresholdGfpSublayerEntry OBJECT-TYPE
    SYNTAX      ThresholdGfpSublayerEntry
    MAX-ACCESS  not-accessible
    STATUS      current
    DESCRIPTION   ""
    INDEX       {
                  entityIndex
                }
    ::=  { thresholdGfpSublayerTable 1 }

ThresholdGfpSublayerEntry ::=  SEQUENCE
  { thresholdGfpSublayerCoreHecCorrectedFramesHighThres15Min Unsigned32,
    thresholdGfpSublayerCoreHecCorrectedFramesHighThres1Day Unsigned32,
    thresholdGfpSublayerTypeHecCorrectedFramesHighThres15Min Unsigned32,
    thresholdGfpSublayerTypeHecCorrectedFramesHighThres15Day Unsigned32,
    thresholdGfpSublayerTypeHecDiscardedFramesHighThres15Min Unsigned32,
    thresholdGfpSublayerTypeHecDiscardedFramesHighThres1Day Unsigned32 }

thresholdGfpSublayerCoreHecCorrectedFramesHighThres15Min OBJECT-TYPE
    SYNTAX      Unsigned32 (0..900 | 4294967295)
    MAX-ACCESS  read-write
    STATUS      current
    DESCRIPTION
        "Core HEC Corrected Frames 15 Minute Threshold" 
    ::=  { thresholdGfpSublayerEntry 1 }

thresholdGfpSublayerCoreHecCorrectedFramesHighThres1Day OBJECT-TYPE
    SYNTAX      Unsigned32 (0..86400 | 4294967295)
    MAX-ACCESS  read-write
    STATUS      current
    DESCRIPTION
        "Core HEC Corrected Frames 1 Day Threshold" 
    ::=  { thresholdGfpSublayerEntry 2 }

thresholdGfpSublayerTypeHecCorrectedFramesHighThres15Min OBJECT-TYPE
    SYNTAX      Unsigned32 (0..900 | 4294967295)
    MAX-ACCESS  read-write
    STATUS      current
    DESCRIPTION
        "Type Field HEC Corrected Frames 15 Minute Threshold" 
    ::=  { thresholdGfpSublayerEntry 3 }

thresholdGfpSublayerTypeHecCorrectedFramesHighThres15Day OBJECT-TYPE
    SYNTAX      Unsigned32 (0..86400 | 4294967295)
    MAX-ACCESS  read-write
    STATUS      current
    DESCRIPTION
        "Type Field HEC Corrected Frames Day Threshold" 
    ::=  { thresholdGfpSublayerEntry 4 }

thresholdGfpSublayerTypeHecDiscardedFramesHighThres15Min OBJECT-TYPE
    SYNTAX      Unsigned32 (0..900 | 4294967295)
    MAX-ACCESS  read-write
    STATUS      current
    DESCRIPTION
        "Type Field HEC Discarded Frames 15 Minute Threshold" 
    ::=  { thresholdGfpSublayerEntry 5 }

thresholdGfpSublayerTypeHecDiscardedFramesHighThres1Day OBJECT-TYPE
    SYNTAX      Unsigned32
    MAX-ACCESS  read-write
    STATUS      current
    DESCRIPTION
        "Type Field HEC Discarded Frames High Threshold" 
    ::=  { thresholdGfpSublayerEntry 6 }

thresholdPhysConvCombinedTable OBJECT-TYPE
    SYNTAX      SEQUENCE OF ThresholdPhysConvCombinedEntry
    MAX-ACCESS  not-accessible
    STATUS      current
    DESCRIPTION   ""
    ::=  { performanceMonitoring 105 }

thresholdPhysConvCombinedEntry OBJECT-TYPE
    SYNTAX      ThresholdPhysConvCombinedEntry
    MAX-ACCESS  not-accessible
    STATUS      current
    DESCRIPTION   ""
    INDEX       {
                  entityIndex
                }
    ::=  { thresholdPhysConvCombinedTable 1 }

ThresholdPhysConvCombinedEntry ::=  SEQUENCE
  { thresholdPhysConvCombinedESHighThres15min Unsigned32,
    thresholdPhysConvCombinedESHighThres1day Unsigned32,
    thresholdPhysConvCombinedCVDEHighThres15min Counter64String,
    thresholdPhysConvCombinedCVDEHighThres1day Counter64String }

thresholdPhysConvCombinedESHighThres15min OBJECT-TYPE
    SYNTAX      Unsigned32 (0..900 | 4294967295)
    MAX-ACCESS  read-write
    STATUS      current
    DESCRIPTION
        "Physical Coding Layer Errored Seconds 15 Minute Threshold" 
    ::=  { thresholdPhysConvCombinedEntry 1 }

thresholdPhysConvCombinedESHighThres1day OBJECT-TYPE
    SYNTAX      Unsigned32 (0..89400 | 4294967295)
    MAX-ACCESS  read-write
    STATUS      current
    DESCRIPTION
        "Physical Coding Layer Errored Seconds 1 Day Threshold" 
    ::=  { thresholdPhysConvCombinedEntry 2 }

thresholdPhysConvCombinedCVDEHighThres15min OBJECT-TYPE
    SYNTAX      Counter64String
    MAX-ACCESS  read-write
    STATUS      current
    DESCRIPTION
        "Physical Coding Layer 15 Minute Threshold" 
    ::=  { thresholdPhysConvCombinedEntry 3 }

thresholdPhysConvCombinedCVDEHighThres1day OBJECT-TYPE
    SYNTAX      Counter64String
    MAX-ACCESS  read-write
    STATUS      current
    DESCRIPTION
        "Physical Coding Layer Coding Violations 1 Day Threshold" 
    ::=  { thresholdPhysConvCombinedEntry 4 }

currentPhysConvCombined15minTable OBJECT-TYPE
    SYNTAX      SEQUENCE OF CurrentPhysConvCombined15minEntry
    MAX-ACCESS  not-accessible
    STATUS      current
    DESCRIPTION   ""
    ::=  { performanceMonitoring 106 }

currentPhysConvCombined15minEntry OBJECT-TYPE
    SYNTAX      CurrentPhysConvCombined15minEntry
    MAX-ACCESS  not-accessible
    STATUS      current
    DESCRIPTION   ""
    INDEX       {
                  entityIndex
                }
    ::=  { currentPhysConvCombined15minTable 1 }

CurrentPhysConvCombined15minEntry ::=  SEQUENCE
  { currentPhysConvCombined15minES Unsigned32,
    currentPhysConvCombined15minCVDE Counter64String,
    currentPhysConvCombined15minElapsedTime Integer32 }

currentPhysConvCombined15minES OBJECT-TYPE
    SYNTAX      Unsigned32
    MAX-ACCESS  read-only
    STATUS      current
    DESCRIPTION
        "Physical Coding Layer Errored Seconds" 
    ::=  { currentPhysConvCombined15minEntry 1 }

currentPhysConvCombined15minCVDE OBJECT-TYPE
    SYNTAX      Counter64String
    MAX-ACCESS  read-only
    STATUS      current
    DESCRIPTION
        "Physical Coding Layer Coding Violations + Disparity Errors" 
    ::=  { currentPhysConvCombined15minEntry 2 }

currentPhysConvCombined15minElapsedTime OBJECT-TYPE
    SYNTAX      Integer32 (0..9000 | -2147483648)
    MAX-ACCESS  read-only
    STATUS      current
    DESCRIPTION
        "Elapsed 15Min" 
    ::=  { currentPhysConvCombined15minEntry 3 }

currentPhysConvCombined1dayTable OBJECT-TYPE
    SYNTAX      SEQUENCE OF CurrentPhysConvCombined1dayEntry
    MAX-ACCESS  not-accessible
    STATUS      current
    DESCRIPTION   ""
    ::=  { performanceMonitoring 107 }

currentPhysConvCombined1dayEntry OBJECT-TYPE
    SYNTAX      CurrentPhysConvCombined1dayEntry
    MAX-ACCESS  not-accessible
    STATUS      current
    DESCRIPTION   ""
    INDEX       {
                  entityIndex
                }
    ::=  { currentPhysConvCombined1dayTable 1 }

CurrentPhysConvCombined1dayEntry ::=  SEQUENCE
  { currentPhysConvCombined1dayES Unsigned32,
    currentPhysConvCombined1dayCVDE Counter64String,
    currentPhysConvCombined1dayElapsedTime Integer32 }

currentPhysConvCombined1dayES OBJECT-TYPE
    SYNTAX      Unsigned32
    MAX-ACCESS  read-only
    STATUS      current
    DESCRIPTION
        "Physical Coding Layer Errored Seconds" 
    ::=  { currentPhysConvCombined1dayEntry 1 }

currentPhysConvCombined1dayCVDE OBJECT-TYPE
    SYNTAX      Counter64String
    MAX-ACCESS  read-only
    STATUS      current
    DESCRIPTION
        "Physical Coding Layer Coding Violations + Disparity Errors" 
    ::=  { currentPhysConvCombined1dayEntry 2 }

currentPhysConvCombined1dayElapsedTime OBJECT-TYPE
    SYNTAX      Integer32 (0..86400 | -2147483648)
    MAX-ACCESS  read-only
    STATUS      current
    DESCRIPTION
        "Elapsed 1Day" 
    ::=  { currentPhysConvCombined1dayEntry 3 }

intervalPhysConvCombined15minTable OBJECT-TYPE
    SYNTAX      SEQUENCE OF IntervalPhysConvCombined15minEntry
    MAX-ACCESS  not-accessible
    STATUS      current
    DESCRIPTION   ""
    ::=  { performanceMonitoring 108 }

intervalPhysConvCombined15minEntry OBJECT-TYPE
    SYNTAX      IntervalPhysConvCombined15minEntry
    MAX-ACCESS  not-accessible
    STATUS      current
    DESCRIPTION   ""
    INDEX       {
                  entityIndex,
                  intervalPhysConvCombined15minNumber
                }
    ::=  { intervalPhysConvCombined15minTable 1 }

IntervalPhysConvCombined15minEntry ::=  SEQUENCE
  { intervalPhysConvCombined15minNumber Integer32,
    intervalPhysConvCombined15minES Unsigned32,
    intervalPhysConvCombined15minCVDE Counter64String,
    intervalPhysConvCombined15minValidFlag TruthValue,
    intervalPhysConvCombined15minTimeStamp DateAndTime }

intervalPhysConvCombined15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysConvCombined15minEntry 1 }

intervalPhysConvCombined15minES OBJECT-TYPE
    SYNTAX      Unsigned32
    MAX-ACCESS  read-only
    STATUS      current
    DESCRIPTION
        "Physical Coding Layer Errored Seconds" 
    ::=  { intervalPhysConvCombined15minEntry 2 }

intervalPhysConvCombined15minCVDE OBJECT-TYPE
    SYNTAX      Counter64String
    MAX-ACCESS  read-only
    STATUS      current
    DESCRIPTION
        "Physical Coding Layer Coding Violations + Disparity Errors" 
    ::=  { intervalPhysConvCombined15minEntry 3 }

intervalPhysConvCombined15minValidFlag OBJECT-TYPE
    SYNTAX      TruthValue
    MAX-ACCESS  read-only
    STATUS      current
    DESCRIPTION
        "Valid Flag" 
    ::=  { intervalPhysConvCombined15minEntry 4 }

intervalPhysConvCombined15minTimeStamp OBJECT-TYPE
    SYNTAX      DateAndTime
    MAX-ACCESS  read-only
    STATUS      current
    DESCRIPTION
        "Timestamp" 
    ::=  { intervalPhysConvCombined15minEntry 5 }

intervalPhysConvCombined1dayTable OBJECT-TYPE
    SYNTAX      SEQUENCE OF IntervalPhysConvCombined1dayEntry
    MAX-ACCESS  not-accessible
    STATUS      current
    DESCRIPTION   ""
    ::=  { performanceMonitoring 109 }

intervalPhysConvCombined1dayEntry OBJECT-TYPE
    SYNTAX      IntervalPhysConvCombined1dayEntry
    MAX-ACCESS  not-accessible
    STATUS      current
    DESCRIPTION   ""
    INDEX       {
                  entityIndex,
                  intervalPhysConvCombined1dayNumber
                }
    ::=  { intervalPhysConvCombined1dayTable 1 }

IntervalPhysConvCombined1dayEntry ::=  SEQUENCE
  { intervalPhysConvCombined1dayNumber Integer32,
    intervalPhysConvCombined1dayES Unsigned32,
    intervalPhysConvCombined1dayCVDE Counter64String,
    intervalPhysConvCombined1dayValidFlag TruthValue,
    intervalPhysConvCombined1dayTimeStamp DateAndTime }

intervalPhysConvCombined1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysConvCombined1dayEntry 1 }

intervalPhysConvCombined1dayES OBJECT-TYPE
    SYNTAX      Unsigned32
    MAX-ACCESS  read-only
    STATUS      current
    DESCRIPTION
        "Physical Coding Layer Errored Seconds" 
    ::=  { intervalPhysConvCombined1dayEntry 2 }

intervalPhysConvCombined1dayCVDE OBJECT-TYPE
    SYNTAX      Counter64String
    MAX-ACCESS  read-only
    STATUS      current
    DESCRIPTION
        "Physical Coding Layer Coding Violations + Disparity Errors" 
    ::=  { intervalPhysConvCombined1dayEntry 3 }

intervalPhysConvCombined1dayValidFlag OBJECT-TYPE
    SYNTAX      TruthValue
    MAX-ACCESS  read-only
    STATUS      current
    DESCRIPTION
        "Valid Flag" 
    ::=  { intervalPhysConvCombined1dayEntry 4 }

intervalPhysConvCombined1dayTimeStamp OBJECT-TYPE
    SYNTAX      DateAndTime
    MAX-ACCESS  read-only
    STATUS      current
    DESCRIPTION
        "Timestamp" 
    ::=  { intervalPhysConvCombined1dayEntry 5 }

thresholdOtuFecSublayerTable OBJECT-TYPE
    SYNTAX      SEQUENCE OF ThresholdOtuFecSublayerEntry
    MAX-ACCESS  not-accessible
    STATUS      current
    DESCRIPTION   ""
    ::=  { performanceMonitoring 110 }

thresholdOtuFecSublayerEntry OBJECT-TYPE
    SYNTAX      ThresholdOtuFecSublayerEntry
    MAX-ACCESS  not-accessible
    STATUS      current
    DESCRIPTION   ""
    INDEX       {
                  entityIndex
                }
    ::=  { thresholdOtuFecSublayerTable 1 }

ThresholdOtuFecSublayerEntry ::=  SEQUENCE
  { thresholdOtuFecSublayerESHighThres15min Unsigned32,
    thresholdOtuFecSublayerESHighThres1day Unsigned32,
    thresholdOtuFecSublayerSESHighThres15min Unsigned32,
    thresholdOtuFecSublayerSESHighThres1day Unsigned32,
    thresholdOtuFecSublayerCEHighThres15min Counter64String,
    thresholdOtuFecSublayerCEHighThres1day Counter64String,
    thresholdOtuFecSublayerUBEHighThres15min Counter64String,
    thresholdOtuFecSublayerUBEHighThres1day Counter64String,
    thresholdOtuFecSublayerBERCEHighThres15min Counter64String,
    thresholdOtuFecSublayerBERCEHighThres1day Counter64String }

thresholdOtuFecSublayerESHighThres15min OBJECT-TYPE
    SYNTAX      Unsigned32 (0..900 | 4294967295)
    MAX-ACCESS  read-write
    STATUS      current
    DESCRIPTION
        "OTU FEC Errored Seconds 15 Minute Threshold" 
    ::=  { thresholdOtuFecSublayerEntry 1 }

thresholdOtuFecSublayerESHighThres1day OBJECT-TYPE
    SYNTAX      Unsigned32 (0..86400 | 4294967295)
    MAX-ACCESS  read-write
    STATUS      current
    DESCRIPTION
        "OTU FEC Errored Seconds Day Threshold" 
    ::=  { thresholdOtuFecSublayerEntry 2 }

thresholdOtuFecSublayerSESHighThres15min OBJECT-TYPE
    SYNTAX      Unsigned32 (0..900 | 4294967295)
    MAX-ACCESS  read-write
    STATUS      current
    DESCRIPTION
        "OTU FEC Severely Errored Seconds 15 Minute Threshold" 
    ::=  { thresholdOtuFecSublayerEntry 3 }

thresholdOtuFecSublayerSESHighThres1day OBJECT-TYPE
    SYNTAX      Unsigned32 (0..86400 | 4294967295)
    MAX-ACCESS  read-write
    STATUS      current
    DESCRIPTION
        "OTU FEC Severely Errored Seconds 1 Day Threshold" 
    ::=  { thresholdOtuFecSublayerEntry 4 }

thresholdOtuFecSublayerCEHighThres15min OBJECT-TYPE
    SYNTAX      Counter64String
    MAX-ACCESS  read-write
    STATUS      current
    DESCRIPTION
        "FEC Corrected Errors 15 Minute Threshold" 
    ::=  { thresholdOtuFecSublayerEntry 5 }

thresholdOtuFecSublayerCEHighThres1day OBJECT-TYPE
    SYNTAX      Counter64String
    MAX-ACCESS  read-write
    STATUS      current
    DESCRIPTION
        "FEC Corrected Errors 1 Day Threshold" 
    ::=  { thresholdOtuFecSublayerEntry 6 }

thresholdOtuFecSublayerUBEHighThres15min OBJECT-TYPE
    SYNTAX      Counter64String
    MAX-ACCESS  read-write
    STATUS      current
    DESCRIPTION
        "Uncorrected Block Errors 15 Minute Threshold" 
    ::=  { thresholdOtuFecSublayerEntry 7 }

thresholdOtuFecSublayerUBEHighThres1day OBJECT-TYPE
    SYNTAX      Counter64String
    MAX-ACCESS  read-write
    STATUS      current
    DESCRIPTION
        "Uncorrected Block Errors 1 Day Threshold" 
    ::=  { thresholdOtuFecSublayerEntry 8 }

thresholdOtuFecSublayerBERCEHighThres15min OBJECT-TYPE
    SYNTAX      Counter64String 
    UNITS       "1.0E-18"
    MAX-ACCESS  read-write
    STATUS      current
    DESCRIPTION
        "Bit Error Rate before FEC 15 Minute Threshold" 
    ::=  { thresholdOtuFecSublayerEntry 9 }

thresholdOtuFecSublayerBERCEHighThres1day OBJECT-TYPE
    SYNTAX      Counter64String 
    UNITS       "1.0E-18"
    MAX-ACCESS  read-write
    STATUS      current
    DESCRIPTION
        "Bit Error Rate before FEC 1 Day Threshold" 
    ::=  { thresholdOtuFecSublayerEntry 10 }

thresholdSonetLineMsTable OBJECT-TYPE
    SYNTAX      SEQUENCE OF ThresholdSonetLineMsEntry
    MAX-ACCESS  not-accessible
    STATUS      current
    DESCRIPTION   ""
    ::=  { performanceMonitoring 111 }

thresholdSonetLineMsEntry OBJECT-TYPE
    SYNTAX      ThresholdSonetLineMsEntry
    MAX-ACCESS  not-accessible
    STATUS      current
    DESCRIPTION   ""
    INDEX       {
                  entityIndex
                }
    ::=  { thresholdSonetLineMsTable 1 }

ThresholdSonetLineMsEntry ::=  SEQUENCE
  { thresholdSonetLineMsESHighThres15min Unsigned32,
    thresholdSonetLineMsESHighThres1day Unsigned32,
    thresholdSonetLineMsSESHighThres15min Unsigned32,
    thresholdSonetLineMsSESHighThres1day Unsigned32,
    thresholdSonetLineMsUASHighThres15min Unsigned32,
    thresholdSonetLineMsUASSHighThres1day Unsigned32,
    thresholdSonetLineMsCVHighThres15min Counter64String,
    thresholdSonetLineMsCVSHighThres1day Counter64String }

thresholdSonetLineMsESHighThres15min OBJECT-TYPE
    SYNTAX      Unsigned32 (0..900 | 4294967295)
    MAX-ACCESS  read-write
    STATUS      current
    DESCRIPTION
        "Line / Multiplex Section Errored Seconds 15 Minute Threshold" 
    ::=  { thresholdSonetLineMsEntry 1 }

thresholdSonetLineMsESHighThres1day OBJECT-TYPE
    SYNTAX      Unsigned32 (0..86400 | 4294967295)
    MAX-ACCESS  read-write
    STATUS      current
    DESCRIPTION
        "Line / Multiplex Section Errored Seconds 1 Day Threshold" 
    ::=  { thresholdSonetLineMsEntry 2 }

thresholdSonetLineMsSESHighThres15min OBJECT-TYPE
    SYNTAX      Unsigned32 (0..900 | 4294967295)
    MAX-ACCESS  read-write
    STATUS      current
    DESCRIPTION
        "Line / Multiplex Section Severely Errored Seconds 15 Minute Threshold" 
    ::=  { thresholdSonetLineMsEntry 3 }

thresholdSonetLineMsSESHighThres1day OBJECT-TYPE
    SYNTAX      Unsigned32 (0..86400 | 4294967295)
    MAX-ACCESS  read-write
    STATUS      current
    DESCRIPTION
        "Line / Multiplex Section Severely Errored Seconds 1 Day Threshold" 
    ::=  { thresholdSonetLineMsEntry 4 }

thresholdSonetLineMsUASHighThres15min OBJECT-TYPE
    SYNTAX      Unsigned32 (0..900 | 4294967295)
    MAX-ACCESS  read-write
    STATUS      current
    DESCRIPTION
        "Line / Multiplex Section Unavailable Seconds 15 Minute Threshold" 
    ::=  { thresholdSonetLineMsEntry 5 }

thresholdSonetLineMsUASSHighThres1day OBJECT-TYPE
    SYNTAX      Unsigned32 (0..86400 | 4294967295)
    MAX-ACCESS  read-write
    STATUS      current
    DESCRIPTION
        "Line / Multiplex Section Unavailable Seconds 1 Day Threshold" 
    ::=  { thresholdSonetLineMsEntry 6 }

thresholdSonetLineMsCVHighThres15min OBJECT-TYPE
    SYNTAX      Counter64String
    MAX-ACCESS  read-write
    STATUS      current
    DESCRIPTION
        "Line / Multiplex Section Coding Violations 15 Minute Threshold" 
    ::=  { thresholdSonetLineMsEntry 7 }

thresholdSonetLineMsCVSHighThres1day OBJECT-TYPE
    SYNTAX      Counter64String
    MAX-ACCESS  read-write
    STATUS      current
    DESCRIPTION
        "Line / Multiplex Section Coding Violations 1 Day Threshold" 
    ::=  { thresholdSonetLineMsEntry 8 }

intervalPhysPerfEstimatedSignalGain15minTable OBJECT-TYPE
    SYNTAX      SEQUENCE OF IntervalPhysPerfEstimatedSignalGain15minEntry
    MAX-ACCESS  not-accessible
    STATUS      current
    DESCRIPTION   ""
    ::=  { performanceMonitoring 112 }

intervalPhysPerfEstimatedSignalGain15minEntry OBJECT-TYPE
    SYNTAX      IntervalPhysPerfEstimatedSignalGain15minEntry
    MAX-ACCESS  not-accessible
    STATUS      current
    DESCRIPTION   ""
    INDEX       {
                  entityIndex,
                  intervalPhysPerfEstimatedSignalGain15minNumber
                }
    ::=  { intervalPhysPerfEstimatedSignalGain15minTable 1 }

IntervalPhysPerfEstimatedSignalGain15minEntry ::=  SEQUENCE
  { intervalPhysPerfEstimatedSignalGain15minNumber Integer32,
    intervalPhysPerfEstimatedSignalGain15minLow Unsigned32,
    intervalPhysPerfEstimatedSignalGain15minMean Unsigned32,
    intervalPhysPerfEstimatedSignalGain15minHigh Unsigned32,
    intervalPhysPerfEstimatedSignalGain15minValidFlag TruthValue,
    intervalPhysPerfEstimatedSignalGain15minTimeStamp DateAndTime }

intervalPhysPerfEstimatedSignalGain15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfEstimatedSignalGain15minEntry 1 }

intervalPhysPerfEstimatedSignalGain15minLow OBJECT-TYPE
    SYNTAX      Unsigned32 
    UNITS       "0.1 dB"
    MAX-ACCESS  read-only
    STATUS      current
    DESCRIPTION
        "Estimated signal gain low" 
    ::=  { intervalPhysPerfEstimatedSignalGain15minEntry 2 }

intervalPhysPerfEstimatedSignalGain15minMean OBJECT-TYPE
    SYNTAX      Unsigned32 
    UNITS       "0.1 dB"
    MAX-ACCESS  read-only
    STATUS      current
    DESCRIPTION
        "Estimated signal gain average" 
    ::=  { intervalPhysPerfEstimatedSignalGain15minEntry 3 }

intervalPhysPerfEstimatedSignalGain15minHigh OBJECT-TYPE
    SYNTAX      Unsigned32 
    UNITS       "0.1 dB"
    MAX-ACCESS  read-only
    STATUS      current
    DESCRIPTION
        "Estimated signal gain high" 
    ::=  { intervalPhysPerfEstimatedSignalGain15minEntry 4 }

intervalPhysPerfEstimatedSignalGain15minValidFlag OBJECT-TYPE
    SYNTAX      TruthValue
    MAX-ACCESS  read-only
    STATUS      current
    DESCRIPTION
        "Valid Flag" 
    ::=  { intervalPhysPerfEstimatedSignalGain15minEntry 5 }

intervalPhysPerfEstimatedSignalGain15minTimeStamp OBJECT-TYPE
    SYNTAX      DateAndTime
    MAX-ACCESS  read-only
    STATUS      current
    DESCRIPTION
        "Timestamp" 
    ::=  { intervalPhysPerfEstimatedSignalGain15minEntry 6 }

intervalPhysPerfEstimatedSignalGain1dayTable OBJECT-TYPE
    SYNTAX      SEQUENCE OF IntervalPhysPerfEstimatedSignalGain1dayEntry
    MAX-ACCESS  not-accessible
    STATUS      current
    DESCRIPTION   ""
    ::=  { performanceMonitoring 113 }

intervalPhysPerfEstimatedSignalGain1dayEntry OBJECT-TYPE
    SYNTAX      IntervalPhysPerfEstimatedSignalGain1dayEntry
    MAX-ACCESS  not-accessible
    STATUS      current
    DESCRIPTION   ""
    INDEX       {
                  entityIndex,
                  intervalPhysPerfEstimatedSignalGain1dayNumber
                }
    ::=  { intervalPhysPerfEstimatedSignalGain1dayTable 1 }

IntervalPhysPerfEstimatedSignalGain1dayEntry ::=  SEQUENCE
  { intervalPhysPerfEstimatedSignalGain1dayNumber Integer32,
    intervalPhysPerfEstimatedSignalGain1dayLow Unsigned32,
    intervalPhysPerfEstimatedSignalGain1dayMean Unsigned32,
    intervalPhysPerfEstimatedSignalGain1dayHigh Unsigned32,
    intervalPhysPerfEstimatedSignalGain1dayValidFlag TruthValue,
    intervalPhysPerfEstimatedSignalGain1dayTimeStamp DateAndTime }

intervalPhysPerfEstimatedSignalGain1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfEstimatedSignalGain1dayEntry 1 }

intervalPhysPerfEstimatedSignalGain1dayLow OBJECT-TYPE
    SYNTAX      Unsigned32 
    UNITS       "0.1 dB"
    MAX-ACCESS  read-only
    STATUS      current
    DESCRIPTION
        "Estimated signal gain low" 
    ::=  { intervalPhysPerfEstimatedSignalGain1dayEntry 2 }

intervalPhysPerfEstimatedSignalGain1dayMean OBJECT-TYPE
    SYNTAX      Unsigned32 
    UNITS       "0.1 dB"
    MAX-ACCESS  read-only
    STATUS      current
    DESCRIPTION
        "Estimated signal gain average" 
    ::=  { intervalPhysPerfEstimatedSignalGain1dayEntry 3 }

intervalPhysPerfEstimatedSignalGain1dayHigh OBJECT-TYPE
    SYNTAX      Unsigned32 
    UNITS       "0.1 dB"
    MAX-ACCESS  read-only
    STATUS      current
    DESCRIPTION
        "Estimated signal gain high" 
    ::=  { intervalPhysPerfEstimatedSignalGain1dayEntry 4 }

intervalPhysPerfEstimatedSignalGain1dayValidFlag OBJECT-TYPE
    SYNTAX      TruthValue
    MAX-ACCESS  read-only
    STATUS      current
    DESCRIPTION
        "Valid Flag" 
    ::=  { intervalPhysPerfEstimatedSignalGain1dayEntry 5 }

intervalPhysPerfEstimatedSignalGain1dayTimeStamp OBJECT-TYPE
    SYNTAX      DateAndTime
    MAX-ACCESS  read-only
    STATUS      current
    DESCRIPTION
        "Timestamp" 
    ::=  { intervalPhysPerfEstimatedSignalGain1dayEntry 6 }

intervalPhysPerfEstimatedSignalGain1weekTable OBJECT-TYPE
    SYNTAX      SEQUENCE OF IntervalPhysPerfEstimatedSignalGain1weekEntry
    MAX-ACCESS  not-accessible
    STATUS      current
    DESCRIPTION   ""
    ::=  { performanceMonitoring 114 }

intervalPhysPerfEstimatedSignalGain1weekEntry OBJECT-TYPE
    SYNTAX      IntervalPhysPerfEstimatedSignalGain1weekEntry
    MAX-ACCESS  not-accessible
    STATUS      current
    DESCRIPTION   ""
    INDEX       {
                  entityIndex,
                  intervalPhysPerfEstimatedSignalGain1weekNumber
                }
    ::=  { intervalPhysPerfEstimatedSignalGain1weekTable 1 }

IntervalPhysPerfEstimatedSignalGain1weekEntry ::=  SEQUENCE
  { intervalPhysPerfEstimatedSignalGain1weekNumber Integer32,
    intervalPhysPerfEstimatedSignalGain1weekLow Unsigned32,
    intervalPhysPerfEstimatedSignalGain1weekMean Unsigned32,
    intervalPhysPerfEstimatedSignalGain1weekHigh Unsigned32,
    intervalPhysPerfEstimatedSignalGain1weekValidFlag TruthValue,
    intervalPhysPerfEstimatedSignalGain1weekTimeStamp DateAndTime }

intervalPhysPerfEstimatedSignalGain1weekNumber OBJECT-TYPE
    SYNTAX      Integer32 (1..52)
    MAX-ACCESS  not-accessible
    STATUS      current
    DESCRIPTION
        "Number 1week" 
    ::=  { intervalPhysPerfEstimatedSignalGain1weekEntry 1 }

intervalPhysPerfEstimatedSignalGain1weekLow OBJECT-TYPE
    SYNTAX      Unsigned32 
    UNITS       "0.1 dB"
    MAX-ACCESS  read-only
    STATUS      current
    DESCRIPTION
        "Estimated signal gain low" 
    ::=  { intervalPhysPerfEstimatedSignalGain1weekEntry 2 }

intervalPhysPerfEstimatedSignalGain1weekMean OBJECT-TYPE
    SYNTAX      Unsigned32 
    UNITS       "0.1 dB"
    MAX-ACCESS  read-only
    STATUS      current
    DESCRIPTION
        "Estimated signal gain average" 
    ::=  { intervalPhysPerfEstimatedSignalGain1weekEntry 3 }

intervalPhysPerfEstimatedSignalGain1weekHigh OBJECT-TYPE
    SYNTAX      Unsigned32 
    UNITS       "0.1 dB"
    MAX-ACCESS  read-only
    STATUS      current
    DESCRIPTION
        "Estimated signal gain high" 
    ::=  { intervalPhysPerfEstimatedSignalGain1weekEntry 4 }

intervalPhysPerfEstimatedSignalGain1weekValidFlag OBJECT-TYPE
    SYNTAX      TruthValue
    MAX-ACCESS  read-only
    STATUS      current
    DESCRIPTION
        "Valid Flag" 
    ::=  { intervalPhysPerfEstimatedSignalGain1weekEntry 5 }

intervalPhysPerfEstimatedSignalGain1weekTimeStamp OBJECT-TYPE
    SYNTAX      DateAndTime
    MAX-ACCESS  read-only
    STATUS      current
    DESCRIPTION
        "Timestamp" 
    ::=  { intervalPhysPerfEstimatedSignalGain1weekEntry 6 }

intervalPhysPerfCurrent15minTable OBJECT-TYPE
    SYNTAX      SEQUENCE OF IntervalPhysPerfCurrent15minEntry
    MAX-ACCESS  not-accessible
    STATUS      current
    DESCRIPTION   ""
    ::=  { performanceMonitoring 115 }

intervalPhysPerfCurrent15minEntry OBJECT-TYPE
    SYNTAX      IntervalPhysPerfCurrent15minEntry
    MAX-ACCESS  not-accessible
    STATUS      current
    DESCRIPTION   ""
    INDEX       {
                  entityIndex,
                  intervalPhysPerfCurrent15minNumber
                }
    ::=  { intervalPhysPerfCurrent15minTable 1 }

IntervalPhysPerfCurrent15minEntry ::=  SEQUENCE
  { intervalPhysPerfCurrent15minNumber Integer32,
    intervalPhysPerfCurrent15minLow Unsigned32,
    intervalPhysPerfCurrent15minMean Unsigned32,
    intervalPhysPerfCurrent15minHigh Unsigned32,
    intervalPhysPerfCurrent15minValidFlag TruthValue,
    intervalPhysPerfCurrent15minTimeStamp DateAndTime }

intervalPhysPerfCurrent15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfCurrent15minEntry 1 }

intervalPhysPerfCurrent15minLow OBJECT-TYPE
    SYNTAX      Unsigned32 
    UNITS       "0.001 A"
    MAX-ACCESS  read-only
    STATUS      current
    DESCRIPTION
        "Board or Pluggable Submodule Low Current" 
    ::=  { intervalPhysPerfCurrent15minEntry 2 }

intervalPhysPerfCurrent15minMean OBJECT-TYPE
    SYNTAX      Unsigned32 
    UNITS       "0.001 A"
    MAX-ACCESS  read-only
    STATUS      current
    DESCRIPTION
        "Board or Pluggable Submodule Mean Current" 
    ::=  { intervalPhysPerfCurrent15minEntry 3 }

intervalPhysPerfCurrent15minHigh OBJECT-TYPE
    SYNTAX      Unsigned32 
    UNITS       "0.001 A"
    MAX-ACCESS  read-only
    STATUS      current
    DESCRIPTION
        "Board or Pluggable Submodule High Current" 
    ::=  { intervalPhysPerfCurrent15minEntry 4 }

intervalPhysPerfCurrent15minValidFlag OBJECT-TYPE
    SYNTAX      TruthValue
    MAX-ACCESS  read-only
    STATUS      current
    DESCRIPTION
        "Valid Flag" 
    ::=  { intervalPhysPerfCurrent15minEntry 5 }

intervalPhysPerfCurrent15minTimeStamp OBJECT-TYPE
    SYNTAX      DateAndTime
    MAX-ACCESS  read-only
    STATUS      current
    DESCRIPTION
        "Timestamp" 
    ::=  { intervalPhysPerfCurrent15minEntry 6 }

intervalPhysPerfCurrent1dayTable OBJECT-TYPE
    SYNTAX      SEQUENCE OF IntervalPhysPerfCurrent1dayEntry
    MAX-ACCESS  not-accessible
    STATUS      current
    DESCRIPTION   ""
    ::=  { performanceMonitoring 116 }

intervalPhysPerfCurrent1dayEntry OBJECT-TYPE
    SYNTAX      IntervalPhysPerfCurrent1dayEntry
    MAX-ACCESS  not-accessible
    STATUS      current
    DESCRIPTION   ""
    INDEX       {
                  entityIndex,
                  intervalPhysPerfCurrent1dayNumber
                }
    ::=  { intervalPhysPerfCurrent1dayTable 1 }

IntervalPhysPerfCurrent1dayEntry ::=  SEQUENCE
  { intervalPhysPerfCurrent1dayNumber Integer32,
    intervalPhysPerfCurrent1dayLow Unsigned32,
    intervalPhysPerfCurrent1dayMean Unsigned32,
    intervalPhysPerfCurrent1dayHigh Unsigned32,
    intervalPhysPerfCurrent1dayValidFlag TruthValue,
    intervalPhysPerfCurrent1dayTimeStamp DateAndTime }

intervalPhysPerfCurrent1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfCurrent1dayEntry 1 }

intervalPhysPerfCurrent1dayLow OBJECT-TYPE
    SYNTAX      Unsigned32 
    UNITS       "0.001 A"
    MAX-ACCESS  read-only
    STATUS      current
    DESCRIPTION
        "Board or Pluggable Submodule Low Current" 
    ::=  { intervalPhysPerfCurrent1dayEntry 2 }

intervalPhysPerfCurrent1dayMean OBJECT-TYPE
    SYNTAX      Unsigned32 
    UNITS       "0.001 A"
    MAX-ACCESS  read-only
    STATUS      current
    DESCRIPTION
        "Board or Pluggable Submodule Mean Current" 
    ::=  { intervalPhysPerfCurrent1dayEntry 3 }

intervalPhysPerfCurrent1dayHigh OBJECT-TYPE
    SYNTAX      Unsigned32 
    UNITS       "0.001 A"
    MAX-ACCESS  read-only
    STATUS      current
    DESCRIPTION
        "Board or Pluggable Submodule High Current" 
    ::=  { intervalPhysPerfCurrent1dayEntry 4 }

intervalPhysPerfCurrent1dayValidFlag OBJECT-TYPE
    SYNTAX      TruthValue
    MAX-ACCESS  read-only
    STATUS      current
    DESCRIPTION
        "Valid Flag" 
    ::=  { intervalPhysPerfCurrent1dayEntry 5 }

intervalPhysPerfCurrent1dayTimeStamp OBJECT-TYPE
    SYNTAX      DateAndTime
    MAX-ACCESS  read-only
    STATUS      current
    DESCRIPTION
        "Timestamp" 
    ::=  { intervalPhysPerfCurrent1dayEntry 6 }

intervalPhysPerfCurrent1weekTable OBJECT-TYPE
    SYNTAX      SEQUENCE OF IntervalPhysPerfCurrent1weekEntry
    MAX-ACCESS  not-accessible
    STATUS      current
    DESCRIPTION   ""
    ::=  { performanceMonitoring 117 }

intervalPhysPerfCurrent1weekEntry OBJECT-TYPE
    SYNTAX      IntervalPhysPerfCurrent1weekEntry
    MAX-ACCESS  not-accessible
    STATUS      current
    DESCRIPTION   ""
    INDEX       {
                  entityIndex,
                  intervalPhysPerfCurrent1weekNumber
                }
    ::=  { intervalPhysPerfCurrent1weekTable 1 }

IntervalPhysPerfCurrent1weekEntry ::=  SEQUENCE
  { intervalPhysPerfCurrent1weekNumber Integer32,
    intervalPhysPerfCurrent1weekLow Unsigned32,
    intervalPhysPerfCurrent1weekMean Unsigned32,
    intervalPhysPerfCurrent1weekHigh Unsigned32,
    intervalPhysPerfCurrent1weekValidFlag TruthValue,
    intervalPhysPerfCurrent1weekTimeStamp DateAndTime }

intervalPhysPerfCurrent1weekNumber OBJECT-TYPE
    SYNTAX      Integer32 (1..52)
    MAX-ACCESS  not-accessible
    STATUS      current
    DESCRIPTION
        "Number 1week" 
    ::=  { intervalPhysPerfCurrent1weekEntry 1 }

intervalPhysPerfCurrent1weekLow OBJECT-TYPE
    SYNTAX      Unsigned32 
    UNITS       "0.001 A"
    MAX-ACCESS  read-only
    STATUS      current
    DESCRIPTION
        "Board or Pluggable Submodule Low Current" 
    ::=  { intervalPhysPerfCurrent1weekEntry 2 }

intervalPhysPerfCurrent1weekMean OBJECT-TYPE
    SYNTAX      Unsigned32 
    UNITS       "0.001 A"
    MAX-ACCESS  read-only
    STATUS      current
    DESCRIPTION
        "Board or Pluggable Submodule Mean Current" 
    ::=  { intervalPhysPerfCurrent1weekEntry 3 }

intervalPhysPerfCurrent1weekHigh OBJECT-TYPE
    SYNTAX      Unsigned32 
    UNITS       "0.001 A"
    MAX-ACCESS  read-only
    STATUS      current
    DESCRIPTION
        "Board or Pluggable Submodule High Current" 
    ::=  { intervalPhysPerfCurrent1weekEntry 4 }

intervalPhysPerfCurrent1weekValidFlag OBJECT-TYPE
    SYNTAX      TruthValue
    MAX-ACCESS  read-only
    STATUS      current
    DESCRIPTION
        "Valid Flag" 
    ::=  { intervalPhysPerfCurrent1weekEntry 5 }

intervalPhysPerfCurrent1weekTimeStamp OBJECT-TYPE
    SYNTAX      DateAndTime
    MAX-ACCESS  read-only
    STATUS      current
    DESCRIPTION
        "Timestamp" 
    ::=  { intervalPhysPerfCurrent1weekEntry 6 }

intervalPhysPerfCurrentOscGain15minTable OBJECT-TYPE
    SYNTAX      SEQUENCE OF IntervalPhysPerfCurrentOscGain15minEntry
    MAX-ACCESS  not-accessible
    STATUS      current
    DESCRIPTION   ""
    ::=  { performanceMonitoring 118 }

intervalPhysPerfCurrentOscGain15minEntry OBJECT-TYPE
    SYNTAX      IntervalPhysPerfCurrentOscGain15minEntry
    MAX-ACCESS  not-accessible
    STATUS      current
    DESCRIPTION   ""
    INDEX       {
                  entityIndex,
                  intervalPhysPerfCurrentOscGain15minNumber
                }
    ::=  { intervalPhysPerfCurrentOscGain15minTable 1 }

IntervalPhysPerfCurrentOscGain15minEntry ::=  SEQUENCE
  { intervalPhysPerfCurrentOscGain15minNumber Integer32,
    intervalPhysPerfCurrentOscGain15minLow Unsigned32,
    intervalPhysPerfCurrentOscGain15minMean Unsigned32,
    intervalPhysPerfCurrentOscGain15minHigh Unsigned32,
    intervalPhysPerfCurrentOscGain15minValidFlag TruthValue,
    intervalPhysPerfCurrentOscGain15minTimeStamp DateAndTime }

intervalPhysPerfCurrentOscGain15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfCurrentOscGain15minEntry 1 }

intervalPhysPerfCurrentOscGain15minLow OBJECT-TYPE
    SYNTAX      Unsigned32 
    UNITS       "0.1 dB"
    MAX-ACCESS  read-only
    STATUS      current
    DESCRIPTION
        "OSC Gain Low" 
    ::=  { intervalPhysPerfCurrentOscGain15minEntry 2 }

intervalPhysPerfCurrentOscGain15minMean OBJECT-TYPE
    SYNTAX      Unsigned32 
    UNITS       "0.1 dB"
    MAX-ACCESS  read-only
    STATUS      current
    DESCRIPTION
        "OSC Gain Average" 
    ::=  { intervalPhysPerfCurrentOscGain15minEntry 3 }

intervalPhysPerfCurrentOscGain15minHigh OBJECT-TYPE
    SYNTAX      Unsigned32 
    UNITS       "0.1 dB"
    MAX-ACCESS  read-only
    STATUS      current
    DESCRIPTION
        "OSC Gain High" 
    ::=  { intervalPhysPerfCurrentOscGain15minEntry 4 }

intervalPhysPerfCurrentOscGain15minValidFlag OBJECT-TYPE
    SYNTAX      TruthValue
    MAX-ACCESS  read-only
    STATUS      current
    DESCRIPTION
        "Valid Flag" 
    ::=  { intervalPhysPerfCurrentOscGain15minEntry 5 }

intervalPhysPerfCurrentOscGain15minTimeStamp OBJECT-TYPE
    SYNTAX      DateAndTime
    MAX-ACCESS  read-only
    STATUS      current
    DESCRIPTION
        "Timestamp" 
    ::=  { intervalPhysPerfCurrentOscGain15minEntry 6 }

intervalPhysPerfCurrentOscGain1dayTable OBJECT-TYPE
    SYNTAX      SEQUENCE OF IntervalPhysPerfCurrentOscGain1dayEntry
    MAX-ACCESS  not-accessible
    STATUS      current
    DESCRIPTION   ""
    ::=  { performanceMonitoring 119 }

intervalPhysPerfCurrentOscGain1dayEntry OBJECT-TYPE
    SYNTAX      IntervalPhysPerfCurrentOscGain1dayEntry
    MAX-ACCESS  not-accessible
    STATUS      current
    DESCRIPTION   ""
    INDEX       {
                  entityIndex,
                  intervalPhysPerfCurrentOscGain1dayNumber
                }
    ::=  { intervalPhysPerfCurrentOscGain1dayTable 1 }

IntervalPhysPerfCurrentOscGain1dayEntry ::=  SEQUENCE
  { intervalPhysPerfCurrentOscGain1dayNumber Integer32,
    intervalPhysPerfCurrentOscGain1dayLow Unsigned32,
    intervalPhysPerfCurrentOscGain1dayMean Unsigned32,
    intervalPhysPerfCurrentOscGain1dayHigh Unsigned32,
    intervalPhysPerfCurrentOscGain1dayValidFlag TruthValue,
    intervalPhysPerfCurrentOscGain1dayTimeStamp DateAndTime }

intervalPhysPerfCurrentOscGain1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfCurrentOscGain1dayEntry 1 }

intervalPhysPerfCurrentOscGain1dayLow OBJECT-TYPE
    SYNTAX      Unsigned32 
    UNITS       "0.1 dB"
    MAX-ACCESS  read-only
    STATUS      current
    DESCRIPTION
        "OSC Gain Low" 
    ::=  { intervalPhysPerfCurrentOscGain1dayEntry 2 }

intervalPhysPerfCurrentOscGain1dayMean OBJECT-TYPE
    SYNTAX      Unsigned32 
    UNITS       "0.1 dB"
    MAX-ACCESS  read-only
    STATUS      current
    DESCRIPTION
        "OSC Gain Average" 
    ::=  { intervalPhysPerfCurrentOscGain1dayEntry 3 }

intervalPhysPerfCurrentOscGain1dayHigh OBJECT-TYPE
    SYNTAX      Unsigned32 
    UNITS       "0.1 dB"
    MAX-ACCESS  read-only
    STATUS      current
    DESCRIPTION
        "OSC Gain High" 
    ::=  { intervalPhysPerfCurrentOscGain1dayEntry 4 }

intervalPhysPerfCurrentOscGain1dayValidFlag OBJECT-TYPE
    SYNTAX      TruthValue
    MAX-ACCESS  read-only
    STATUS      current
    DESCRIPTION
        "Valid Flag" 
    ::=  { intervalPhysPerfCurrentOscGain1dayEntry 5 }

intervalPhysPerfCurrentOscGain1dayTimeStamp OBJECT-TYPE
    SYNTAX      DateAndTime
    MAX-ACCESS  read-only
    STATUS      current
    DESCRIPTION
        "Timestamp" 
    ::=  { intervalPhysPerfCurrentOscGain1dayEntry 6 }

intervalPhysPerfCurrentOscGain1weekTable OBJECT-TYPE
    SYNTAX      SEQUENCE OF IntervalPhysPerfCurrentOscGain1weekEntry
    MAX-ACCESS  not-accessible
    STATUS      current
    DESCRIPTION   ""
    ::=  { performanceMonitoring 120 }

intervalPhysPerfCurrentOscGain1weekEntry OBJECT-TYPE
    SYNTAX      IntervalPhysPerfCurrentOscGain1weekEntry
    MAX-ACCESS  not-accessible
    STATUS      current
    DESCRIPTION   ""
    INDEX       {
                  entityIndex,
                  intervalPhysPerfCurrentOscGain1weekNumber
                }
    ::=  { intervalPhysPerfCurrentOscGain1weekTable 1 }

IntervalPhysPerfCurrentOscGain1weekEntry ::=  SEQUENCE
  { intervalPhysPerfCurrentOscGain1weekNumber Integer32,
    intervalPhysPerfCurrentOscGain1weekLow Unsigned32,
    intervalPhysPerfCurrentOscGain1weekMean Unsigned32,
    intervalPhysPerfCurrentOscGain1weekHigh Unsigned32,
    intervalPhysPerfCurrentOscGain1weekValidFlag TruthValue,
    intervalPhysPerfCurrentOscGain1weekTimeStamp DateAndTime }

intervalPhysPerfCurrentOscGain1weekNumber OBJECT-TYPE
    SYNTAX      Integer32 (1..52)
    MAX-ACCESS  not-accessible
    STATUS      current
    DESCRIPTION
        "Number 1week" 
    ::=  { intervalPhysPerfCurrentOscGain1weekEntry 1 }

intervalPhysPerfCurrentOscGain1weekLow OBJECT-TYPE
    SYNTAX      Unsigned32 
    UNITS       "0.1 dB"
    MAX-ACCESS  read-only
    STATUS      current
    DESCRIPTION
        "OSC Gain Low" 
    ::=  { intervalPhysPerfCurrentOscGain1weekEntry 2 }

intervalPhysPerfCurrentOscGain1weekMean OBJECT-TYPE
    SYNTAX      Unsigned32 
    UNITS       "0.1 dB"
    MAX-ACCESS  read-only
    STATUS      current
    DESCRIPTION
        "OSC Gain Average" 
    ::=  { intervalPhysPerfCurrentOscGain1weekEntry 3 }

intervalPhysPerfCurrentOscGain1weekHigh OBJECT-TYPE
    SYNTAX      Unsigned32 
    UNITS       "0.1 dB"
    MAX-ACCESS  read-only
    STATUS      current
    DESCRIPTION
        "OSC Gain High" 
    ::=  { intervalPhysPerfCurrentOscGain1weekEntry 4 }

intervalPhysPerfCurrentOscGain1weekValidFlag OBJECT-TYPE
    SYNTAX      TruthValue
    MAX-ACCESS  read-only
    STATUS      current
    DESCRIPTION
        "Valid Flag" 
    ::=  { intervalPhysPerfCurrentOscGain1weekEntry 5 }

intervalPhysPerfCurrentOscGain1weekTimeStamp OBJECT-TYPE
    SYNTAX      DateAndTime
    MAX-ACCESS  read-only
    STATUS      current
    DESCRIPTION
        "Timestamp" 
    ::=  { intervalPhysPerfCurrentOscGain1weekEntry 6 }

intervalPhysPerfBackreflectionPwrRcv15minTable OBJECT-TYPE
    SYNTAX      SEQUENCE OF IntervalPhysPerfBackreflectionPwrRcv15minEntry
    MAX-ACCESS  not-accessible
    STATUS      current
    DESCRIPTION   ""
    ::=  { performanceMonitoring 121 }

intervalPhysPerfBackreflectionPwrRcv15minEntry OBJECT-TYPE
    SYNTAX      IntervalPhysPerfBackreflectionPwrRcv15minEntry
    MAX-ACCESS  not-accessible
    STATUS      current
    DESCRIPTION   ""
    INDEX       {
                  entityIndex,
                  intervalPhysPerfBackreflectionPwrRcv15minNumber
                }
    ::=  { intervalPhysPerfBackreflectionPwrRcv15minTable 1 }

IntervalPhysPerfBackreflectionPwrRcv15minEntry ::=  SEQUENCE
  { intervalPhysPerfBackreflectionPwrRcv15minNumber Integer32,
    intervalPhysPerfBackreflectionPwrRcv15minLow Integer32,
    intervalPhysPerfBackreflectionPwrRcv15minMean Integer32,
    intervalPhysPerfBackreflectionPwrRcv15minHigh Integer32,
    intervalPhysPerfBackreflectionPwrRcv15minValidFlag TruthValue,
    intervalPhysPerfBackreflectionPwrRcv15minTimeStamp DateAndTime }

intervalPhysPerfBackreflectionPwrRcv15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfBackreflectionPwrRcv15minEntry 1 }

intervalPhysPerfBackreflectionPwrRcv15minLow OBJECT-TYPE
    SYNTAX      Integer32 
    UNITS       "0.1 dB"
    MAX-ACCESS  read-only
    STATUS      current
    DESCRIPTION
        "Back Reflection Received" 
    ::=  { intervalPhysPerfBackreflectionPwrRcv15minEntry 2 }

intervalPhysPerfBackreflectionPwrRcv15minMean OBJECT-TYPE
    SYNTAX      Integer32 
    UNITS       "0.1 dB"
    MAX-ACCESS  read-only
    STATUS      current
    DESCRIPTION
        "Back Reflection Received Average" 
    ::=  { intervalPhysPerfBackreflectionPwrRcv15minEntry 3 }

intervalPhysPerfBackreflectionPwrRcv15minHigh OBJECT-TYPE
    SYNTAX      Integer32 
    UNITS       "0.1 dB"
    MAX-ACCESS  read-only
    STATUS      current
    DESCRIPTION
        "Back Reflection Received High" 
    ::=  { intervalPhysPerfBackreflectionPwrRcv15minEntry 4 }

intervalPhysPerfBackreflectionPwrRcv15minValidFlag OBJECT-TYPE
    SYNTAX      TruthValue
    MAX-ACCESS  read-only
    STATUS      current
    DESCRIPTION
        "Valid Flag" 
    ::=  { intervalPhysPerfBackreflectionPwrRcv15minEntry 5 }

intervalPhysPerfBackreflectionPwrRcv15minTimeStamp OBJECT-TYPE
    SYNTAX      DateAndTime
    MAX-ACCESS  read-only
    STATUS      current
    DESCRIPTION
        "Timestamp" 
    ::=  { intervalPhysPerfBackreflectionPwrRcv15minEntry 6 }

intervalPhysPerfBackreflectionPwrRcv1dayTable OBJECT-TYPE
    SYNTAX      SEQUENCE OF IntervalPhysPerfBackreflectionPwrRcv1dayEntry
    MAX-ACCESS  not-accessible
    STATUS      current
    DESCRIPTION   ""
    ::=  { performanceMonitoring 122 }

intervalPhysPerfBackreflectionPwrRcv1dayEntry OBJECT-TYPE
    SYNTAX      IntervalPhysPerfBackreflectionPwrRcv1dayEntry
    MAX-ACCESS  not-accessible
    STATUS      current
    DESCRIPTION   ""
    INDEX       {
                  entityIndex,
                  intervalPhysPerfBackreflectionPwrRcv1dayNumber
                }
    ::=  { intervalPhysPerfBackreflectionPwrRcv1dayTable 1 }

IntervalPhysPerfBackreflectionPwrRcv1dayEntry ::=  SEQUENCE
  { intervalPhysPerfBackreflectionPwrRcv1dayNumber Integer32,
    intervalPhysPerfBackreflectionPwrRcv1dayLow Integer32,
    intervalPhysPerfBackreflectionPwrRcv1dayMean Integer32,
    intervalPhysPerfBackreflectionPwrRcv1dayHigh Integer32,
    intervalPhysPerfBackreflectionPwrRcv1dayValidFlag TruthValue,
    intervalPhysPerfBackreflectionPwrRcv1dayTimeStamp DateAndTime }

intervalPhysPerfBackreflectionPwrRcv1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfBackreflectionPwrRcv1dayEntry 1 }

intervalPhysPerfBackreflectionPwrRcv1dayLow OBJECT-TYPE
    SYNTAX      Integer32 
    UNITS       "0.1 dB"
    MAX-ACCESS  read-only
    STATUS      current
    DESCRIPTION
        "Back Reflection Received" 
    ::=  { intervalPhysPerfBackreflectionPwrRcv1dayEntry 2 }

intervalPhysPerfBackreflectionPwrRcv1dayMean OBJECT-TYPE
    SYNTAX      Integer32 
    UNITS       "0.1 dB"
    MAX-ACCESS  read-only
    STATUS      current
    DESCRIPTION
        "Back Reflection Received Average" 
    ::=  { intervalPhysPerfBackreflectionPwrRcv1dayEntry 3 }

intervalPhysPerfBackreflectionPwrRcv1dayHigh OBJECT-TYPE
    SYNTAX      Integer32 
    UNITS       "0.1 dB"
    MAX-ACCESS  read-only
    STATUS      current
    DESCRIPTION
        "Back Reflection Received High" 
    ::=  { intervalPhysPerfBackreflectionPwrRcv1dayEntry 4 }

intervalPhysPerfBackreflectionPwrRcv1dayValidFlag OBJECT-TYPE
    SYNTAX      TruthValue
    MAX-ACCESS  read-only
    STATUS      current
    DESCRIPTION
        "Valid Flag" 
    ::=  { intervalPhysPerfBackreflectionPwrRcv1dayEntry 5 }

intervalPhysPerfBackreflectionPwrRcv1dayTimeStamp OBJECT-TYPE
    SYNTAX      DateAndTime
    MAX-ACCESS  read-only
    STATUS      current
    DESCRIPTION
        "Timestamp" 
    ::=  { intervalPhysPerfBackreflectionPwrRcv1dayEntry 6 }

intervalPhysPerfBackreflectionPwrRcv1weekTable OBJECT-TYPE
    SYNTAX      SEQUENCE OF IntervalPhysPerfBackreflectionPwrRcv1weekEntry
    MAX-ACCESS  not-accessible
    STATUS      current
    DESCRIPTION   ""
    ::=  { performanceMonitoring 123 }

intervalPhysPerfBackreflectionPwrRcv1weekEntry OBJECT-TYPE
    SYNTAX      IntervalPhysPerfBackreflectionPwrRcv1weekEntry
    MAX-ACCESS  not-accessible
    STATUS      current
    DESCRIPTION   ""
    INDEX       {
                  entityIndex,
                  intervalPhysPerfBackreflectionPwrRcv1weekNumber
                }
    ::=  { intervalPhysPerfBackreflectionPwrRcv1weekTable 1 }

IntervalPhysPerfBackreflectionPwrRcv1weekEntry ::=  SEQUENCE
  { intervalPhysPerfBackreflectionPwrRcv1weekNumber Integer32,
    intervalPhysPerfBackreflectionPwrRcv1weekLow Integer32,
    intervalPhysPerfBackreflectionPwrRcv1weekMean Integer32,
    intervalPhysPerfBackreflectionPwrRcv1weekHigh Integer32,
    intervalPhysPerfBackreflectionPwrRcv1weekValidFlag TruthValue,
    intervalPhysPerfBackreflectionPwrRcv1weekTimeStamp DateAndTime }

intervalPhysPerfBackreflectionPwrRcv1weekNumber OBJECT-TYPE
    SYNTAX      Integer32 (1..52)
    MAX-ACCESS  not-accessible
    STATUS      current
    DESCRIPTION
        "Number 1week" 
    ::=  { intervalPhysPerfBackreflectionPwrRcv1weekEntry 1 }

intervalPhysPerfBackreflectionPwrRcv1weekLow OBJECT-TYPE
    SYNTAX      Integer32 
    UNITS       "0.1 dB"
    MAX-ACCESS  read-only
    STATUS      current
    DESCRIPTION
        "Back Reflection Received" 
    ::=  { intervalPhysPerfBackreflectionPwrRcv1weekEntry 2 }

intervalPhysPerfBackreflectionPwrRcv1weekMean OBJECT-TYPE
    SYNTAX      Integer32 
    UNITS       "0.1 dB"
    MAX-ACCESS  read-only
    STATUS      current
    DESCRIPTION
        "Back Reflection Received Average" 
    ::=  { intervalPhysPerfBackreflectionPwrRcv1weekEntry 3 }

intervalPhysPerfBackreflectionPwrRcv1weekHigh OBJECT-TYPE
    SYNTAX      Integer32 
    UNITS       "0.1 dB"
    MAX-ACCESS  read-only
    STATUS      current
    DESCRIPTION
        "Back Reflection Received High" 
    ::=  { intervalPhysPerfBackreflectionPwrRcv1weekEntry 4 }

intervalPhysPerfBackreflectionPwrRcv1weekValidFlag OBJECT-TYPE
    SYNTAX      TruthValue
    MAX-ACCESS  read-only
    STATUS      current
    DESCRIPTION
        "Valid Flag" 
    ::=  { intervalPhysPerfBackreflectionPwrRcv1weekEntry 5 }

intervalPhysPerfBackreflectionPwrRcv1weekTimeStamp OBJECT-TYPE
    SYNTAX      DateAndTime
    MAX-ACCESS  read-only
    STATUS      current
    DESCRIPTION
        "Timestamp" 
    ::=  { intervalPhysPerfBackreflectionPwrRcv1weekEntry 6 }

intervalPhysPerfOscPwr15minTable OBJECT-TYPE
    SYNTAX      SEQUENCE OF IntervalPhysPerfOscPwr15minEntry
    MAX-ACCESS  not-accessible
    STATUS      current
    DESCRIPTION   ""
    ::=  { performanceMonitoring 124 }

intervalPhysPerfOscPwr15minEntry OBJECT-TYPE
    SYNTAX      IntervalPhysPerfOscPwr15minEntry
    MAX-ACCESS  not-accessible
    STATUS      current
    DESCRIPTION   ""
    INDEX       {
                  entityIndex,
                  intervalPhysPerfOscPwr15minNumber
                }
    ::=  { intervalPhysPerfOscPwr15minTable 1 }

IntervalPhysPerfOscPwr15minEntry ::=  SEQUENCE
  { intervalPhysPerfOscPwr15minNumber Integer32,
    intervalPhysPerfOscPwr15minLow Integer32,
    intervalPhysPerfOscPwr15minMean Integer32,
    intervalPhysPerfOscPwr15minHigh Integer32,
    intervalPhysPerfOscPwr15minValidFlag TruthValue,
    intervalPhysPerfOscPwr15minTimeStamp DateAndTime }

intervalPhysPerfOscPwr15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfOscPwr15minEntry 1 }

intervalPhysPerfOscPwr15minLow OBJECT-TYPE
    SYNTAX      Integer32 
    UNITS       "0.1 dBm"
    MAX-ACCESS  read-only
    STATUS      current
    DESCRIPTION
        "Optical Supervisory Channel Input Power Received Low" 
    ::=  { intervalPhysPerfOscPwr15minEntry 2 }

intervalPhysPerfOscPwr15minMean OBJECT-TYPE
    SYNTAX      Integer32 
    UNITS       "0.1 dBm"
    MAX-ACCESS  read-only
    STATUS      current
    DESCRIPTION
        "Optical Supervisory Channel Input Power Received Average" 
    ::=  { intervalPhysPerfOscPwr15minEntry 3 }

intervalPhysPerfOscPwr15minHigh OBJECT-TYPE
    SYNTAX      Integer32 
    UNITS       "0.1 dBm"
    MAX-ACCESS  read-only
    STATUS      current
    DESCRIPTION
        "Optical Supervisory Channel Input Power Received High" 
    ::=  { intervalPhysPerfOscPwr15minEntry 4 }

intervalPhysPerfOscPwr15minValidFlag OBJECT-TYPE
    SYNTAX      TruthValue
    MAX-ACCESS  read-only
    STATUS      current
    DESCRIPTION
        "Valid Flag" 
    ::=  { intervalPhysPerfOscPwr15minEntry 5 }

intervalPhysPerfOscPwr15minTimeStamp OBJECT-TYPE
    SYNTAX      DateAndTime
    MAX-ACCESS  read-only
    STATUS      current
    DESCRIPTION
        "Timestamp" 
    ::=  { intervalPhysPerfOscPwr15minEntry 6 }

intervalPhysPerfOscPwr1dayTable OBJECT-TYPE
    SYNTAX      SEQUENCE OF IntervalPhysPerfOscPwr1dayEntry
    MAX-ACCESS  not-accessible
    STATUS      current
    DESCRIPTION   ""
    ::=  { performanceMonitoring 125 }

intervalPhysPerfOscPwr1dayEntry OBJECT-TYPE
    SYNTAX      IntervalPhysPerfOscPwr1dayEntry
    MAX-ACCESS  not-accessible
    STATUS      current
    DESCRIPTION   ""
    INDEX       {
                  entityIndex,
                  intervalPhysPerfOscPwr1dayNumber
                }
    ::=  { intervalPhysPerfOscPwr1dayTable 1 }

IntervalPhysPerfOscPwr1dayEntry ::=  SEQUENCE
  { intervalPhysPerfOscPwr1dayNumber Integer32,
    intervalPhysPerfOscPwr1dayLow Integer32,
    intervalPhysPerfOscPwr1dayMean Integer32,
    intervalPhysPerfOscPwr1dayHigh Integer32,
    intervalPhysPerfOscPwr1dayValidFlag TruthValue,
    intervalPhysPerfOscPwr1dayTimeStamp DateAndTime }

intervalPhysPerfOscPwr1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfOscPwr1dayEntry 1 }

intervalPhysPerfOscPwr1dayLow OBJECT-TYPE
    SYNTAX      Integer32 
    UNITS       "0.1 dBm"
    MAX-ACCESS  read-only
    STATUS      current
    DESCRIPTION
        "Optical Supervisory Channel Input Power Received Low" 
    ::=  { intervalPhysPerfOscPwr1dayEntry 2 }

intervalPhysPerfOscPwr1dayMean OBJECT-TYPE
    SYNTAX      Integer32 
    UNITS       "0.1 dBm"
    MAX-ACCESS  read-only
    STATUS      current
    DESCRIPTION
        "Optical Supervisory Channel Input Power Received Average" 
    ::=  { intervalPhysPerfOscPwr1dayEntry 3 }

intervalPhysPerfOscPwr1dayHigh OBJECT-TYPE
    SYNTAX      Integer32 
    UNITS       "0.1 dBm"
    MAX-ACCESS  read-only
    STATUS      current
    DESCRIPTION
        "Optical Supervisory Channel Input Power Received High" 
    ::=  { intervalPhysPerfOscPwr1dayEntry 4 }

intervalPhysPerfOscPwr1dayValidFlag OBJECT-TYPE
    SYNTAX      TruthValue
    MAX-ACCESS  read-only
    STATUS      current
    DESCRIPTION
        "Valid Flag" 
    ::=  { intervalPhysPerfOscPwr1dayEntry 5 }

intervalPhysPerfOscPwr1dayTimeStamp OBJECT-TYPE
    SYNTAX      DateAndTime
    MAX-ACCESS  read-only
    STATUS      current
    DESCRIPTION
        "Timestamp" 
    ::=  { intervalPhysPerfOscPwr1dayEntry 6 }

intervalPhysPerfOscPwr1weekTable OBJECT-TYPE
    SYNTAX      SEQUENCE OF IntervalPhysPerfOscPwr1weekEntry
    MAX-ACCESS  not-accessible
    STATUS      current
    DESCRIPTION   ""
    ::=  { performanceMonitoring 126 }

intervalPhysPerfOscPwr1weekEntry OBJECT-TYPE
    SYNTAX      IntervalPhysPerfOscPwr1weekEntry
    MAX-ACCESS  not-accessible
    STATUS      current
    DESCRIPTION   ""
    INDEX       {
                  entityIndex,
                  intervalPhysPerfOscPwr1weekNumber
                }
    ::=  { intervalPhysPerfOscPwr1weekTable 1 }

IntervalPhysPerfOscPwr1weekEntry ::=  SEQUENCE
  { intervalPhysPerfOscPwr1weekNumber Integer32,
    intervalPhysPerfOscPwr1weekLow Integer32,
    intervalPhysPerfOscPwr1weekMean Integer32,
    intervalPhysPerfOscPwr1weekHigh Integer32,
    intervalPhysPerfOscPwr1weekValidFlag TruthValue,
    intervalPhysPerfOscPwr1weekTimeStamp DateAndTime }

intervalPhysPerfOscPwr1weekNumber OBJECT-TYPE
    SYNTAX      Integer32 (1..52)
    MAX-ACCESS  not-accessible
    STATUS      current
    DESCRIPTION
        "Number 1week" 
    ::=  { intervalPhysPerfOscPwr1weekEntry 1 }

intervalPhysPerfOscPwr1weekLow OBJECT-TYPE
    SYNTAX      Integer32 
    UNITS       "0.1 dBm"
    MAX-ACCESS  read-only
    STATUS      current
    DESCRIPTION
        "Optical Supervisory Channel Input Power Received Low" 
    ::=  { intervalPhysPerfOscPwr1weekEntry 2 }

intervalPhysPerfOscPwr1weekMean OBJECT-TYPE
    SYNTAX      Integer32 
    UNITS       "0.1 dBm"
    MAX-ACCESS  read-only
    STATUS      current
    DESCRIPTION
        "Optical Supervisory Channel Input Power Received Average" 
    ::=  { intervalPhysPerfOscPwr1weekEntry 3 }

intervalPhysPerfOscPwr1weekHigh OBJECT-TYPE
    SYNTAX      Integer32 
    UNITS       "0.1 dBm"
    MAX-ACCESS  read-only
    STATUS      current
    DESCRIPTION
        "Optical Supervisory Channel Input Power Received High" 
    ::=  { intervalPhysPerfOscPwr1weekEntry 4 }

intervalPhysPerfOscPwr1weekValidFlag OBJECT-TYPE
    SYNTAX      TruthValue
    MAX-ACCESS  read-only
    STATUS      current
    DESCRIPTION
        "Valid Flag" 
    ::=  { intervalPhysPerfOscPwr1weekEntry 5 }

intervalPhysPerfOscPwr1weekTimeStamp OBJECT-TYPE
    SYNTAX      DateAndTime
    MAX-ACCESS  read-only
    STATUS      current
    DESCRIPTION
        "Timestamp" 
    ::=  { intervalPhysPerfOscPwr1weekEntry 6 }

intervalPhysPerfPumpPwr15minTable OBJECT-TYPE
    SYNTAX      SEQUENCE OF IntervalPhysPerfPumpPwr15minEntry
    MAX-ACCESS  not-accessible
    STATUS      current
    DESCRIPTION   ""
    ::=  { performanceMonitoring 127 }

intervalPhysPerfPumpPwr15minEntry OBJECT-TYPE
    SYNTAX      IntervalPhysPerfPumpPwr15minEntry
    MAX-ACCESS  not-accessible
    STATUS      current
    DESCRIPTION   ""
    INDEX       {
                  entityIndex,
                  intervalPhysPerfPumpPwr15minNumber
                }
    ::=  { intervalPhysPerfPumpPwr15minTable 1 }

IntervalPhysPerfPumpPwr15minEntry ::=  SEQUENCE
  { intervalPhysPerfPumpPwr15minNumber Integer32,
    intervalPhysPerfPumpPwr15minLow Integer32,
    intervalPhysPerfPumpPwr15minMean Integer32,
    intervalPhysPerfPumpPwr15minHigh Integer32,
    intervalPhysPerfPumpPwr15minValidFlag TruthValue,
    intervalPhysPerfPumpPwr15minTimeStamp DateAndTime }

intervalPhysPerfPumpPwr15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfPumpPwr15minEntry 1 }

intervalPhysPerfPumpPwr15minLow OBJECT-TYPE
    SYNTAX      Integer32 
    UNITS       "0.1 dBm"
    MAX-ACCESS  read-only
    STATUS      current
    DESCRIPTION
        "Total raman pump power low" 
    ::=  { intervalPhysPerfPumpPwr15minEntry 2 }

intervalPhysPerfPumpPwr15minMean OBJECT-TYPE
    SYNTAX      Integer32 
    UNITS       "0.1 dBm"
    MAX-ACCESS  read-only
    STATUS      current
    DESCRIPTION
        "Raman Pump Power Received Average" 
    ::=  { intervalPhysPerfPumpPwr15minEntry 3 }

intervalPhysPerfPumpPwr15minHigh OBJECT-TYPE
    SYNTAX      Integer32 
    UNITS       "0.1 dBm"
    MAX-ACCESS  read-only
    STATUS      current
    DESCRIPTION
        "Total raman pump power High" 
    ::=  { intervalPhysPerfPumpPwr15minEntry 4 }

intervalPhysPerfPumpPwr15minValidFlag OBJECT-TYPE
    SYNTAX      TruthValue
    MAX-ACCESS  read-only
    STATUS      current
    DESCRIPTION
        "Valid Flag" 
    ::=  { intervalPhysPerfPumpPwr15minEntry 5 }

intervalPhysPerfPumpPwr15minTimeStamp OBJECT-TYPE
    SYNTAX      DateAndTime
    MAX-ACCESS  read-only
    STATUS      current
    DESCRIPTION
        "Timestamp" 
    ::=  { intervalPhysPerfPumpPwr15minEntry 6 }

intervalPhysPerfPumpPwr1dayTable OBJECT-TYPE
    SYNTAX      SEQUENCE OF IntervalPhysPerfPumpPwr1dayEntry
    MAX-ACCESS  not-accessible
    STATUS      current
    DESCRIPTION   ""
    ::=  { performanceMonitoring 128 }

intervalPhysPerfPumpPwr1dayEntry OBJECT-TYPE
    SYNTAX      IntervalPhysPerfPumpPwr1dayEntry
    MAX-ACCESS  not-accessible
    STATUS      current
    DESCRIPTION   ""
    INDEX       {
                  entityIndex,
                  intervalPhysPerfPumpPwr1dayNumber
                }
    ::=  { intervalPhysPerfPumpPwr1dayTable 1 }

IntervalPhysPerfPumpPwr1dayEntry ::=  SEQUENCE
  { intervalPhysPerfPumpPwr1dayNumber Integer32,
    intervalPhysPerfPumpPwr1dayLow Integer32,
    intervalPhysPerfPumpPwr1dayMean Integer32,
    intervalPhysPerfPumpPwr1dayHigh Integer32,
    intervalPhysPerfPumpPwr1dayValidFlag TruthValue,
    intervalPhysPerfPumpPwr1dayTimeStamp DateAndTime }

intervalPhysPerfPumpPwr1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfPumpPwr1dayEntry 1 }

intervalPhysPerfPumpPwr1dayLow OBJECT-TYPE
    SYNTAX      Integer32 
    UNITS       "0.1 dBm"
    MAX-ACCESS  read-only
    STATUS      current
    DESCRIPTION
        "Total raman pump power low" 
    ::=  { intervalPhysPerfPumpPwr1dayEntry 2 }

intervalPhysPerfPumpPwr1dayMean OBJECT-TYPE
    SYNTAX      Integer32 
    UNITS       "0.1 dBm"
    MAX-ACCESS  read-only
    STATUS      current
    DESCRIPTION
        "Raman Pump Power Received Average" 
    ::=  { intervalPhysPerfPumpPwr1dayEntry 3 }

intervalPhysPerfPumpPwr1dayHigh OBJECT-TYPE
    SYNTAX      Integer32 
    UNITS       "0.1 dBm"
    MAX-ACCESS  read-only
    STATUS      current
    DESCRIPTION
        "Total raman pump power High" 
    ::=  { intervalPhysPerfPumpPwr1dayEntry 4 }

intervalPhysPerfPumpPwr1dayValidFlag OBJECT-TYPE
    SYNTAX      TruthValue
    MAX-ACCESS  read-only
    STATUS      current
    DESCRIPTION
        "Valid Flag" 
    ::=  { intervalPhysPerfPumpPwr1dayEntry 5 }

intervalPhysPerfPumpPwr1dayTimeStamp OBJECT-TYPE
    SYNTAX      DateAndTime
    MAX-ACCESS  read-only
    STATUS      current
    DESCRIPTION
        "Timestamp" 
    ::=  { intervalPhysPerfPumpPwr1dayEntry 6 }

intervalPhysPerfPumpPwr1weekTable OBJECT-TYPE
    SYNTAX      SEQUENCE OF IntervalPhysPerfPumpPwr1weekEntry
    MAX-ACCESS  not-accessible
    STATUS      current
    DESCRIPTION   ""
    ::=  { performanceMonitoring 129 }

intervalPhysPerfPumpPwr1weekEntry OBJECT-TYPE
    SYNTAX      IntervalPhysPerfPumpPwr1weekEntry
    MAX-ACCESS  not-accessible
    STATUS      current
    DESCRIPTION   ""
    INDEX       {
                  entityIndex,
                  intervalPhysPerfPumpPwr1weekNumber
                }
    ::=  { intervalPhysPerfPumpPwr1weekTable 1 }

IntervalPhysPerfPumpPwr1weekEntry ::=  SEQUENCE
  { intervalPhysPerfPumpPwr1weekNumber Integer32,
    intervalPhysPerfPumpPwr1weekLow Integer32,
    intervalPhysPerfPumpPwr1weekMean Integer32,
    intervalPhysPerfPumpPwr1weekHigh Integer32,
    intervalPhysPerfPumpPwr1weekValidFlag TruthValue,
    intervalPhysPerfPumpPwr1weekTimeStamp DateAndTime }

intervalPhysPerfPumpPwr1weekNumber OBJECT-TYPE
    SYNTAX      Integer32 (1..52)
    MAX-ACCESS  not-accessible
    STATUS      current
    DESCRIPTION
        "Number 1week" 
    ::=  { intervalPhysPerfPumpPwr1weekEntry 1 }

intervalPhysPerfPumpPwr1weekLow OBJECT-TYPE
    SYNTAX      Integer32 
    UNITS       "0.1 dBm"
    MAX-ACCESS  read-only
    STATUS      current
    DESCRIPTION
        "Total raman pump power low" 
    ::=  { intervalPhysPerfPumpPwr1weekEntry 2 }

intervalPhysPerfPumpPwr1weekMean OBJECT-TYPE
    SYNTAX      Integer32 
    UNITS       "0.1 dBm"
    MAX-ACCESS  read-only
    STATUS      current
    DESCRIPTION
        "Raman Pump Power Received Average" 
    ::=  { intervalPhysPerfPumpPwr1weekEntry 3 }

intervalPhysPerfPumpPwr1weekHigh OBJECT-TYPE
    SYNTAX      Integer32 
    UNITS       "0.1 dBm"
    MAX-ACCESS  read-only
    STATUS      current
    DESCRIPTION
        "Total raman pump power High" 
    ::=  { intervalPhysPerfPumpPwr1weekEntry 4 }

intervalPhysPerfPumpPwr1weekValidFlag OBJECT-TYPE
    SYNTAX      TruthValue
    MAX-ACCESS  read-only
    STATUS      current
    DESCRIPTION
        "Valid Flag" 
    ::=  { intervalPhysPerfPumpPwr1weekEntry 5 }

intervalPhysPerfPumpPwr1weekTimeStamp OBJECT-TYPE
    SYNTAX      DateAndTime
    MAX-ACCESS  read-only
    STATUS      current
    DESCRIPTION
        "Timestamp" 
    ::=  { intervalPhysPerfPumpPwr1weekEntry 6 }

intervalDispersionCompensation15minTable OBJECT-TYPE
    SYNTAX      SEQUENCE OF IntervalDispersionCompensation15minEntry
    MAX-ACCESS  not-accessible
    STATUS      current
    DESCRIPTION   ""
    ::=  { performanceMonitoring 130 }

intervalDispersionCompensation15minEntry OBJECT-TYPE
    SYNTAX      IntervalDispersionCompensation15minEntry
    MAX-ACCESS  not-accessible
    STATUS      current
    DESCRIPTION   ""
    INDEX       {
                  entityIndex,
                  intervalDispersionCompensation15minNumber
                }
    ::=  { intervalDispersionCompensation15minTable 1 }

IntervalDispersionCompensation15minEntry ::=  SEQUENCE
  { intervalDispersionCompensation15minNumber Integer32,
    intervalDispersionCompensation15minLow Integer32,
    intervalDispersionCompensation15minMean Integer32,
    intervalDispersionCompensation15minHigh Integer32,
    intervalDispersionCompensation15minValidFlag TruthValue,
    intervalDispersionCompensation15minTimeStamp DateAndTime }

intervalDispersionCompensation15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalDispersionCompensation15minEntry 1 }

intervalDispersionCompensation15minLow OBJECT-TYPE
    SYNTAX      Integer32 
    UNITS       "ps/nm"
    MAX-ACCESS  read-only
    STATUS      current
    DESCRIPTION
        "Chromatic Dispersion Compensation Low" 
    ::=  { intervalDispersionCompensation15minEntry 2 }

intervalDispersionCompensation15minMean OBJECT-TYPE
    SYNTAX      Integer32 
    UNITS       "ps/nm"
    MAX-ACCESS  read-only
    STATUS      current
    DESCRIPTION
        "Chromatic Dispersion Compensation Mean" 
    ::=  { intervalDispersionCompensation15minEntry 3 }

intervalDispersionCompensation15minHigh OBJECT-TYPE
    SYNTAX      Integer32 
    UNITS       "ps/nm"
    MAX-ACCESS  read-only
    STATUS      current
    DESCRIPTION
        "Chromatic Dispersion Compensation High" 
    ::=  { intervalDispersionCompensation15minEntry 4 }

intervalDispersionCompensation15minValidFlag OBJECT-TYPE
    SYNTAX      TruthValue
    MAX-ACCESS  read-only
    STATUS      current
    DESCRIPTION
        "Valid Flag" 
    ::=  { intervalDispersionCompensation15minEntry 5 }

intervalDispersionCompensation15minTimeStamp OBJECT-TYPE
    SYNTAX      DateAndTime
    MAX-ACCESS  read-only
    STATUS      current
    DESCRIPTION
        "Timestamp" 
    ::=  { intervalDispersionCompensation15minEntry 6 }

intervalDispersionCompensation1dayTable OBJECT-TYPE
    SYNTAX      SEQUENCE OF IntervalDispersionCompensation1dayEntry
    MAX-ACCESS  not-accessible
    STATUS      current
    DESCRIPTION   ""
    ::=  { performanceMonitoring 131 }

intervalDispersionCompensation1dayEntry OBJECT-TYPE
    SYNTAX      IntervalDispersionCompensation1dayEntry
    MAX-ACCESS  not-accessible
    STATUS      current
    DESCRIPTION   ""
    INDEX       {
                  entityIndex,
                  intervalDispersionCompensation1dayNumber
                }
    ::=  { intervalDispersionCompensation1dayTable 1 }

IntervalDispersionCompensation1dayEntry ::=  SEQUENCE
  { intervalDispersionCompensation1dayNumber Integer32,
    intervalDispersionCompensation1dayLow Integer32,
    intervalDispersionCompensation1dayMean Integer32,
    intervalDispersionCompensation1dayHigh Integer32,
    intervalDispersionCompensation1dayValidFlag TruthValue,
    intervalDispersionCompensation1dayTimeStamp DateAndTime }

intervalDispersionCompensation1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalDispersionCompensation1dayEntry 1 }

intervalDispersionCompensation1dayLow OBJECT-TYPE
    SYNTAX      Integer32 
    UNITS       "ps/nm"
    MAX-ACCESS  read-only
    STATUS      current
    DESCRIPTION
        "Chromatic Dispersion Compensation Low" 
    ::=  { intervalDispersionCompensation1dayEntry 2 }

intervalDispersionCompensation1dayMean OBJECT-TYPE
    SYNTAX      Integer32 
    UNITS       "ps/nm"
    MAX-ACCESS  read-only
    STATUS      current
    DESCRIPTION
        "Chromatic Dispersion Compensation Mean" 
    ::=  { intervalDispersionCompensation1dayEntry 3 }

intervalDispersionCompensation1dayHigh OBJECT-TYPE
    SYNTAX      Integer32 
    UNITS       "ps/nm"
    MAX-ACCESS  read-only
    STATUS      current
    DESCRIPTION
        "Chromatic Dispersion Compensation High" 
    ::=  { intervalDispersionCompensation1dayEntry 4 }

intervalDispersionCompensation1dayValidFlag OBJECT-TYPE
    SYNTAX      TruthValue
    MAX-ACCESS  read-only
    STATUS      current
    DESCRIPTION
        "Valid Flag" 
    ::=  { intervalDispersionCompensation1dayEntry 5 }

intervalDispersionCompensation1dayTimeStamp OBJECT-TYPE
    SYNTAX      DateAndTime
    MAX-ACCESS  read-only
    STATUS      current
    DESCRIPTION
        "Timestamp" 
    ::=  { intervalDispersionCompensation1dayEntry 6 }

intervalDispersionCompensation1weekTable OBJECT-TYPE
    SYNTAX      SEQUENCE OF IntervalDispersionCompensation1weekEntry
    MAX-ACCESS  not-accessible
    STATUS      current
    DESCRIPTION   ""
    ::=  { performanceMonitoring 132 }

intervalDispersionCompensation1weekEntry OBJECT-TYPE
    SYNTAX      IntervalDispersionCompensation1weekEntry
    MAX-ACCESS  not-accessible
    STATUS      current
    DESCRIPTION   ""
    INDEX       {
                  entityIndex,
                  intervalDispersionCompensation1weekNumber
                }
    ::=  { intervalDispersionCompensation1weekTable 1 }

IntervalDispersionCompensation1weekEntry ::=  SEQUENCE
  { intervalDispersionCompensation1weekNumber Integer32,
    intervalDispersionCompensation1weekLow Integer32,
    intervalDispersionCompensation1weekMean Integer32,
    intervalDispersionCompensation1weekHigh Integer32,
    intervalDispersionCompensation1weekValidFlag TruthValue,
    intervalDispersionCompensation1weekTimeStamp DateAndTime }

intervalDispersionCompensation1weekNumber OBJECT-TYPE
    SYNTAX      Integer32 (1..52)
    MAX-ACCESS  not-accessible
    STATUS      current
    DESCRIPTION
        "Number 1week" 
    ::=  { intervalDispersionCompensation1weekEntry 1 }

intervalDispersionCompensation1weekLow OBJECT-TYPE
    SYNTAX      Integer32 
    UNITS       "ps/nm"
    MAX-ACCESS  read-only
    STATUS      current
    DESCRIPTION
        "Chromatic Dispersion Compensation Low" 
    ::=  { intervalDispersionCompensation1weekEntry 2 }

intervalDispersionCompensation1weekMean OBJECT-TYPE
    SYNTAX      Integer32 
    UNITS       "ps/nm"
    MAX-ACCESS  read-only
    STATUS      current
    DESCRIPTION
        "Chromatic Dispersion Compensation Mean" 
    ::=  { intervalDispersionCompensation1weekEntry 3 }

intervalDispersionCompensation1weekHigh OBJECT-TYPE
    SYNTAX      Integer32 
    UNITS       "ps/nm"
    MAX-ACCESS  read-only
    STATUS      current
    DESCRIPTION
        "Chromatic Dispersion Compensation High" 
    ::=  { intervalDispersionCompensation1weekEntry 4 }

intervalDispersionCompensation1weekValidFlag OBJECT-TYPE
    SYNTAX      TruthValue
    MAX-ACCESS  read-only
    STATUS      current
    DESCRIPTION
        "Valid Flag" 
    ::=  { intervalDispersionCompensation1weekEntry 5 }

intervalDispersionCompensation1weekTimeStamp OBJECT-TYPE
    SYNTAX      DateAndTime
    MAX-ACCESS  read-only
    STATUS      current
    DESCRIPTION
        "Timestamp" 
    ::=  { intervalDispersionCompensation1weekEntry 6 }

intervalLinkAttenuation15minTable OBJECT-TYPE
    SYNTAX      SEQUENCE OF IntervalLinkAttenuation15minEntry
    MAX-ACCESS  not-accessible
    STATUS      current
    DESCRIPTION   ""
    ::=  { performanceMonitoring 133 }

intervalLinkAttenuation15minEntry OBJECT-TYPE
    SYNTAX      IntervalLinkAttenuation15minEntry
    MAX-ACCESS  not-accessible
    STATUS      current
    DESCRIPTION   ""
    INDEX       {
                  entityIndex,
                  intervalLinkAttenuation15minNumber
                }
    ::=  { intervalLinkAttenuation15minTable 1 }

IntervalLinkAttenuation15minEntry ::=  SEQUENCE
  { intervalLinkAttenuation15minNumber Integer32,
    intervalLinkAttenuation15minLow Integer32,
    intervalLinkAttenuation15minMean Integer32,
    intervalLinkAttenuation15minHigh Integer32,
    intervalLinkAttenuation15minValidFlag TruthValue,
    intervalLinkAttenuation15minTimeStamp DateAndTime }

intervalLinkAttenuation15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalLinkAttenuation15minEntry 1 }

intervalLinkAttenuation15minLow OBJECT-TYPE
    SYNTAX      Integer32 
    UNITS       "0.1 dB"
    MAX-ACCESS  read-only
    STATUS      current
    DESCRIPTION
        "Link Attenuation Low" 
    ::=  { intervalLinkAttenuation15minEntry 2 }

intervalLinkAttenuation15minMean OBJECT-TYPE
    SYNTAX      Integer32 
    UNITS       "0.1 dB"
    MAX-ACCESS  read-only
    STATUS      current
    DESCRIPTION
        "Link Attenuation Mean" 
    ::=  { intervalLinkAttenuation15minEntry 3 }

intervalLinkAttenuation15minHigh OBJECT-TYPE
    SYNTAX      Integer32 
    UNITS       "0.1 dB"
    MAX-ACCESS  read-only
    STATUS      current
    DESCRIPTION
        "Link Attenuation High" 
    ::=  { intervalLinkAttenuation15minEntry 4 }

intervalLinkAttenuation15minValidFlag OBJECT-TYPE
    SYNTAX      TruthValue
    MAX-ACCESS  read-only
    STATUS      current
    DESCRIPTION
        "Valid Flag" 
    ::=  { intervalLinkAttenuation15minEntry 5 }

intervalLinkAttenuation15minTimeStamp OBJECT-TYPE
    SYNTAX      DateAndTime
    MAX-ACCESS  read-only
    STATUS      current
    DESCRIPTION
        "Timestamp" 
    ::=  { intervalLinkAttenuation15minEntry 6 }

intervalLinkAttenuation1dayTable OBJECT-TYPE
    SYNTAX      SEQUENCE OF IntervalLinkAttenuation1dayEntry
    MAX-ACCESS  not-accessible
    STATUS      current
    DESCRIPTION   ""
    ::=  { performanceMonitoring 134 }

intervalLinkAttenuation1dayEntry OBJECT-TYPE
    SYNTAX      IntervalLinkAttenuation1dayEntry
    MAX-ACCESS  not-accessible
    STATUS      current
    DESCRIPTION   ""
    INDEX       {
                  entityIndex,
                  intervalLinkAttenuation1dayNumber
                }
    ::=  { intervalLinkAttenuation1dayTable 1 }

IntervalLinkAttenuation1dayEntry ::=  SEQUENCE
  { intervalLinkAttenuation1dayNumber Integer32,
    intervalLinkAttenuation1dayLow Integer32,
    intervalLinkAttenuation1dayMean Integer32,
    intervalLinkAttenuation1dayHigh Integer32,
    intervalLinkAttenuation1dayValidFlag TruthValue,
    intervalLinkAttenuation1dayTimeStamp DateAndTime }

intervalLinkAttenuation1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalLinkAttenuation1dayEntry 1 }

intervalLinkAttenuation1dayLow OBJECT-TYPE
    SYNTAX      Integer32 
    UNITS       "0.1 dB"
    MAX-ACCESS  read-only
    STATUS      current
    DESCRIPTION
        "Link Attenuation Low" 
    ::=  { intervalLinkAttenuation1dayEntry 2 }

intervalLinkAttenuation1dayMean OBJECT-TYPE
    SYNTAX      Integer32 
    UNITS       "0.1 dB"
    MAX-ACCESS  read-only
    STATUS      current
    DESCRIPTION
        "Link Attenuation Mean" 
    ::=  { intervalLinkAttenuation1dayEntry 3 }

intervalLinkAttenuation1dayHigh OBJECT-TYPE
    SYNTAX      Integer32 
    UNITS       "0.1 dB"
    MAX-ACCESS  read-only
    STATUS      current
    DESCRIPTION
        "Link Attenuation High" 
    ::=  { intervalLinkAttenuation1dayEntry 4 }

intervalLinkAttenuation1dayValidFlag OBJECT-TYPE
    SYNTAX      TruthValue
    MAX-ACCESS  read-only
    STATUS      current
    DESCRIPTION
        "Valid Flag" 
    ::=  { intervalLinkAttenuation1dayEntry 5 }

intervalLinkAttenuation1dayTimeStamp OBJECT-TYPE
    SYNTAX      DateAndTime
    MAX-ACCESS  read-only
    STATUS      current
    DESCRIPTION
        "Timestamp" 
    ::=  { intervalLinkAttenuation1dayEntry 6 }

intervalLinkAttenuation1weekTable OBJECT-TYPE
    SYNTAX      SEQUENCE OF IntervalLinkAttenuation1weekEntry
    MAX-ACCESS  not-accessible
    STATUS      current
    DESCRIPTION   ""
    ::=  { performanceMonitoring 135 }

intervalLinkAttenuation1weekEntry OBJECT-TYPE
    SYNTAX      IntervalLinkAttenuation1weekEntry
    MAX-ACCESS  not-accessible
    STATUS      current
    DESCRIPTION   ""
    INDEX       {
                  entityIndex,
                  intervalLinkAttenuation1weekNumber
                }
    ::=  { intervalLinkAttenuation1weekTable 1 }

IntervalLinkAttenuation1weekEntry ::=  SEQUENCE
  { intervalLinkAttenuation1weekNumber Integer32,
    intervalLinkAttenuation1weekLow Integer32,
    intervalLinkAttenuation1weekMean Integer32,
    intervalLinkAttenuation1weekHigh Integer32,
    intervalLinkAttenuation1weekValidFlag TruthValue,
    intervalLinkAttenuation1weekTimeStamp DateAndTime }

intervalLinkAttenuation1weekNumber OBJECT-TYPE
    SYNTAX      Integer32 (1..52)
    MAX-ACCESS  not-accessible
    STATUS      current
    DESCRIPTION
        "Number 1week" 
    ::=  { intervalLinkAttenuation1weekEntry 1 }

intervalLinkAttenuation1weekLow OBJECT-TYPE
    SYNTAX      Integer32 
    UNITS       "0.1 dB"
    MAX-ACCESS  read-only
    STATUS      current
    DESCRIPTION
        "Link Attenuation Low" 
    ::=  { intervalLinkAttenuation1weekEntry 2 }

intervalLinkAttenuation1weekMean OBJECT-TYPE
    SYNTAX      Integer32 
    UNITS       "0.1 dB"
    MAX-ACCESS  read-only
    STATUS      current
    DESCRIPTION
        "Link Attenuation Mean" 
    ::=  { intervalLinkAttenuation1weekEntry 3 }

intervalLinkAttenuation1weekHigh OBJECT-TYPE
    SYNTAX      Integer32 
    UNITS       "0.1 dB"
    MAX-ACCESS  read-only
    STATUS      current
    DESCRIPTION
        "Link Attenuation High" 
    ::=  { intervalLinkAttenuation1weekEntry 4 }

intervalLinkAttenuation1weekValidFlag OBJECT-TYPE
    SYNTAX      TruthValue
    MAX-ACCESS  read-only
    STATUS      current
    DESCRIPTION
        "Valid Flag" 
    ::=  { intervalLinkAttenuation1weekEntry 5 }

intervalLinkAttenuation1weekTimeStamp OBJECT-TYPE
    SYNTAX      DateAndTime
    MAX-ACCESS  read-only
    STATUS      current
    DESCRIPTION
        "Timestamp" 
    ::=  { intervalLinkAttenuation1weekEntry 6 }

currentL2EthRx15minTable OBJECT-TYPE
    SYNTAX      SEQUENCE OF CurrentL2EthRx15minEntry
    MAX-ACCESS  not-accessible
    STATUS      current
    DESCRIPTION   ""
    ::=  { performanceMonitoring 136 }

currentL2EthRx15minEntry OBJECT-TYPE
    SYNTAX      CurrentL2EthRx15minEntry
    MAX-ACCESS  not-accessible
    STATUS      current
    DESCRIPTION   ""
    INDEX       {
                  entityIndex
                }
    ::=  { currentL2EthRx15minTable 1 }

CurrentL2EthRx15minEntry ::=  SEQUENCE
  { currentL2EthRx15minFramesRcv Counter64String,
    currentL2EthRx15minBytesRcv Counter64String,
    currentL2EthRx15minBroadcastFramesRcv Counter64String,
    currentL2EthRx15minMulticastFramesRcv Counter64String,
    currentL2EthRx15minCrcErrorsRcv Counter64String,
    currentL2EthRx15minUndersizedFramesRcv Counter64String,
    currentL2EthRx15minOversizedFramesRcv Counter64String,
    currentL2EthRx15minPauseFramesRcv Counter64String,
    currentL2EthRx15minBytesFrames64Rcv Counter64String,
    currentL2EthRx15minBytesFrames65Rcv Counter64String,
    currentL2EthRx15minBytesFrames128Rcv Counter64String,
    currentL2EthRx15minBytesFrames256Rcv Counter64String,
    currentL2EthRx15minBytesFrames512Rcv Counter64String,
    currentL2EthRx15minBytesFrames1024Rcv Counter64String,
    currentL2EthRx15minBytesFrames1519Rcv Counter64String,
    currentL2EthRx15minInterPackJunkBytesFramesRcv Counter64String,
    currentL2EthRx15minElapsedTime Integer32 }

currentL2EthRx15minFramesRcv OBJECT-TYPE
    SYNTAX      Counter64String
    MAX-ACCESS  read-only
    STATUS      current
    DESCRIPTION
        "Frames Received" 
    ::=  { currentL2EthRx15minEntry 1 }

currentL2EthRx15minBytesRcv OBJECT-TYPE
    SYNTAX      Counter64String
    MAX-ACCESS  read-only
    STATUS      current
    DESCRIPTION
        "Bytes Received" 
    ::=  { currentL2EthRx15minEntry 2 }

currentL2EthRx15minBroadcastFramesRcv OBJECT-TYPE
    SYNTAX      Counter64String
    MAX-ACCESS  read-only
    STATUS      current
    DESCRIPTION
        "Broadcast Frames Received" 
    ::=  { currentL2EthRx15minEntry 3 }

currentL2EthRx15minMulticastFramesRcv OBJECT-TYPE
    SYNTAX      Counter64String
    MAX-ACCESS  read-only
    STATUS      current
    DESCRIPTION
        "Multicast Frames Received" 
    ::=  { currentL2EthRx15minEntry 4 }

currentL2EthRx15minCrcErrorsRcv OBJECT-TYPE
    SYNTAX      Counter64String
    MAX-ACCESS  read-only
    STATUS      current
    DESCRIPTION
        "Received CRC Errors" 
    ::=  { currentL2EthRx15minEntry 5 }

currentL2EthRx15minUndersizedFramesRcv OBJECT-TYPE
    SYNTAX      Counter64String
    MAX-ACCESS  read-only
    STATUS      current
    DESCRIPTION
        "Undersized Frames Received" 
    ::=  { currentL2EthRx15minEntry 6 }

currentL2EthRx15minOversizedFramesRcv OBJECT-TYPE
    SYNTAX      Counter64String
    MAX-ACCESS  read-only
    STATUS      current
    DESCRIPTION
        "Oversized Frames Received" 
    ::=  { currentL2EthRx15minEntry 7 }

currentL2EthRx15minPauseFramesRcv OBJECT-TYPE
    SYNTAX      Counter64String
    MAX-ACCESS  read-only
    STATUS      current
    DESCRIPTION
        "Pause Frames Received" 
    ::=  { currentL2EthRx15minEntry 8 }

currentL2EthRx15minBytesFrames64Rcv OBJECT-TYPE
    SYNTAX      Counter64String
    MAX-ACCESS  read-only
    STATUS      current
    DESCRIPTION
        "64 Byte Frames Received" 
    ::=  { currentL2EthRx15minEntry 9 }

currentL2EthRx15minBytesFrames65Rcv OBJECT-TYPE
    SYNTAX      Counter64String
    MAX-ACCESS  read-only
    STATUS      current
    DESCRIPTION
        "65-127 Byte Frames Received" 
    ::=  { currentL2EthRx15minEntry 10 }

currentL2EthRx15minBytesFrames128Rcv OBJECT-TYPE
    SYNTAX      Counter64String
    MAX-ACCESS  read-only
    STATUS      current
    DESCRIPTION
        "128-255 Byte Frames Received" 
    ::=  { currentL2EthRx15minEntry 11 }

currentL2EthRx15minBytesFrames256Rcv OBJECT-TYPE
    SYNTAX      Counter64String
    MAX-ACCESS  read-only
    STATUS      current
    DESCRIPTION
        "256-511 Byte Frames Received" 
    ::=  { currentL2EthRx15minEntry 12 }

currentL2EthRx15minBytesFrames512Rcv OBJECT-TYPE
    SYNTAX      Counter64String
    MAX-ACCESS  read-only
    STATUS      current
    DESCRIPTION
        "512-1023 Byte Frames Received" 
    ::=  { currentL2EthRx15minEntry 13 }

currentL2EthRx15minBytesFrames1024Rcv OBJECT-TYPE
    SYNTAX      Counter64String
    MAX-ACCESS  read-only
    STATUS      current
    DESCRIPTION
        "1024-1518 Byte Frames Received" 
    ::=  { currentL2EthRx15minEntry 14 }

currentL2EthRx15minBytesFrames1519Rcv OBJECT-TYPE
    SYNTAX      Counter64String
    MAX-ACCESS  read-only
    STATUS      current
    DESCRIPTION
        "1519-Max Byte Frames Received" 
    ::=  { currentL2EthRx15minEntry 15 }

currentL2EthRx15minInterPackJunkBytesFramesRcv OBJECT-TYPE
    SYNTAX      Counter64String
    MAX-ACCESS  read-only
    STATUS      current
    DESCRIPTION
        "InterPackJunk Bytes Frames Received (10Gbit/s only)" 
    ::=  { currentL2EthRx15minEntry 16 }

currentL2EthRx15minElapsedTime OBJECT-TYPE
    SYNTAX      Integer32 (0..9000 | -2147483648)
    MAX-ACCESS  read-only
    STATUS      current
    DESCRIPTION
        "Elapsed 15Min" 
    ::=  { currentL2EthRx15minEntry 17 }

currentL2EthRx1dayTable OBJECT-TYPE
    SYNTAX      SEQUENCE OF CurrentL2EthRx1dayEntry
    MAX-ACCESS  not-accessible
    STATUS      current
    DESCRIPTION   ""
    ::=  { performanceMonitoring 137 }

currentL2EthRx1dayEntry OBJECT-TYPE
    SYNTAX      CurrentL2EthRx1dayEntry
    MAX-ACCESS  not-accessible
    STATUS      current
    DESCRIPTION   ""
    INDEX       {
                  entityIndex
                }
    ::=  { currentL2EthRx1dayTable 1 }

CurrentL2EthRx1dayEntry ::=  SEQUENCE
  { currentL2EthRx1dayFramesRcv Counter64String,
    currentL2EthRx1dayBytesRcv Counter64String,
    currentL2EthRx1dayBroadcastFramesRcv Counter64String,
    currentL2EthRx1dayMulticastFramesRcv Counter64String,
    currentL2EthRx1dayCrcErrorsRcv Counter64String,
    currentL2EthRx1dayUndersizedFramesRcv Counter64String,
    currentL2EthRx1dayOversizedFramesRcv Counter64String,
    currentL2EthRx1dayPauseFramesRcv Counter64String,
    currentL2EthRx1dayBytesFrames64Rcv Counter64String,
    currentL2EthRx1dayBytesFrames65Rcv Counter64String,
    currentL2EthRx1dayBytesFrames128Rcv Counter64String,
    currentL2EthRx1dayBytesFrames256Rcv Counter64String,
    currentL2EthRx1dayBytesFrames512Rcv Counter64String,
    currentL2EthRx1dayBytesFrames1024Rcv Counter64String,
    currentL2EthRx1dayBytesFrames1519Rcv Counter64String,
    currentL2EthRx1dayInterPackJunkBytesFramesRcv Counter64String,
    currentL2EthRx1dayElapsedTime Integer32 }

currentL2EthRx1dayFramesRcv OBJECT-TYPE
    SYNTAX      Counter64String
    MAX-ACCESS  read-only
    STATUS      current
    DESCRIPTION
        "Frames Received" 
    ::=  { currentL2EthRx1dayEntry 1 }

currentL2EthRx1dayBytesRcv OBJECT-TYPE
    SYNTAX      Counter64String
    MAX-ACCESS  read-only
    STATUS      current
    DESCRIPTION
        "Bytes Received" 
    ::=  { currentL2EthRx1dayEntry 2 }

currentL2EthRx1dayBroadcastFramesRcv OBJECT-TYPE
    SYNTAX      Counter64String
    MAX-ACCESS  read-only
    STATUS      current
    DESCRIPTION
        "Broadcast Frames Received" 
    ::=  { currentL2EthRx1dayEntry 3 }

currentL2EthRx1dayMulticastFramesRcv OBJECT-TYPE
    SYNTAX      Counter64String
    MAX-ACCESS  read-only
    STATUS      current
    DESCRIPTION
        "Multicast Frames Received" 
    ::=  { currentL2EthRx1dayEntry 4 }

currentL2EthRx1dayCrcErrorsRcv OBJECT-TYPE
    SYNTAX      Counter64String
    MAX-ACCESS  read-only
    STATUS      current
    DESCRIPTION
        "Received CRC Errors" 
    ::=  { currentL2EthRx1dayEntry 5 }

currentL2EthRx1dayUndersizedFramesRcv OBJECT-TYPE
    SYNTAX      Counter64String
    MAX-ACCESS  read-only
    STATUS      current
    DESCRIPTION
        "Undersized Frames Received" 
    ::=  { currentL2EthRx1dayEntry 6 }

currentL2EthRx1dayOversizedFramesRcv OBJECT-TYPE
    SYNTAX      Counter64String
    MAX-ACCESS  read-only
    STATUS      current
    DESCRIPTION
        "Oversized Frames Received" 
    ::=  { currentL2EthRx1dayEntry 7 }

currentL2EthRx1dayPauseFramesRcv OBJECT-TYPE
    SYNTAX      Counter64String
    MAX-ACCESS  read-only
    STATUS      current
    DESCRIPTION
        "Pause Frames Received" 
    ::=  { currentL2EthRx1dayEntry 8 }

currentL2EthRx1dayBytesFrames64Rcv OBJECT-TYPE
    SYNTAX      Counter64String
    MAX-ACCESS  read-only
    STATUS      current
    DESCRIPTION
        "64 Byte Frames Received" 
    ::=  { currentL2EthRx1dayEntry 9 }

currentL2EthRx1dayBytesFrames65Rcv OBJECT-TYPE
    SYNTAX      Counter64String
    MAX-ACCESS  read-only
    STATUS      current
    DESCRIPTION
        "65-127 Byte Frames Received" 
    ::=  { currentL2EthRx1dayEntry 10 }

currentL2EthRx1dayBytesFrames128Rcv OBJECT-TYPE
    SYNTAX      Counter64String
    MAX-ACCESS  read-only
    STATUS      current
    DESCRIPTION
        "128-255 Byte Frames Received" 
    ::=  { currentL2EthRx1dayEntry 11 }

currentL2EthRx1dayBytesFrames256Rcv OBJECT-TYPE
    SYNTAX      Counter64String
    MAX-ACCESS  read-only
    STATUS      current
    DESCRIPTION
        "256-511 Byte Frames Received" 
    ::=  { currentL2EthRx1dayEntry 12 }

currentL2EthRx1dayBytesFrames512Rcv OBJECT-TYPE
    SYNTAX      Counter64String
    MAX-ACCESS  read-only
    STATUS      current
    DESCRIPTION
        "512-1023 Byte Frames Received" 
    ::=  { currentL2EthRx1dayEntry 13 }

currentL2EthRx1dayBytesFrames1024Rcv OBJECT-TYPE
    SYNTAX      Counter64String
    MAX-ACCESS  read-only
    STATUS      current
    DESCRIPTION
        "1024-1518 Byte Frames Received" 
    ::=  { currentL2EthRx1dayEntry 14 }

currentL2EthRx1dayBytesFrames1519Rcv OBJECT-TYPE
    SYNTAX      Counter64String
    MAX-ACCESS  read-only
    STATUS      current
    DESCRIPTION
        "1519-Max Byte Frames Received" 
    ::=  { currentL2EthRx1dayEntry 15 }

currentL2EthRx1dayInterPackJunkBytesFramesRcv OBJECT-TYPE
    SYNTAX      Counter64String
    MAX-ACCESS  read-only
    STATUS      current
    DESCRIPTION
        "InterPackJunk Bytes Frames Received (10Gbit/s only)" 
    ::=  { currentL2EthRx1dayEntry 16 }

currentL2EthRx1dayElapsedTime OBJECT-TYPE
    SYNTAX      Integer32 (0..86400 | -2147483648)
    MAX-ACCESS  read-only
    STATUS      current
    DESCRIPTION
        "Elapsed 1Day" 
    ::=  { currentL2EthRx1dayEntry 17 }

intervalL2EthRx15minTable OBJECT-TYPE
    SYNTAX      SEQUENCE OF IntervalL2EthRx15minEntry
    MAX-ACCESS  not-accessible
    STATUS      current
    DESCRIPTION   ""
    ::=  { performanceMonitoring 138 }

intervalL2EthRx15minEntry OBJECT-TYPE
    SYNTAX      IntervalL2EthRx15minEntry
    MAX-ACCESS  not-accessible
    STATUS      current
    DESCRIPTION   ""
    INDEX       {
                  entityIndex,
                  intervalEthRx15minNumber
                }
    ::=  { intervalL2EthRx15minTable 1 }

IntervalL2EthRx15minEntry ::=  SEQUENCE
  { intervalL2EthRx15minNumber Integer32,
    intervalL2EthRx15minFramesRcv Counter64String,
    intervalL2EthRx15minBytesRcv Counter64String,
    intervalL2EthRx15minBroadcastFramesRcv Counter64String,
    intervalL2EthRx15minMulticastFramesRcv Counter64String,
    intervalL2EthRx15minCrcErrorsRcv Counter64String,
    intervalL2EthRx15minUndersizedFramesRcv Counter64String,
    intervalL2EthRx15minOversizedFramesRcv Counter64String,
    intervalL2EthRx15minPauseFramesRcv Counter64String,
    intervalL2EthRx15minBytesFrames64Rcv Counter64String,
    intervalL2EthRx15minBytesFrames65Rcv Counter64String,
    intervalL2EthRx15minBytesFrames128Rcv Counter64String,
    intervalL2EthRx15minBytesFrames256Rcv Counter64String,
    intervalL2EthRx15minBytesFrames512Rcv Counter64String,
    intervalL2EthRx15minBytesFrames1024Rcv Counter64String,
    intervalL2EthRx15minBytesFrames1519Rcv Counter64String,
    intervalL2EthRx15minInterPackJunkBytesFramesRcv Counter64String,
    intervalL2EthRx15minValidFlag TruthValue,
    intervalL2EthRx15minTimeStamp DateAndTime }

intervalL2EthRx15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalL2EthRx15minEntry 1 }

intervalL2EthRx15minFramesRcv OBJECT-TYPE
    SYNTAX      Counter64String
    MAX-ACCESS  read-only
    STATUS      current
    DESCRIPTION
        "Frames Received" 
    ::=  { intervalL2EthRx15minEntry 2 }

intervalL2EthRx15minBytesRcv OBJECT-TYPE
    SYNTAX      Counter64String
    MAX-ACCESS  read-only
    STATUS      current
    DESCRIPTION
        "Bytes Received" 
    ::=  { intervalL2EthRx15minEntry 3 }

intervalL2EthRx15minBroadcastFramesRcv OBJECT-TYPE
    SYNTAX      Counter64String
    MAX-ACCESS  read-only
    STATUS      current
    DESCRIPTION
        "Broadcast Frames Received" 
    ::=  { intervalL2EthRx15minEntry 4 }

intervalL2EthRx15minMulticastFramesRcv OBJECT-TYPE
    SYNTAX      Counter64String
    MAX-ACCESS  read-only
    STATUS      current
    DESCRIPTION
        "Multicast Frames Received" 
    ::=  { intervalL2EthRx15minEntry 5 }

intervalL2EthRx15minCrcErrorsRcv OBJECT-TYPE
    SYNTAX      Counter64String
    MAX-ACCESS  read-only
    STATUS      current
    DESCRIPTION
        "Received CRC Errors" 
    ::=  { intervalL2EthRx15minEntry 6 }

intervalL2EthRx15minUndersizedFramesRcv OBJECT-TYPE
    SYNTAX      Counter64String
    MAX-ACCESS  read-only
    STATUS      current
    DESCRIPTION
        "Undersized Frames Received" 
    ::=  { intervalL2EthRx15minEntry 7 }

intervalL2EthRx15minOversizedFramesRcv OBJECT-TYPE
    SYNTAX      Counter64String
    MAX-ACCESS  read-only
    STATUS      current
    DESCRIPTION
        "Oversized Frames Received" 
    ::=  { intervalL2EthRx15minEntry 8 }

intervalL2EthRx15minPauseFramesRcv OBJECT-TYPE
    SYNTAX      Counter64String
    MAX-ACCESS  read-only
    STATUS      current
    DESCRIPTION
        "Pause Frames Received" 
    ::=  { intervalL2EthRx15minEntry 9 }

intervalL2EthRx15minBytesFrames64Rcv OBJECT-TYPE
    SYNTAX      Counter64String
    MAX-ACCESS  read-only
    STATUS      current
    DESCRIPTION
        "64 Byte Frames Received" 
    ::=  { intervalL2EthRx15minEntry 10 }

intervalL2EthRx15minBytesFrames65Rcv OBJECT-TYPE
    SYNTAX      Counter64String
    MAX-ACCESS  read-only
    STATUS      current
    DESCRIPTION
        "65-127 Byte Frames Received" 
    ::=  { intervalL2EthRx15minEntry 11 }

intervalL2EthRx15minBytesFrames128Rcv OBJECT-TYPE
    SYNTAX      Counter64String
    MAX-ACCESS  read-only
    STATUS      current
    DESCRIPTION
        "128-255 Byte Frames Received" 
    ::=  { intervalL2EthRx15minEntry 12 }

intervalL2EthRx15minBytesFrames256Rcv OBJECT-TYPE
    SYNTAX      Counter64String
    MAX-ACCESS  read-only
    STATUS      current
    DESCRIPTION
        "256-511 Byte Frames Received" 
    ::=  { intervalL2EthRx15minEntry 13 }

intervalL2EthRx15minBytesFrames512Rcv OBJECT-TYPE
    SYNTAX      Counter64String
    MAX-ACCESS  read-only
    STATUS      current
    DESCRIPTION
        "512-1023 Byte Frames Received" 
    ::=  { intervalL2EthRx15minEntry 14 }

intervalL2EthRx15minBytesFrames1024Rcv OBJECT-TYPE
    SYNTAX      Counter64String
    MAX-ACCESS  read-only
    STATUS      current
    DESCRIPTION
        "1024-1518 Byte Frames Received" 
    ::=  { intervalL2EthRx15minEntry 15 }

intervalL2EthRx15minBytesFrames1519Rcv OBJECT-TYPE
    SYNTAX      Counter64String
    MAX-ACCESS  read-only
    STATUS      current
    DESCRIPTION
        "1519-Max Byte Frames Received" 
    ::=  { intervalL2EthRx15minEntry 16 }

intervalL2EthRx15minInterPackJunkBytesFramesRcv OBJECT-TYPE
    SYNTAX      Counter64String
    MAX-ACCESS  read-only
    STATUS      current
    DESCRIPTION
        "InterPackJunk Bytes Frames Received (10Gbit/s only)" 
    ::=  { intervalL2EthRx15minEntry 17 }

intervalL2EthRx15minValidFlag OBJECT-TYPE
    SYNTAX      TruthValue
    MAX-ACCESS  read-only
    STATUS      current
    DESCRIPTION
        "Valid Flag" 
    ::=  { intervalL2EthRx15minEntry 18 }

intervalL2EthRx15minTimeStamp OBJECT-TYPE
    SYNTAX      DateAndTime
    MAX-ACCESS  read-only
    STATUS      current
    DESCRIPTION
        "Timestamp" 
    ::=  { intervalL2EthRx15minEntry 19 }

intervalL2EthRx1dayTable OBJECT-TYPE
    SYNTAX      SEQUENCE OF IntervalL2EthRx1dayEntry
    MAX-ACCESS  not-accessible
    STATUS      current
    DESCRIPTION   ""
    ::=  { performanceMonitoring 139 }

intervalL2EthRx1dayEntry OBJECT-TYPE
    SYNTAX      IntervalL2EthRx1dayEntry
    MAX-ACCESS  not-accessible
    STATUS      current
    DESCRIPTION   ""
    INDEX       {
                  entityIndex,
                  intervalEthRx1dayNumber
                }
    ::=  { intervalL2EthRx1dayTable 1 }

IntervalL2EthRx1dayEntry ::=  SEQUENCE
  { intervalL2EthRx1dayNumber Integer32,
    intervalL2EthRx1dayFramesRcv Counter64String,
    intervalL2EthRx1dayBytesRcv Counter64String,
    intervalL2EthRx1dayBroadcastFramesRcv Counter64String,
    intervalL2EthRx1dayMulticastFramesRcv Counter64String,
    intervalL2EthRx1dayCrcErrorsRcv Counter64String,
    intervalL2EthRx1dayUndersizedFramesRcv Counter64String,
    intervalL2EthRx1dayOversizedFramesRcv Counter64String,
    intervalL2EthRx1dayPauseFramesRcv Counter64String,
    intervalL2EthRx1dayBytesFrames64Rcv Counter64String,
    intervalL2EthRx1dayBytesFrames65Rcv Counter64String,
    intervalL2EthRx1dayBytesFrames128Rcv Counter64String,
    intervalL2EthRx1dayBytesFrames256Rcv Counter64String,
    intervalL2EthRx1dayBytesFrames512Rcv Counter64String,
    intervalL2EthRx1dayBytesFrames1024Rcv Counter64String,
    intervalL2EthRx1dayBytesFrames1519Rcv Counter64String,
    intervalL2EthRx1dayInterPackJunkBytesFramesRcv Counter64String,
    intervalL2EthRx1dayValidFlag TruthValue,
    intervalL2EthRx1dayTimeStamp DateAndTime }

intervalL2EthRx1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalL2EthRx1dayEntry 1 }

intervalL2EthRx1dayFramesRcv OBJECT-TYPE
    SYNTAX      Counter64String
    MAX-ACCESS  read-only
    STATUS      current
    DESCRIPTION
        "Frames Received" 
    ::=  { intervalL2EthRx1dayEntry 2 }

intervalL2EthRx1dayBytesRcv OBJECT-TYPE
    SYNTAX      Counter64String
    MAX-ACCESS  read-only
    STATUS      current
    DESCRIPTION
        "Bytes Received" 
    ::=  { intervalL2EthRx1dayEntry 3 }

intervalL2EthRx1dayBroadcastFramesRcv OBJECT-TYPE
    SYNTAX      Counter64String
    MAX-ACCESS  read-only
    STATUS      current
    DESCRIPTION
        "Broadcast Frames Received" 
    ::=  { intervalL2EthRx1dayEntry 4 }

intervalL2EthRx1dayMulticastFramesRcv OBJECT-TYPE
    SYNTAX      Counter64String
    MAX-ACCESS  read-only
    STATUS      current
    DESCRIPTION
        "Multicast Frames Received" 
    ::=  { intervalL2EthRx1dayEntry 5 }

intervalL2EthRx1dayCrcErrorsRcv OBJECT-TYPE
    SYNTAX      Counter64String
    MAX-ACCESS  read-only
    STATUS      current
    DESCRIPTION
        "Received CRC Errors" 
    ::=  { intervalL2EthRx1dayEntry 6 }

intervalL2EthRx1dayUndersizedFramesRcv OBJECT-TYPE
    SYNTAX      Counter64String
    MAX-ACCESS  read-only
    STATUS      current
    DESCRIPTION
        "Undersized Frames Received" 
    ::=  { intervalL2EthRx1dayEntry 7 }

intervalL2EthRx1dayOversizedFramesRcv OBJECT-TYPE
    SYNTAX      Counter64String
    MAX-ACCESS  read-only
    STATUS      current
    DESCRIPTION
        "Oversized Frames Received" 
    ::=  { intervalL2EthRx1dayEntry 8 }

intervalL2EthRx1dayPauseFramesRcv OBJECT-TYPE
    SYNTAX      Counter64String
    MAX-ACCESS  read-only
    STATUS      current
    DESCRIPTION
        "Pause Frames Received" 
    ::=  { intervalL2EthRx1dayEntry 9 }

intervalL2EthRx1dayBytesFrames64Rcv OBJECT-TYPE
    SYNTAX      Counter64String
    MAX-ACCESS  read-only
    STATUS      current
    DESCRIPTION
        "64 Byte Frames Received" 
    ::=  { intervalL2EthRx1dayEntry 10 }

intervalL2EthRx1dayBytesFrames65Rcv OBJECT-TYPE
    SYNTAX      Counter64String
    MAX-ACCESS  read-only
    STATUS      current
    DESCRIPTION
        "65-127 Byte Frames Received" 
    ::=  { intervalL2EthRx1dayEntry 11 }

intervalL2EthRx1dayBytesFrames128Rcv OBJECT-TYPE
    SYNTAX      Counter64String
    MAX-ACCESS  read-only
    STATUS      current
    DESCRIPTION
        "128-255 Byte Frames Received" 
    ::=  { intervalL2EthRx1dayEntry 12 }

intervalL2EthRx1dayBytesFrames256Rcv OBJECT-TYPE
    SYNTAX      Counter64String
    MAX-ACCESS  read-only
    STATUS      current
    DESCRIPTION
        "256-511 Byte Frames Received" 
    ::=  { intervalL2EthRx1dayEntry 13 }

intervalL2EthRx1dayBytesFrames512Rcv OBJECT-TYPE
    SYNTAX      Counter64String
    MAX-ACCESS  read-only
    STATUS      current
    DESCRIPTION
        "512-1023 Byte Frames Received" 
    ::=  { intervalL2EthRx1dayEntry 14 }

intervalL2EthRx1dayBytesFrames1024Rcv OBJECT-TYPE
    SYNTAX      Counter64String
    MAX-ACCESS  read-only
    STATUS      current
    DESCRIPTION
        "1024-1518 Byte Frames Received" 
    ::=  { intervalL2EthRx1dayEntry 15 }

intervalL2EthRx1dayBytesFrames1519Rcv OBJECT-TYPE
    SYNTAX      Counter64String
    MAX-ACCESS  read-only
    STATUS      current
    DESCRIPTION
        "1519-Max Byte Frames Received" 
    ::=  { intervalL2EthRx1dayEntry 16 }

intervalL2EthRx1dayInterPackJunkBytesFramesRcv OBJECT-TYPE
    SYNTAX      Counter64String
    MAX-ACCESS  read-only
    STATUS      current
    DESCRIPTION
        "InterPackJunk Bytes Frames Received (10Gbit/s only)" 
    ::=  { intervalL2EthRx1dayEntry 17 }

intervalL2EthRx1dayValidFlag OBJECT-TYPE
    SYNTAX      TruthValue
    MAX-ACCESS  read-only
    STATUS      current
    DESCRIPTION
        "Valid Flag" 
    ::=  { intervalL2EthRx1dayEntry 18 }

intervalL2EthRx1dayTimeStamp OBJECT-TYPE
    SYNTAX      DateAndTime
    MAX-ACCESS  read-only
    STATUS      current
    DESCRIPTION
        "Timestamp" 
    ::=  { intervalL2EthRx1dayEntry 19 }

currentL2EthTx15minTable OBJECT-TYPE
    SYNTAX      SEQUENCE OF CurrentL2EthTx15minEntry
    MAX-ACCESS  not-accessible
    STATUS      current
    DESCRIPTION   ""
    ::=  { performanceMonitoring 140 }

currentL2EthTx15minEntry OBJECT-TYPE
    SYNTAX      CurrentL2EthTx15minEntry
    MAX-ACCESS  not-accessible
    STATUS      current
    DESCRIPTION   ""
    INDEX       {
                  entityIndex
                }
    ::=  { currentL2EthTx15minTable 1 }

CurrentL2EthTx15minEntry ::=  SEQUENCE
  { currentL2EthTx15minFramesTrmt Counter64String,
    currentL2EthTx15minBytesTrmt Counter64String,
    currentL2EthTx15minBroadcastFramesTrmt Counter64String,
    currentL2EthTx15minMulticastFramesTrmt Counter64String,
    currentL2EthTx15minPauseFramesTrmt Counter64String,
    currentL2EthTx15minBytesFrames64Trmt Counter64String,
    currentL2EthTx15minBytesFrames65Trmt Counter64String,
    currentL2EthTx15minBytesFrames128Trmt Counter64String,
    currentL2EthTx15minBytesFrames256Trmt Counter64String,
    currentL2EthTx15minBytesFrames512Trmt Counter64String,
    currentL2EthTx15minBytesFrames1024Trmt Counter64String,
    currentL2EthTx15minBytesFrames1519Trmt Counter64String,
    currentL2EthTx15minElapsedTime Integer32 }

currentL2EthTx15minFramesTrmt OBJECT-TYPE
    SYNTAX      Counter64String
    MAX-ACCESS  read-only
    STATUS      current
    DESCRIPTION
        "Frames Transmitted" 
    ::=  { currentL2EthTx15minEntry 1 }

currentL2EthTx15minBytesTrmt OBJECT-TYPE
    SYNTAX      Counter64String
    MAX-ACCESS  read-only
    STATUS      current
    DESCRIPTION
        "Bytes Transmitted" 
    ::=  { currentL2EthTx15minEntry 2 }

currentL2EthTx15minBroadcastFramesTrmt OBJECT-TYPE
    SYNTAX      Counter64String
    MAX-ACCESS  read-only
    STATUS      current
    DESCRIPTION
        "Broadcast Frames Transmitted" 
    ::=  { currentL2EthTx15minEntry 3 }

currentL2EthTx15minMulticastFramesTrmt OBJECT-TYPE
    SYNTAX      Counter64String
    MAX-ACCESS  read-only
    STATUS      current
    DESCRIPTION
        "Multicast Frames Received" 
    ::=  { currentL2EthTx15minEntry 4 }

currentL2EthTx15minPauseFramesTrmt OBJECT-TYPE
    SYNTAX      Counter64String
    MAX-ACCESS  read-only
    STATUS      current
    DESCRIPTION
        "Pause Frames Transmitted" 
    ::=  { currentL2EthTx15minEntry 5 }

currentL2EthTx15minBytesFrames64Trmt OBJECT-TYPE
    SYNTAX      Counter64String
    MAX-ACCESS  read-only
    STATUS      current
    DESCRIPTION
        "64 Byte Frames Transmitted" 
    ::=  { currentL2EthTx15minEntry 6 }

currentL2EthTx15minBytesFrames65Trmt OBJECT-TYPE
    SYNTAX      Counter64String
    MAX-ACCESS  read-only
    STATUS      current
    DESCRIPTION
        "65-127 Byte Frames Transmitted" 
    ::=  { currentL2EthTx15minEntry 7 }

currentL2EthTx15minBytesFrames128Trmt OBJECT-TYPE
    SYNTAX      Counter64String
    MAX-ACCESS  read-only
    STATUS      current
    DESCRIPTION
        "128-255 Byte Frames Transmitted" 
    ::=  { currentL2EthTx15minEntry 8 }

currentL2EthTx15minBytesFrames256Trmt OBJECT-TYPE
    SYNTAX      Counter64String
    MAX-ACCESS  read-only
    STATUS      current
    DESCRIPTION
        "256-511 Byte Frames Transmitted" 
    ::=  { currentL2EthTx15minEntry 9 }

currentL2EthTx15minBytesFrames512Trmt OBJECT-TYPE
    SYNTAX      Counter64String
    MAX-ACCESS  read-only
    STATUS      current
    DESCRIPTION
        "512-1023 Byte Frames Transmitted" 
    ::=  { currentL2EthTx15minEntry 10 }

currentL2EthTx15minBytesFrames1024Trmt OBJECT-TYPE
    SYNTAX      Counter64String
    MAX-ACCESS  read-only
    STATUS      current
    DESCRIPTION
        "1024-1518 Byte Frames Transmitted" 
    ::=  { currentL2EthTx15minEntry 11 }

currentL2EthTx15minBytesFrames1519Trmt OBJECT-TYPE
    SYNTAX      Counter64String
    MAX-ACCESS  read-only
    STATUS      current
    DESCRIPTION
        "1519-Max Byte Frames Transmitted" 
    ::=  { currentL2EthTx15minEntry 12 }

currentL2EthTx15minElapsedTime OBJECT-TYPE
    SYNTAX      Integer32 (0..9000 | -2147483648)
    MAX-ACCESS  read-only
    STATUS      current
    DESCRIPTION
        "Elapsed 15Min" 
    ::=  { currentL2EthTx15minEntry 13 }

currentL2EthTx1dayTable OBJECT-TYPE
    SYNTAX      SEQUENCE OF CurrentL2EthTx1dayEntry
    MAX-ACCESS  not-accessible
    STATUS      current
    DESCRIPTION   ""
    ::=  { performanceMonitoring 141 }

currentL2EthTx1dayEntry OBJECT-TYPE
    SYNTAX      CurrentL2EthTx1dayEntry
    MAX-ACCESS  not-accessible
    STATUS      current
    DESCRIPTION   ""
    INDEX       {
                  entityIndex
                }
    ::=  { currentL2EthTx1dayTable 1 }

CurrentL2EthTx1dayEntry ::=  SEQUENCE
  { currentL2EthTx1dayFramesTrmt Counter64String,
    currentL2EthTx1dayBytesTrmt Counter64String,
    currentL2EthTx1dayBroadcastFramesTrmt Counter64String,
    currentL2EthTx1dayMulticastFramesTrmt Counter64String,
    currentL2EthTx1dayPauseFramesTrmt Counter64String,
    currentL2EthTx1dayBytesFrames64Trmt Counter64String,
    currentL2EthTx1dayBytesFrames65Trmt Counter64String,
    currentL2EthTx1dayBytesFrames128Trmt Counter64String,
    currentL2EthTx1dayBytesFrames256Trmt Counter64String,
    currentL2EthTx1dayBytesFrames512Trmt Counter64String,
    currentL2EthTx1dayBytesFrames1024Trmt Counter64String,
    currentL2EthTx1dayBytesFrames1519Trmt Counter64String,
    currentL2EthTx1dayElapsedTime Integer32 }

currentL2EthTx1dayFramesTrmt OBJECT-TYPE
    SYNTAX      Counter64String
    MAX-ACCESS  read-only
    STATUS      current
    DESCRIPTION
        "Frames Transmitted" 
    ::=  { currentL2EthTx1dayEntry 1 }

currentL2EthTx1dayBytesTrmt OBJECT-TYPE
    SYNTAX      Counter64String
    MAX-ACCESS  read-only
    STATUS      current
    DESCRIPTION
        "Bytes Transmitted" 
    ::=  { currentL2EthTx1dayEntry 2 }

currentL2EthTx1dayBroadcastFramesTrmt OBJECT-TYPE
    SYNTAX      Counter64String
    MAX-ACCESS  read-only
    STATUS      current
    DESCRIPTION
        "Broadcast Frames Transmitted" 
    ::=  { currentL2EthTx1dayEntry 3 }

currentL2EthTx1dayMulticastFramesTrmt OBJECT-TYPE
    SYNTAX      Counter64String
    MAX-ACCESS  read-only
    STATUS      current
    DESCRIPTION
        "Multicast Frames Received" 
    ::=  { currentL2EthTx1dayEntry 4 }

currentL2EthTx1dayPauseFramesTrmt OBJECT-TYPE
    SYNTAX      Counter64String
    MAX-ACCESS  read-only
    STATUS      current
    DESCRIPTION
        "Pause Frames Transmitted" 
    ::=  { currentL2EthTx1dayEntry 5 }

currentL2EthTx1dayBytesFrames64Trmt OBJECT-TYPE
    SYNTAX      Counter64String
    MAX-ACCESS  read-only
    STATUS      current
    DESCRIPTION
        "64 Byte Frames Transmitted" 
    ::=  { currentL2EthTx1dayEntry 6 }

currentL2EthTx1dayBytesFrames65Trmt OBJECT-TYPE
    SYNTAX      Counter64String
    MAX-ACCESS  read-only
    STATUS      current
    DESCRIPTION
        "65-127 Byte Frames Transmitted" 
    ::=  { currentL2EthTx1dayEntry 7 }

currentL2EthTx1dayBytesFrames128Trmt OBJECT-TYPE
    SYNTAX      Counter64String
    MAX-ACCESS  read-only
    STATUS      current
    DESCRIPTION
        "128-255 Byte Frames Transmitted" 
    ::=  { currentL2EthTx1dayEntry 8 }

currentL2EthTx1dayBytesFrames256Trmt OBJECT-TYPE
    SYNTAX      Counter64String
    MAX-ACCESS  read-only
    STATUS      current
    DESCRIPTION
        "256-511 Byte Frames Transmitted" 
    ::=  { currentL2EthTx1dayEntry 9 }

currentL2EthTx1dayBytesFrames512Trmt OBJECT-TYPE
    SYNTAX      Counter64String
    MAX-ACCESS  read-only
    STATUS      current
    DESCRIPTION
        "512-1023 Byte Frames Transmitted" 
    ::=  { currentL2EthTx1dayEntry 10 }

currentL2EthTx1dayBytesFrames1024Trmt OBJECT-TYPE
    SYNTAX      Counter64String
    MAX-ACCESS  read-only
    STATUS      current
    DESCRIPTION
        "1024-1518 Byte Frames Transmitted" 
    ::=  { currentL2EthTx1dayEntry 11 }

currentL2EthTx1dayBytesFrames1519Trmt OBJECT-TYPE
    SYNTAX      Counter64String
    MAX-ACCESS  read-only
    STATUS      current
    DESCRIPTION
        "1519-Max Byte Frames Transmitted" 
    ::=  { currentL2EthTx1dayEntry 12 }

currentL2EthTx1dayElapsedTime OBJECT-TYPE
    SYNTAX      Integer32 (0..86400 | -2147483648)
    MAX-ACCESS  read-only
    STATUS      current
    DESCRIPTION
        "Elapsed 1Day" 
    ::=  { currentL2EthTx1dayEntry 13 }

intervalL2EthTx15minTable OBJECT-TYPE
    SYNTAX      SEQUENCE OF IntervalL2EthTx15minEntry
    MAX-ACCESS  not-accessible
    STATUS      current
    DESCRIPTION   ""
    ::=  { performanceMonitoring 142 }

intervalL2EthTx15minEntry OBJECT-TYPE
    SYNTAX      IntervalL2EthTx15minEntry
    MAX-ACCESS  not-accessible
    STATUS      current
    DESCRIPTION   ""
    INDEX       {
                  entityIndex,
                  intervalEthTx15minNumber
                }
    ::=  { intervalL2EthTx15minTable 1 }

IntervalL2EthTx15minEntry ::=  SEQUENCE
  { intervalL2EthTx15minNumber Integer32,
    intervalL2EthTx15minFramesTrmt Counter64String,
    intervalL2EthTx15minBytesTrmt Counter64String,
    intervalL2EthTx15minBroadcastFramesTrmt Counter64String,
    intervalL2EthTx15minMulticastFramesTrmt Counter64String,
    intervalL2EthTx15minPauseFramesTrmt Counter64String,
    intervalL2EthTx15minBytesFrames64Trmt Counter64String,
    intervalL2EthTx15minBytesFrames65Trmt Counter64String,
    intervalL2EthTx15minBytesFrames128Trmt Counter64String,
    intervalL2EthTx15minBytesFrames256Trmt Counter64String,
    intervalL2EthTx15minBytesFrames512Trmt Counter64String,
    intervalL2EthTx15minBytesFrames1024Trmt Counter64String,
    intervalL2EthTx15minBytesFrames1519Trmt Counter64String,
    intervalL2EthTx15minValidFlag TruthValue,
    intervalL2EthTx15minTimeStamp DateAndTime }

intervalL2EthTx15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalL2EthTx15minEntry 1 }

intervalL2EthTx15minFramesTrmt OBJECT-TYPE
    SYNTAX      Counter64String
    MAX-ACCESS  read-only
    STATUS      current
    DESCRIPTION
        "Frames Transmitted" 
    ::=  { intervalL2EthTx15minEntry 2 }

intervalL2EthTx15minBytesTrmt OBJECT-TYPE
    SYNTAX      Counter64String
    MAX-ACCESS  read-only
    STATUS      current
    DESCRIPTION
        "Bytes Transmitted" 
    ::=  { intervalL2EthTx15minEntry 3 }

intervalL2EthTx15minBroadcastFramesTrmt OBJECT-TYPE
    SYNTAX      Counter64String
    MAX-ACCESS  read-only
    STATUS      current
    DESCRIPTION
        "Broadcast Frames Transmitted" 
    ::=  { intervalL2EthTx15minEntry 4 }

intervalL2EthTx15minMulticastFramesTrmt OBJECT-TYPE
    SYNTAX      Counter64String
    MAX-ACCESS  read-only
    STATUS      current
    DESCRIPTION
        "Multicast Frames Received" 
    ::=  { intervalL2EthTx15minEntry 5 }

intervalL2EthTx15minPauseFramesTrmt OBJECT-TYPE
    SYNTAX      Counter64String
    MAX-ACCESS  read-only
    STATUS      current
    DESCRIPTION
        "Pause Frames Transmitted" 
    ::=  { intervalL2EthTx15minEntry 6 }

intervalL2EthTx15minBytesFrames64Trmt OBJECT-TYPE
    SYNTAX      Counter64String
    MAX-ACCESS  read-only
    STATUS      current
    DESCRIPTION
        "64 Byte Frames Transmitted" 
    ::=  { intervalL2EthTx15minEntry 7 }

intervalL2EthTx15minBytesFrames65Trmt OBJECT-TYPE
    SYNTAX      Counter64String
    MAX-ACCESS  read-only
    STATUS      current
    DESCRIPTION
        "65-127 Byte Frames Transmitted" 
    ::=  { intervalL2EthTx15minEntry 8 }

intervalL2EthTx15minBytesFrames128Trmt OBJECT-TYPE
    SYNTAX      Counter64String
    MAX-ACCESS  read-only
    STATUS      current
    DESCRIPTION
        "128-255 Byte Frames Transmitted" 
    ::=  { intervalL2EthTx15minEntry 9 }

intervalL2EthTx15minBytesFrames256Trmt OBJECT-TYPE
    SYNTAX      Counter64String
    MAX-ACCESS  read-only
    STATUS      current
    DESCRIPTION
        "256-511 Byte Frames Transmitted" 
    ::=  { intervalL2EthTx15minEntry 10 }

intervalL2EthTx15minBytesFrames512Trmt OBJECT-TYPE
    SYNTAX      Counter64String
    MAX-ACCESS  read-only
    STATUS      current
    DESCRIPTION
        "512-1023 Byte Frames Transmitted" 
    ::=  { intervalL2EthTx15minEntry 11 }

intervalL2EthTx15minBytesFrames1024Trmt OBJECT-TYPE
    SYNTAX      Counter64String
    MAX-ACCESS  read-only
    STATUS      current
    DESCRIPTION
        "1024-1518 Byte Frames Transmitted" 
    ::=  { intervalL2EthTx15minEntry 12 }

intervalL2EthTx15minBytesFrames1519Trmt OBJECT-TYPE
    SYNTAX      Counter64String
    MAX-ACCESS  read-only
    STATUS      current
    DESCRIPTION
        "1519-Max Byte Frames Transmitted" 
    ::=  { intervalL2EthTx15minEntry 13 }

intervalL2EthTx15minValidFlag OBJECT-TYPE
    SYNTAX      TruthValue
    MAX-ACCESS  read-only
    STATUS      current
    DESCRIPTION
        "Valid Flag" 
    ::=  { intervalL2EthTx15minEntry 14 }

intervalL2EthTx15minTimeStamp OBJECT-TYPE
    SYNTAX      DateAndTime
    MAX-ACCESS  read-only
    STATUS      current
    DESCRIPTION
        "Timestamp" 
    ::=  { intervalL2EthTx15minEntry 15 }

intervalL2EthTx1dayTable OBJECT-TYPE
    SYNTAX      SEQUENCE OF IntervalL2EthTx1dayEntry
    MAX-ACCESS  not-accessible
    STATUS      current
    DESCRIPTION   ""
    ::=  { performanceMonitoring 143 }

intervalL2EthTx1dayEntry OBJECT-TYPE
    SYNTAX      IntervalL2EthTx1dayEntry
    MAX-ACCESS  not-accessible
    STATUS      current
    DESCRIPTION   ""
    INDEX       {
                  entityIndex,
                  intervalEthTx1dayNumber
                }
    ::=  { intervalL2EthTx1dayTable 1 }

IntervalL2EthTx1dayEntry ::=  SEQUENCE
  { intervalL2EthTx1dayNumber Integer32,
    intervalL2EthTx1dayFramesTrmt Counter64String,
    intervalL2EthTx1dayBytesTrmt Counter64String,
    intervalL2EthTx1dayBroadcastFramesTrmt Counter64String,
    intervalL2EthTx1dayMulticastFramesTrmt Counter64String,
    intervalL2EthTx1dayPauseFramesTrmt Counter64String,
    intervalL2EthTx1dayBytesFrames64Trmt Counter64String,
    intervalL2EthTx1dayBytesFrames65Trmt Counter64String,
    intervalL2EthTx1dayBytesFrames128Trmt Counter64String,
    intervalL2EthTx1dayBytesFrames256Trmt Counter64String,
    intervalL2EthTx1dayBytesFrames512Trmt Counter64String,
    intervalL2EthTx1dayBytesFrames1024Trmt Counter64String,
    intervalL2EthTx1dayBytesFrames1519Trmt Counter64String,
    intervalL2EthTx1dayValidFlag TruthValue,
    intervalL2EthTx1dayTimeStamp DateAndTime }

intervalL2EthTx1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalL2EthTx1dayEntry 1 }

intervalL2EthTx1dayFramesTrmt OBJECT-TYPE
    SYNTAX      Counter64String
    MAX-ACCESS  read-only
    STATUS      current
    DESCRIPTION
        "Frames Transmitted" 
    ::=  { intervalL2EthTx1dayEntry 2 }

intervalL2EthTx1dayBytesTrmt OBJECT-TYPE
    SYNTAX      Counter64String
    MAX-ACCESS  read-only
    STATUS      current
    DESCRIPTION
        "Bytes Transmitted" 
    ::=  { intervalL2EthTx1dayEntry 3 }

intervalL2EthTx1dayBroadcastFramesTrmt OBJECT-TYPE
    SYNTAX      Counter64String
    MAX-ACCESS  read-only
    STATUS      current
    DESCRIPTION
        "Broadcast Frames Transmitted" 
    ::=  { intervalL2EthTx1dayEntry 4 }

intervalL2EthTx1dayMulticastFramesTrmt OBJECT-TYPE
    SYNTAX      Counter64String
    MAX-ACCESS  read-only
    STATUS      current
    DESCRIPTION
        "Multicast Frames Received" 
    ::=  { intervalL2EthTx1dayEntry 5 }

intervalL2EthTx1dayPauseFramesTrmt OBJECT-TYPE
    SYNTAX      Counter64String
    MAX-ACCESS  read-only
    STATUS      current
    DESCRIPTION
        "Pause Frames Transmitted" 
    ::=  { intervalL2EthTx1dayEntry 6 }

intervalL2EthTx1dayBytesFrames64Trmt OBJECT-TYPE
    SYNTAX      Counter64String
    MAX-ACCESS  read-only
    STATUS      current
    DESCRIPTION
        "64 Byte Frames Transmitted" 
    ::=  { intervalL2EthTx1dayEntry 7 }

intervalL2EthTx1dayBytesFrames65Trmt OBJECT-TYPE
    SYNTAX      Counter64String
    MAX-ACCESS  read-only
    STATUS      current
    DESCRIPTION
        "65-127 Byte Frames Transmitted" 
    ::=  { intervalL2EthTx1dayEntry 8 }

intervalL2EthTx1dayBytesFrames128Trmt OBJECT-TYPE
    SYNTAX      Counter64String
    MAX-ACCESS  read-only
    STATUS      current
    DESCRIPTION
        "128-255 Byte Frames Transmitted" 
    ::=  { intervalL2EthTx1dayEntry 9 }

intervalL2EthTx1dayBytesFrames256Trmt OBJECT-TYPE
    SYNTAX      Counter64String
    MAX-ACCESS  read-only
    STATUS      current
    DESCRIPTION
        "256-511 Byte Frames Transmitted" 
    ::=  { intervalL2EthTx1dayEntry 10 }

intervalL2EthTx1dayBytesFrames512Trmt OBJECT-TYPE
    SYNTAX      Counter64String
    MAX-ACCESS  read-only
    STATUS      current
    DESCRIPTION
        "512-1023 Byte Frames Transmitted" 
    ::=  { intervalL2EthTx1dayEntry 11 }

intervalL2EthTx1dayBytesFrames1024Trmt OBJECT-TYPE
    SYNTAX      Counter64String
    MAX-ACCESS  read-only
    STATUS      current
    DESCRIPTION
        "1024-1518 Byte Frames Transmitted" 
    ::=  { intervalL2EthTx1dayEntry 12 }

intervalL2EthTx1dayBytesFrames1519Trmt OBJECT-TYPE
    SYNTAX      Counter64String
    MAX-ACCESS  read-only
    STATUS      current
    DESCRIPTION
        "1519-Max Byte Frames Transmitted" 
    ::=  { intervalL2EthTx1dayEntry 13 }

intervalL2EthTx1dayValidFlag OBJECT-TYPE
    SYNTAX      TruthValue
    MAX-ACCESS  read-only
    STATUS      current
    DESCRIPTION
        "Valid Flag" 
    ::=  { intervalL2EthTx1dayEntry 14 }

intervalL2EthTx1dayTimeStamp OBJECT-TYPE
    SYNTAX      DateAndTime
    MAX-ACCESS  read-only
    STATUS      current
    DESCRIPTION
        "Timestamp" 
    ::=  { intervalL2EthTx1dayEntry 15 }

intervalFarEndPhysPerfOpticalInputPwr15minTable OBJECT-TYPE
    SYNTAX      SEQUENCE OF IntervalFarEndPhysPerfOpticalInputPwr15minEntry
    MAX-ACCESS  not-accessible
    STATUS      current
    DESCRIPTION   ""
    ::=  { performanceMonitoring 144 }

intervalFarEndPhysPerfOpticalInputPwr15minEntry OBJECT-TYPE
    SYNTAX      IntervalFarEndPhysPerfOpticalInputPwr15minEntry
    MAX-ACCESS  not-accessible
    STATUS      current
    DESCRIPTION   ""
    INDEX       {
                  entityIndex,
                  intervalPhysPerfOpticalInputPwr15minNumber
                }
    ::=  { intervalFarEndPhysPerfOpticalInputPwr15minTable 1 }

IntervalFarEndPhysPerfOpticalInputPwr15minEntry ::=  SEQUENCE
  { intervalFarEndPhysPerfOpticalInputPwr15minNumber Integer32,
    intervalFarEndPhysPerfOpticalInputPwr15minLow Integer32,
    intervalFarEndPhysPerfOpticalInputPwr15minMean Integer32,
    intervalFarEndPhysPerfOpticalInputPwr15minHigh Integer32,
    intervalFarEndPhysPerfOpticalInputPwr15minValidFlag TruthValue,
    intervalFarEndPhysPerfOpticalInputPwr15minTimeStamp DateAndTime }

intervalFarEndPhysPerfOpticalInputPwr15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalFarEndPhysPerfOpticalInputPwr15minEntry 1 }

intervalFarEndPhysPerfOpticalInputPwr15minLow OBJECT-TYPE
    SYNTAX      Integer32 
    UNITS       "0.1 dBm"
    MAX-ACCESS  read-only
    STATUS      current
    DESCRIPTION
        "Optical Input Power Received" 
    ::=  { intervalFarEndPhysPerfOpticalInputPwr15minEntry 2 }

intervalFarEndPhysPerfOpticalInputPwr15minMean OBJECT-TYPE
    SYNTAX      Integer32 
    UNITS       "0.1 dBm"
    MAX-ACCESS  read-only
    STATUS      current
    DESCRIPTION
        "Optical Input Power Received" 
    ::=  { intervalFarEndPhysPerfOpticalInputPwr15minEntry 3 }

intervalFarEndPhysPerfOpticalInputPwr15minHigh OBJECT-TYPE
    SYNTAX      Integer32 
    UNITS       "0.1 dBm"
    MAX-ACCESS  read-only
    STATUS      current
    DESCRIPTION
        "Optical Input Power Received" 
    ::=  { intervalFarEndPhysPerfOpticalInputPwr15minEntry 4 }

intervalFarEndPhysPerfOpticalInputPwr15minValidFlag OBJECT-TYPE
    SYNTAX      TruthValue
    MAX-ACCESS  read-only
    STATUS      current
    DESCRIPTION
        "Valid Flag" 
    ::=  { intervalFarEndPhysPerfOpticalInputPwr15minEntry 5 }

intervalFarEndPhysPerfOpticalInputPwr15minTimeStamp OBJECT-TYPE
    SYNTAX      DateAndTime
    MAX-ACCESS  read-only
    STATUS      current
    DESCRIPTION
        "Timestamp" 
    ::=  { intervalFarEndPhysPerfOpticalInputPwr15minEntry 6 }

intervalFarEndPhysPerfOpticalInputPwr1dayTable OBJECT-TYPE
    SYNTAX      SEQUENCE OF IntervalFarEndPhysPerfOpticalInputPwr1dayEntry
    MAX-ACCESS  not-accessible
    STATUS      current
    DESCRIPTION   ""
    ::=  { performanceMonitoring 145 }

intervalFarEndPhysPerfOpticalInputPwr1dayEntry OBJECT-TYPE
    SYNTAX      IntervalFarEndPhysPerfOpticalInputPwr1dayEntry
    MAX-ACCESS  not-accessible
    STATUS      current
    DESCRIPTION   ""
    INDEX       {
                  entityIndex,
                  intervalPhysPerfOpticalInputPwr1dayNumber
                }
    ::=  { intervalFarEndPhysPerfOpticalInputPwr1dayTable 1 }

IntervalFarEndPhysPerfOpticalInputPwr1dayEntry ::=  SEQUENCE
  { intervalFarEndPhysPerfOpticalInputPwr1dayNumber Integer32,
    intervalFarEndPhysPerfOpticalInputPwr1dayLow Integer32,
    intervalFarEndPhysPerfOpticalInputPwr1dayMean Integer32,
    intervalFarEndPhysPerfOpticalInputPwr1dayHigh Integer32,
    intervalFarEndPhysPerfOpticalInputPwr1dayValidFlag TruthValue,
    intervalFarEndPhysPerfOpticalInputPwr1dayTimeStamp DateAndTime }

intervalFarEndPhysPerfOpticalInputPwr1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalFarEndPhysPerfOpticalInputPwr1dayEntry 1 }

intervalFarEndPhysPerfOpticalInputPwr1dayLow OBJECT-TYPE
    SYNTAX      Integer32 
    UNITS       "0.1 dBm"
    MAX-ACCESS  read-only
    STATUS      current
    DESCRIPTION
        "Optical Input Power Received" 
    ::=  { intervalFarEndPhysPerfOpticalInputPwr1dayEntry 2 }

intervalFarEndPhysPerfOpticalInputPwr1dayMean OBJECT-TYPE
    SYNTAX      Integer32 
    UNITS       "0.1 dBm"
    MAX-ACCESS  read-only
    STATUS      current
    DESCRIPTION
        "Optical Input Power Received" 
    ::=  { intervalFarEndPhysPerfOpticalInputPwr1dayEntry 3 }

intervalFarEndPhysPerfOpticalInputPwr1dayHigh OBJECT-TYPE
    SYNTAX      Integer32 
    UNITS       "0.1 dBm"
    MAX-ACCESS  read-only
    STATUS      current
    DESCRIPTION
        "Optical Input Power Received" 
    ::=  { intervalFarEndPhysPerfOpticalInputPwr1dayEntry 4 }

intervalFarEndPhysPerfOpticalInputPwr1dayValidFlag OBJECT-TYPE
    SYNTAX      TruthValue
    MAX-ACCESS  read-only
    STATUS      current
    DESCRIPTION
        "Valid Flag" 
    ::=  { intervalFarEndPhysPerfOpticalInputPwr1dayEntry 5 }

intervalFarEndPhysPerfOpticalInputPwr1dayTimeStamp OBJECT-TYPE
    SYNTAX      DateAndTime
    MAX-ACCESS  read-only
    STATUS      current
    DESCRIPTION
        "Timestamp" 
    ::=  { intervalFarEndPhysPerfOpticalInputPwr1dayEntry 6 }

intervalFarEndPhysPerfOpticalInputPwr1weekTable OBJECT-TYPE
    SYNTAX      SEQUENCE OF IntervalFarEndPhysPerfOpticalInputPwr1weekEntry
    MAX-ACCESS  not-accessible
    STATUS      current
    DESCRIPTION   ""
    ::=  { performanceMonitoring 146 }

intervalFarEndPhysPerfOpticalInputPwr1weekEntry OBJECT-TYPE
    SYNTAX      IntervalFarEndPhysPerfOpticalInputPwr1weekEntry
    MAX-ACCESS  not-accessible
    STATUS      current
    DESCRIPTION   ""
    INDEX       {
                  entityIndex,
                  intervalPhysPerfOpticalInputPwr1weekNumber
                }
    ::=  { intervalFarEndPhysPerfOpticalInputPwr1weekTable 1 }

IntervalFarEndPhysPerfOpticalInputPwr1weekEntry ::=  SEQUENCE
  { intervalFarEndPhysPerfOpticalInputPwr1weekNumber Integer32,
    intervalFarEndPhysPerfOpticalInputPwr1weekLow Integer32,
    intervalFarEndPhysPerfOpticalInputPwr1weekMean Integer32,
    intervalFarEndPhysPerfOpticalInputPwr1weekHigh Integer32,
    intervalFarEndPhysPerfOpticalInputPwr1weekValidFlag TruthValue,
    intervalFarEndPhysPerfOpticalInputPwr1weekTimeStamp DateAndTime }

intervalFarEndPhysPerfOpticalInputPwr1weekNumber OBJECT-TYPE
    SYNTAX      Integer32 (1..52)
    MAX-ACCESS  not-accessible
    STATUS      current
    DESCRIPTION
        "Number 1week" 
    ::=  { intervalFarEndPhysPerfOpticalInputPwr1weekEntry 1 }

intervalFarEndPhysPerfOpticalInputPwr1weekLow OBJECT-TYPE
    SYNTAX      Integer32 
    UNITS       "0.1 dBm"
    MAX-ACCESS  read-only
    STATUS      current
    DESCRIPTION
        "Optical Input Power Received" 
    ::=  { intervalFarEndPhysPerfOpticalInputPwr1weekEntry 2 }

intervalFarEndPhysPerfOpticalInputPwr1weekMean OBJECT-TYPE
    SYNTAX      Integer32 
    UNITS       "0.1 dBm"
    MAX-ACCESS  read-only
    STATUS      current
    DESCRIPTION
        "Optical Input Power Received" 
    ::=  { intervalFarEndPhysPerfOpticalInputPwr1weekEntry 3 }

intervalFarEndPhysPerfOpticalInputPwr1weekHigh OBJECT-TYPE
    SYNTAX      Integer32 
    UNITS       "0.1 dBm"
    MAX-ACCESS  read-only
    STATUS      current
    DESCRIPTION
        "Optical Input Power Received" 
    ::=  { intervalFarEndPhysPerfOpticalInputPwr1weekEntry 4 }

intervalFarEndPhysPerfOpticalInputPwr1weekValidFlag OBJECT-TYPE
    SYNTAX      TruthValue
    MAX-ACCESS  read-only
    STATUS      current
    DESCRIPTION
        "Valid Flag" 
    ::=  { intervalFarEndPhysPerfOpticalInputPwr1weekEntry 5 }

intervalFarEndPhysPerfOpticalInputPwr1weekTimeStamp OBJECT-TYPE
    SYNTAX      DateAndTime
    MAX-ACCESS  read-only
    STATUS      current
    DESCRIPTION
        "Timestamp" 
    ::=  { intervalFarEndPhysPerfOpticalInputPwr1weekEntry 6 }

intervalFarEndPhysPerfOpticalOutputPwr15minTable OBJECT-TYPE
    SYNTAX      SEQUENCE OF IntervalFarEndPhysPerfOpticalOutputPwr15minEntry
    MAX-ACCESS  not-accessible
    STATUS      current
    DESCRIPTION   ""
    ::=  { performanceMonitoring 147 }

intervalFarEndPhysPerfOpticalOutputPwr15minEntry OBJECT-TYPE
    SYNTAX      IntervalFarEndPhysPerfOpticalOutputPwr15minEntry
    MAX-ACCESS  not-accessible
    STATUS      current
    DESCRIPTION   ""
    INDEX       {
                  entityIndex,
                  intervalPhysPerfOpticalOutputPwr15minNumber
                }
    ::=  { intervalFarEndPhysPerfOpticalOutputPwr15minTable 1 }

IntervalFarEndPhysPerfOpticalOutputPwr15minEntry ::=  SEQUENCE
  { intervalFarEndPhysPerfOpticalOutputPwr15minNumber Integer32,
    intervalFarEndPhysPerfOpticalOutputPwr15minLow Integer32,
    intervalFarEndPhysPerfOpticalOutputPwr15minMean Integer32,
    intervalFarEndPhysPerfOpticalOutputPwr15minHigh Integer32,
    intervalFarEndPhysPerfOpticalOutputPwr15minValidFlag TruthValue,
    intervalFarEndPhysPerfOpticalOutputPwr15minTimeStamp DateAndTime }

intervalFarEndPhysPerfOpticalOutputPwr15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalFarEndPhysPerfOpticalOutputPwr15minEntry 1 }

intervalFarEndPhysPerfOpticalOutputPwr15minLow OBJECT-TYPE
    SYNTAX      Integer32 
    UNITS       "0.1 dBm"
    MAX-ACCESS  read-only
    STATUS      current
    DESCRIPTION
        "Optical Output Power Transmitted" 
    ::=  { intervalFarEndPhysPerfOpticalOutputPwr15minEntry 2 }

intervalFarEndPhysPerfOpticalOutputPwr15minMean OBJECT-TYPE
    SYNTAX      Integer32 
    UNITS       "0.1 dBm"
    MAX-ACCESS  read-only
    STATUS      current
    DESCRIPTION
        "Optical Output Power Transmitted" 
    ::=  { intervalFarEndPhysPerfOpticalOutputPwr15minEntry 3 }

intervalFarEndPhysPerfOpticalOutputPwr15minHigh OBJECT-TYPE
    SYNTAX      Integer32 
    UNITS       "0.1 dBm"
    MAX-ACCESS  read-only
    STATUS      current
    DESCRIPTION
        "Optical Output Power Transmitted" 
    ::=  { intervalFarEndPhysPerfOpticalOutputPwr15minEntry 4 }

intervalFarEndPhysPerfOpticalOutputPwr15minValidFlag OBJECT-TYPE
    SYNTAX      TruthValue
    MAX-ACCESS  read-only
    STATUS      current
    DESCRIPTION
        "Valid Flag" 
    ::=  { intervalFarEndPhysPerfOpticalOutputPwr15minEntry 5 }

intervalFarEndPhysPerfOpticalOutputPwr15minTimeStamp OBJECT-TYPE
    SYNTAX      DateAndTime
    MAX-ACCESS  read-only
    STATUS      current
    DESCRIPTION
        "Timestamp" 
    ::=  { intervalFarEndPhysPerfOpticalOutputPwr15minEntry 6 }

intervalFarEndPhysPerfOpticalOutputPwr1dayTable OBJECT-TYPE
    SYNTAX      SEQUENCE OF IntervalFarEndPhysPerfOpticalOutputPwr1dayEntry
    MAX-ACCESS  not-accessible
    STATUS      current
    DESCRIPTION   ""
    ::=  { performanceMonitoring 148 }

intervalFarEndPhysPerfOpticalOutputPwr1dayEntry OBJECT-TYPE
    SYNTAX      IntervalFarEndPhysPerfOpticalOutputPwr1dayEntry
    MAX-ACCESS  not-accessible
    STATUS      current
    DESCRIPTION   ""
    INDEX       {
                  entityIndex,
                  intervalPhysPerfOpticalOutputPwr1dayNumber
                }
    ::=  { intervalFarEndPhysPerfOpticalOutputPwr1dayTable 1 }

IntervalFarEndPhysPerfOpticalOutputPwr1dayEntry ::=  SEQUENCE
  { intervalFarEndPhysPerfOpticalOutputPwr1dayNumber Integer32,
    intervalFarEndPhysPerfOpticalOutputPwr1dayLow Integer32,
    intervalFarEndPhysPerfOpticalOutputPwr1dayMean Integer32,
    intervalFarEndPhysPerfOpticalOutputPwr1dayHigh Integer32,
    intervalFarEndPhysPerfOpticalOutputPwr1dayValidFlag TruthValue,
    intervalFarEndPhysPerfOpticalOutputPwr1dayTimeStamp DateAndTime }

intervalFarEndPhysPerfOpticalOutputPwr1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalFarEndPhysPerfOpticalOutputPwr1dayEntry 1 }

intervalFarEndPhysPerfOpticalOutputPwr1dayLow OBJECT-TYPE
    SYNTAX      Integer32 
    UNITS       "0.1 dBm"
    MAX-ACCESS  read-only
    STATUS      current
    DESCRIPTION
        "Optical Output Power Transmitted" 
    ::=  { intervalFarEndPhysPerfOpticalOutputPwr1dayEntry 2 }

intervalFarEndPhysPerfOpticalOutputPwr1dayMean OBJECT-TYPE
    SYNTAX      Integer32 
    UNITS       "0.1 dBm"
    MAX-ACCESS  read-only
    STATUS      current
    DESCRIPTION
        "Optical Output Power Transmitted" 
    ::=  { intervalFarEndPhysPerfOpticalOutputPwr1dayEntry 3 }

intervalFarEndPhysPerfOpticalOutputPwr1dayHigh OBJECT-TYPE
    SYNTAX      Integer32 
    UNITS       "0.1 dBm"
    MAX-ACCESS  read-only
    STATUS      current
    DESCRIPTION
        "Optical Output Power Transmitted" 
    ::=  { intervalFarEndPhysPerfOpticalOutputPwr1dayEntry 4 }

intervalFarEndPhysPerfOpticalOutputPwr1dayValidFlag OBJECT-TYPE
    SYNTAX      TruthValue
    MAX-ACCESS  read-only
    STATUS      current
    DESCRIPTION
        "Valid Flag" 
    ::=  { intervalFarEndPhysPerfOpticalOutputPwr1dayEntry 5 }

intervalFarEndPhysPerfOpticalOutputPwr1dayTimeStamp OBJECT-TYPE
    SYNTAX      DateAndTime
    MAX-ACCESS  read-only
    STATUS      current
    DESCRIPTION
        "Timestamp" 
    ::=  { intervalFarEndPhysPerfOpticalOutputPwr1dayEntry 6 }

intervalFarEndPhysPerfOpticalOutputPwr1weekTable OBJECT-TYPE
    SYNTAX      SEQUENCE OF IntervalFarEndPhysPerfOpticalOutputPwr1weekEntry
    MAX-ACCESS  not-accessible
    STATUS      current
    DESCRIPTION   ""
    ::=  { performanceMonitoring 149 }

intervalFarEndPhysPerfOpticalOutputPwr1weekEntry OBJECT-TYPE
    SYNTAX      IntervalFarEndPhysPerfOpticalOutputPwr1weekEntry
    MAX-ACCESS  not-accessible
    STATUS      current
    DESCRIPTION   ""
    INDEX       {
                  entityIndex,
                  intervalPhysPerfOpticalOutputPwr1weekNumber
                }
    ::=  { intervalFarEndPhysPerfOpticalOutputPwr1weekTable 1 }

IntervalFarEndPhysPerfOpticalOutputPwr1weekEntry ::=  SEQUENCE
  { intervalFarEndPhysPerfOpticalOutputPwr1weekNumber Integer32,
    intervalFarEndPhysPerfOpticalOutputPwr1weekLow Integer32,
    intervalFarEndPhysPerfOpticalOutputPwr1weekMean Integer32,
    intervalFarEndPhysPerfOpticalOutputPwr1weekHigh Integer32,
    intervalFarEndPhysPerfOpticalOutputPwr1weekValidFlag TruthValue,
    intervalFarEndPhysPerfOpticalOutputPwr1weekTimeStamp DateAndTime }

intervalFarEndPhysPerfOpticalOutputPwr1weekNumber OBJECT-TYPE
    SYNTAX      Integer32 (1..52)
    MAX-ACCESS  not-accessible
    STATUS      current
    DESCRIPTION
        "Number 1week" 
    ::=  { intervalFarEndPhysPerfOpticalOutputPwr1weekEntry 1 }

intervalFarEndPhysPerfOpticalOutputPwr1weekLow OBJECT-TYPE
    SYNTAX      Integer32 
    UNITS       "0.1 dBm"
    MAX-ACCESS  read-only
    STATUS      current
    DESCRIPTION
        "Optical Output Power Transmitted" 
    ::=  { intervalFarEndPhysPerfOpticalOutputPwr1weekEntry 2 }

intervalFarEndPhysPerfOpticalOutputPwr1weekMean OBJECT-TYPE
    SYNTAX      Integer32 
    UNITS       "0.1 dBm"
    MAX-ACCESS  read-only
    STATUS      current
    DESCRIPTION
        "Optical Output Power Transmitted" 
    ::=  { intervalFarEndPhysPerfOpticalOutputPwr1weekEntry 3 }

intervalFarEndPhysPerfOpticalOutputPwr1weekHigh OBJECT-TYPE
    SYNTAX      Integer32 
    UNITS       "0.1 dBm"
    MAX-ACCESS  read-only
    STATUS      current
    DESCRIPTION
        "Optical Output Power Transmitted" 
    ::=  { intervalFarEndPhysPerfOpticalOutputPwr1weekEntry 4 }

intervalFarEndPhysPerfOpticalOutputPwr1weekValidFlag OBJECT-TYPE
    SYNTAX      TruthValue
    MAX-ACCESS  read-only
    STATUS      current
    DESCRIPTION
        "Valid Flag" 
    ::=  { intervalFarEndPhysPerfOpticalOutputPwr1weekEntry 5 }

intervalFarEndPhysPerfOpticalOutputPwr1weekTimeStamp OBJECT-TYPE
    SYNTAX      DateAndTime
    MAX-ACCESS  read-only
    STATUS      current
    DESCRIPTION
        "Timestamp" 
    ::=  { intervalFarEndPhysPerfOpticalOutputPwr1weekEntry 6 }

intervalLatency15minTable OBJECT-TYPE
    SYNTAX      SEQUENCE OF IntervalLatency15minEntry
    MAX-ACCESS  not-accessible
    STATUS      current
    DESCRIPTION   ""
    ::=  { performanceMonitoring 150 }

intervalLatency15minEntry OBJECT-TYPE
    SYNTAX      IntervalLatency15minEntry
    MAX-ACCESS  not-accessible
    STATUS      current
    DESCRIPTION   ""
    INDEX       {
                  entityIndex,
                  intervalLatency15minNumber
                }
    ::=  { intervalLatency15minTable 1 }

IntervalLatency15minEntry ::=  SEQUENCE
  { intervalLatency15minNumber Integer32,
    intervalLatency15minLow Unsigned32,
    intervalLatency15minMean Unsigned32,
    intervalLatency15minHigh Unsigned32,
    intervalLatency15minValidFlag TruthValue,
    intervalLatency15minTimeStamp DateAndTime }

intervalLatency15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalLatency15minEntry 1 }

intervalLatency15minLow OBJECT-TYPE
    SYNTAX      Unsigned32 
    UNITS       "0.1 us"
    MAX-ACCESS  read-only
    STATUS      current
    DESCRIPTION
        "Measured round trip delay" 
    ::=  { intervalLatency15minEntry 2 }

intervalLatency15minMean OBJECT-TYPE
    SYNTAX      Unsigned32 
    UNITS       "0.1 us"
    MAX-ACCESS  read-only
    STATUS      current
    DESCRIPTION
        "Measured round trip delay" 
    ::=  { intervalLatency15minEntry 3 }

intervalLatency15minHigh OBJECT-TYPE
    SYNTAX      Unsigned32 
    UNITS       "0.1 us"
    MAX-ACCESS  read-only
    STATUS      current
    DESCRIPTION
        "Measured round trip delay" 
    ::=  { intervalLatency15minEntry 4 }

intervalLatency15minValidFlag OBJECT-TYPE
    SYNTAX      TruthValue
    MAX-ACCESS  read-only
    STATUS      current
    DESCRIPTION
        "Valid Flag" 
    ::=  { intervalLatency15minEntry 5 }

intervalLatency15minTimeStamp OBJECT-TYPE
    SYNTAX      DateAndTime
    MAX-ACCESS  read-only
    STATUS      current
    DESCRIPTION
        "Timestamp" 
    ::=  { intervalLatency15minEntry 6 }

intervalLatency1dayTable OBJECT-TYPE
    SYNTAX      SEQUENCE OF IntervalLatency1dayEntry
    MAX-ACCESS  not-accessible
    STATUS      current
    DESCRIPTION   ""
    ::=  { performanceMonitoring 151 }

intervalLatency1dayEntry OBJECT-TYPE
    SYNTAX      IntervalLatency1dayEntry
    MAX-ACCESS  not-accessible
    STATUS      current
    DESCRIPTION   ""
    INDEX       {
                  entityIndex,
                  intervalLatency1dayNumber
                }
    ::=  { intervalLatency1dayTable 1 }

IntervalLatency1dayEntry ::=  SEQUENCE
  { intervalLatency1dayNumber Integer32,
    intervalLatency1dayLow Unsigned32,
    intervalLatency1dayMean Unsigned32,
    intervalLatency1dayHigh Unsigned32,
    intervalLatency1dayValidFlag TruthValue,
    intervalLatency1dayTimeStamp DateAndTime }

intervalLatency1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalLatency1dayEntry 1 }

intervalLatency1dayLow OBJECT-TYPE
    SYNTAX      Unsigned32 
    UNITS       "0.1 us"
    MAX-ACCESS  read-only
    STATUS      current
    DESCRIPTION
        "Measured round trip delay" 
    ::=  { intervalLatency1dayEntry 2 }

intervalLatency1dayMean OBJECT-TYPE
    SYNTAX      Unsigned32 
    UNITS       "0.1 us"
    MAX-ACCESS  read-only
    STATUS      current
    DESCRIPTION
        "Measured round trip delay" 
    ::=  { intervalLatency1dayEntry 3 }

intervalLatency1dayHigh OBJECT-TYPE
    SYNTAX      Unsigned32 
    UNITS       "0.1 us"
    MAX-ACCESS  read-only
    STATUS      current
    DESCRIPTION
        "Measured round trip delay" 
    ::=  { intervalLatency1dayEntry 4 }

intervalLatency1dayValidFlag OBJECT-TYPE
    SYNTAX      TruthValue
    MAX-ACCESS  read-only
    STATUS      current
    DESCRIPTION
        "Valid Flag" 
    ::=  { intervalLatency1dayEntry 5 }

intervalLatency1dayTimeStamp OBJECT-TYPE
    SYNTAX      DateAndTime
    MAX-ACCESS  read-only
    STATUS      current
    DESCRIPTION
        "Timestamp" 
    ::=  { intervalLatency1dayEntry 6 }

intervalLatency1weekTable OBJECT-TYPE
    SYNTAX      SEQUENCE OF IntervalLatency1weekEntry
    MAX-ACCESS  not-accessible
    STATUS      current
    DESCRIPTION   ""
    ::=  { performanceMonitoring 152 }

intervalLatency1weekEntry OBJECT-TYPE
    SYNTAX      IntervalLatency1weekEntry
    MAX-ACCESS  not-accessible
    STATUS      current
    DESCRIPTION   ""
    INDEX       {
                  entityIndex,
                  intervalLatency1weekNumber
                }
    ::=  { intervalLatency1weekTable 1 }

IntervalLatency1weekEntry ::=  SEQUENCE
  { intervalLatency1weekNumber Integer32,
    intervalLatency1weekLow Unsigned32,
    intervalLatency1weekMean Unsigned32,
    intervalLatency1weekHigh Unsigned32,
    intervalLatency1weekValidFlag TruthValue,
    intervalLatency1weekTimeStamp DateAndTime }

intervalLatency1weekNumber OBJECT-TYPE
    SYNTAX      Integer32 (1..52)
    MAX-ACCESS  not-accessible
    STATUS      current
    DESCRIPTION
        "Number 1week" 
    ::=  { intervalLatency1weekEntry 1 }

intervalLatency1weekLow OBJECT-TYPE
    SYNTAX      Unsigned32 
    UNITS       "0.1 us"
    MAX-ACCESS  read-only
    STATUS      current
    DESCRIPTION
        "Measured round trip delay" 
    ::=  { intervalLatency1weekEntry 2 }

intervalLatency1weekMean OBJECT-TYPE
    SYNTAX      Unsigned32 
    UNITS       "0.1 us"
    MAX-ACCESS  read-only
    STATUS      current
    DESCRIPTION
        "Measured round trip delay" 
    ::=  { intervalLatency1weekEntry 3 }

intervalLatency1weekHigh OBJECT-TYPE
    SYNTAX      Unsigned32 
    UNITS       "0.1 us"
    MAX-ACCESS  read-only
    STATUS      current
    DESCRIPTION
        "Measured round trip delay" 
    ::=  { intervalLatency1weekEntry 4 }

intervalLatency1weekValidFlag OBJECT-TYPE
    SYNTAX      TruthValue
    MAX-ACCESS  read-only
    STATUS      current
    DESCRIPTION
        "Valid Flag" 
    ::=  { intervalLatency1weekEntry 5 }

intervalLatency1weekTimeStamp OBJECT-TYPE
    SYNTAX      DateAndTime
    MAX-ACCESS  read-only
    STATUS      current
    DESCRIPTION
        "Timestamp" 
    ::=  { intervalLatency1weekEntry 6 }

intervalRoundTripDelay15minTable OBJECT-TYPE
    SYNTAX      SEQUENCE OF IntervalRoundTripDelay15minEntry
    MAX-ACCESS  not-accessible
    STATUS      current
    DESCRIPTION   ""
    ::=  { performanceMonitoring 153 }

intervalRoundTripDelay15minEntry OBJECT-TYPE
    SYNTAX      IntervalRoundTripDelay15minEntry
    MAX-ACCESS  not-accessible
    STATUS      current
    DESCRIPTION   ""
    INDEX       {
                  entityIndex,
                  intervalRoundTripDelay15minNumber
                }
    ::=  { intervalRoundTripDelay15minTable 1 }

IntervalRoundTripDelay15minEntry ::=  SEQUENCE
  { intervalRoundTripDelay15minNumber Integer32,
    intervalRoundTripDelay15minLow Unsigned32,
    intervalRoundTripDelay15minMean Unsigned32,
    intervalRoundTripDelay15minHigh Unsigned32,
    intervalRoundTripDelay15minValidFlag TruthValue,
    intervalRoundTripDelay15minTimeStamp DateAndTime }

intervalRoundTripDelay15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalRoundTripDelay15minEntry 1 }

intervalRoundTripDelay15minLow OBJECT-TYPE
    SYNTAX      Unsigned32 
    UNITS       "ns"
    MAX-ACCESS  read-only
    STATUS      current
    DESCRIPTION
        "Measured round trip delay low" 
    ::=  { intervalRoundTripDelay15minEntry 2 }

intervalRoundTripDelay15minMean OBJECT-TYPE
    SYNTAX      Unsigned32 
    UNITS       "ns"
    MAX-ACCESS  read-only
    STATUS      current
    DESCRIPTION
        "Measured round trip delay mean" 
    ::=  { intervalRoundTripDelay15minEntry 3 }

intervalRoundTripDelay15minHigh OBJECT-TYPE
    SYNTAX      Unsigned32 
    UNITS       "ns"
    MAX-ACCESS  read-only
    STATUS      current
    DESCRIPTION
        "Measured round trip delay high" 
    ::=  { intervalRoundTripDelay15minEntry 4 }

intervalRoundTripDelay15minValidFlag OBJECT-TYPE
    SYNTAX      TruthValue
    MAX-ACCESS  read-only
    STATUS      current
    DESCRIPTION
        "Valid Flag" 
    ::=  { intervalRoundTripDelay15minEntry 5 }

intervalRoundTripDelay15minTimeStamp OBJECT-TYPE
    SYNTAX      DateAndTime
    MAX-ACCESS  read-only
    STATUS      current
    DESCRIPTION
        "Timestamp" 
    ::=  { intervalRoundTripDelay15minEntry 6 }

intervalRoundTripDelay1dayTable OBJECT-TYPE
    SYNTAX      SEQUENCE OF IntervalRoundTripDelay1dayEntry
    MAX-ACCESS  not-accessible
    STATUS      current
    DESCRIPTION   ""
    ::=  { performanceMonitoring 154 }

intervalRoundTripDelay1dayEntry OBJECT-TYPE
    SYNTAX      IntervalRoundTripDelay1dayEntry
    MAX-ACCESS  not-accessible
    STATUS      current
    DESCRIPTION   ""
    INDEX       {
                  entityIndex,
                  intervalRoundTripDelay1dayNumber
                }
    ::=  { intervalRoundTripDelay1dayTable 1 }

IntervalRoundTripDelay1dayEntry ::=  SEQUENCE
  { intervalRoundTripDelay1dayNumber Integer32,
    intervalRoundTripDelay1dayLow Unsigned32,
    intervalRoundTripDelay1dayMean Unsigned32,
    intervalRoundTripDelay1dayHigh Unsigned32,
    intervalRoundTripDelay1dayValidFlag TruthValue,
    intervalRoundTripDelay1dayTimeStamp DateAndTime }

intervalRoundTripDelay1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalRoundTripDelay1dayEntry 1 }

intervalRoundTripDelay1dayLow OBJECT-TYPE
    SYNTAX      Unsigned32 
    UNITS       "ns"
    MAX-ACCESS  read-only
    STATUS      current
    DESCRIPTION
        "Measured round trip delay low" 
    ::=  { intervalRoundTripDelay1dayEntry 2 }

intervalRoundTripDelay1dayMean OBJECT-TYPE
    SYNTAX      Unsigned32 
    UNITS       "ns"
    MAX-ACCESS  read-only
    STATUS      current
    DESCRIPTION
        "Measured round trip delay mean" 
    ::=  { intervalRoundTripDelay1dayEntry 3 }

intervalRoundTripDelay1dayHigh OBJECT-TYPE
    SYNTAX      Unsigned32 
    UNITS       "ns"
    MAX-ACCESS  read-only
    STATUS      current
    DESCRIPTION
        "Measured round trip delay high" 
    ::=  { intervalRoundTripDelay1dayEntry 4 }

intervalRoundTripDelay1dayValidFlag OBJECT-TYPE
    SYNTAX      TruthValue
    MAX-ACCESS  read-only
    STATUS      current
    DESCRIPTION
        "Valid Flag" 
    ::=  { intervalRoundTripDelay1dayEntry 5 }

intervalRoundTripDelay1dayTimeStamp OBJECT-TYPE
    SYNTAX      DateAndTime
    MAX-ACCESS  read-only
    STATUS      current
    DESCRIPTION
        "Timestamp" 
    ::=  { intervalRoundTripDelay1dayEntry 6 }

intervalRoundTripDelay1weekTable OBJECT-TYPE
    SYNTAX      SEQUENCE OF IntervalRoundTripDelay1weekEntry
    MAX-ACCESS  not-accessible
    STATUS      current
    DESCRIPTION   ""
    ::=  { performanceMonitoring 155 }

intervalRoundTripDelay1weekEntry OBJECT-TYPE
    SYNTAX      IntervalRoundTripDelay1weekEntry
    MAX-ACCESS  not-accessible
    STATUS      current
    DESCRIPTION   ""
    INDEX       {
                  entityIndex,
                  intervalRoundTripDelay1weekNumber
                }
    ::=  { intervalRoundTripDelay1weekTable 1 }

IntervalRoundTripDelay1weekEntry ::=  SEQUENCE
  { intervalRoundTripDelay1weekNumber Integer32,
    intervalRoundTripDelay1weekLow Unsigned32,
    intervalRoundTripDelay1weekMean Unsigned32,
    intervalRoundTripDelay1weekHigh Unsigned32,
    intervalRoundTripDelay1weekValidFlag TruthValue,
    intervalRoundTripDelay1weekTimeStamp DateAndTime }

intervalRoundTripDelay1weekNumber OBJECT-TYPE
    SYNTAX      Integer32 (1..52)
    MAX-ACCESS  not-accessible
    STATUS      current
    DESCRIPTION
        "Number 1week" 
    ::=  { intervalRoundTripDelay1weekEntry 1 }

intervalRoundTripDelay1weekLow OBJECT-TYPE
    SYNTAX      Unsigned32 
    UNITS       "ns"
    MAX-ACCESS  read-only
    STATUS      current
    DESCRIPTION
        "Measured round trip delay low" 
    ::=  { intervalRoundTripDelay1weekEntry 2 }

intervalRoundTripDelay1weekMean OBJECT-TYPE
    SYNTAX      Unsigned32 
    UNITS       "ns"
    MAX-ACCESS  read-only
    STATUS      current
    DESCRIPTION
        "Measured round trip delay mean" 
    ::=  { intervalRoundTripDelay1weekEntry 3 }

intervalRoundTripDelay1weekHigh OBJECT-TYPE
    SYNTAX      Unsigned32 
    UNITS       "ns"
    MAX-ACCESS  read-only
    STATUS      current
    DESCRIPTION
        "Measured round trip delay high" 
    ::=  { intervalRoundTripDelay1weekEntry 4 }

intervalRoundTripDelay1weekValidFlag OBJECT-TYPE
    SYNTAX      TruthValue
    MAX-ACCESS  read-only
    STATUS      current
    DESCRIPTION
        "Valid Flag" 
    ::=  { intervalRoundTripDelay1weekEntry 5 }

intervalRoundTripDelay1weekTimeStamp OBJECT-TYPE
    SYNTAX      DateAndTime
    MAX-ACCESS  read-only
    STATUS      current
    DESCRIPTION
        "Timestamp" 
    ::=  { intervalRoundTripDelay1weekEntry 6 }

currentPmSnapshotTable OBJECT-TYPE
    SYNTAX      SEQUENCE OF CurrentPmSnapshotEntry
    MAX-ACCESS  not-accessible
    STATUS      current
    DESCRIPTION   ""
    ::=  { performanceMonitoring 156 }

currentPmSnapshotEntry OBJECT-TYPE
    SYNTAX      CurrentPmSnapshotEntry
    MAX-ACCESS  not-accessible
    STATUS      current
    DESCRIPTION   ""
    INDEX       {
                  entityIndex
                }
    ::=  { currentPmSnapshotTable 1 }

CurrentPmSnapshotEntry ::=  SEQUENCE
  { currentPmSnapshotOutputPower Integer32,
    currentPmSnapshotInputPower Integer32,
    currentPmSnapshotAttenuation Integer32,
    currentPmSnapshotAttenuationOfVoa Unsigned32,
    currentPmSnapshotOscGain Unsigned32,
    currentPmSnapshotBackreflectionPowerReceived Integer32,
    currentPmSnapshotRamanPumpPower Integer32,
    currentPmSnapshotOscPowerReceived Integer32,
    currentPmSnapshotVariableGain Unsigned32,
    currentPmSnapshotTxLineAttenuation Integer32,
    currentPmSnapshotRxLineAttenuation Integer32 }

currentPmSnapshotOutputPower OBJECT-TYPE
    SYNTAX      Integer32 
    UNITS       "0.1 dBm"
    MAX-ACCESS  read-only
    STATUS      current
    DESCRIPTION
        "Instantaneous Optical Power Transmitted (Output)" 
    ::=  { currentPmSnapshotEntry 1 }

currentPmSnapshotInputPower OBJECT-TYPE
    SYNTAX      Integer32 
    UNITS       "0.1 dBm"
    MAX-ACCESS  read-only
    STATUS      current
    DESCRIPTION
        "Total Optical Input Power Received" 
    ::=  { currentPmSnapshotEntry 2 }

currentPmSnapshotAttenuation OBJECT-TYPE
    SYNTAX      Integer32 
    UNITS       "0.1 dB"
    MAX-ACCESS  read-only
    STATUS      current
    DESCRIPTION
        "Signal attenuation in dB associated with Port. Generally, this parameter is used for the EDFA mid-stage access port (Port 2) and is the attenuation between the first stage transmit (Port 2 Tx) and the second stage receive (Port 2 Rx)." 
    ::=  { currentPmSnapshotEntry 3 }

currentPmSnapshotAttenuationOfVoa OBJECT-TYPE
    SYNTAX      Unsigned32 
    UNITS       "0.1 dB"
    MAX-ACCESS  read-only
    STATUS      current
    DESCRIPTION
        "Variable Attenuator attenuation in dB" 
    ::=  { currentPmSnapshotEntry 4 }

currentPmSnapshotOscGain OBJECT-TYPE
    SYNTAX      Unsigned32 
    UNITS       "0.1 dB"
    MAX-ACCESS  read-only
    STATUS      current
    DESCRIPTION
        "Current Raman OSC gain" 
    ::=  { currentPmSnapshotEntry 5 }

currentPmSnapshotBackreflectionPowerReceived OBJECT-TYPE
    SYNTAX      Integer32 
    UNITS       "0.1 dB"
    MAX-ACCESS  read-only
    STATUS      current
    DESCRIPTION
        "Back Reflection Received Current" 
    ::=  { currentPmSnapshotEntry 6 }

currentPmSnapshotRamanPumpPower OBJECT-TYPE
    SYNTAX      Integer32 
    UNITS       "0.1 dBm"
    MAX-ACCESS  read-only
    STATUS      current
    DESCRIPTION
        "Total raman pump power" 
    ::=  { currentPmSnapshotEntry 7 }

currentPmSnapshotOscPowerReceived OBJECT-TYPE
    SYNTAX      Integer32 
    UNITS       "0.1 dBm"
    MAX-ACCESS  read-only
    STATUS      current
    DESCRIPTION
        "Optical Supervisory Channel Input Power Received Current" 
    ::=  { currentPmSnapshotEntry 8 }

currentPmSnapshotVariableGain OBJECT-TYPE
    SYNTAX      Unsigned32 
    UNITS       "0.1 dB"
    MAX-ACCESS  read-only
    STATUS      current
    DESCRIPTION
        "Variable Gain of EDFA" 
    ::=  { currentPmSnapshotEntry 9 }

currentPmSnapshotTxLineAttenuation OBJECT-TYPE
    SYNTAX      Integer32 
    UNITS       "0.1 dB"
    MAX-ACCESS  read-only
    STATUS      current
    DESCRIPTION
        "Attenuation of Transmit Fiber" 
    ::=  { currentPmSnapshotEntry 10 }

currentPmSnapshotRxLineAttenuation OBJECT-TYPE
    SYNTAX      Integer32 
    UNITS       "0.1 dB"
    MAX-ACCESS  read-only
    STATUS      current
    DESCRIPTION
        "Attenuation of Receive Fiber" 
    ::=  { currentPmSnapshotEntry 11 }

intervalPmSnapshotTable OBJECT-TYPE
    SYNTAX      SEQUENCE OF IntervalPmSnapshotEntry
    MAX-ACCESS  not-accessible
    STATUS      current
    DESCRIPTION   ""
    ::=  { performanceMonitoring 157 }

intervalPmSnapshotEntry OBJECT-TYPE
    SYNTAX      IntervalPmSnapshotEntry
    MAX-ACCESS  not-accessible
    STATUS      current
    DESCRIPTION   ""
    INDEX       {
                  intervalPmSnapshotParameter,
                  entityIndex,
                  intervalPmSnapshotNumber
                }
    ::=  { intervalPmSnapshotTable 1 }

IntervalPmSnapshotEntry ::=  SEQUENCE
  { intervalPmSnapshotParameter FspR7PmSnapshotParameterTypes,
    intervalPmSnapshotNumber Unsigned32,
    intervalPmSnapshotValue Integer32,
    intervalPmSnapshotValidFlag TruthValue,
    intervalPmSnapshotTimeStamp DateAndTime }

intervalPmSnapshotParameter OBJECT-TYPE
    SYNTAX      FspR7PmSnapshotParameterTypes
    MAX-ACCESS  not-accessible
    STATUS      current
    DESCRIPTION   "Index representing the PM parameter"
    ::=  { intervalPmSnapshotEntry 1 }

intervalPmSnapshotNumber OBJECT-TYPE
    SYNTAX      Unsigned32 (1..10)
    MAX-ACCESS  not-accessible
    STATUS      current
    DESCRIPTION
        "Record number of optical power reference level" 
    ::=  { intervalPmSnapshotEntry 2 }

intervalPmSnapshotValue OBJECT-TYPE
    SYNTAX      Integer32 
    UNITS       "0.1"
    MAX-ACCESS  read-only
    STATUS      current
    DESCRIPTION   "Different units are used for specific parameters (intervalPmSnapshotParameter - the first index of the table):
         'dBm' for OutputPower, InputPower, RamanPumpPower, OscPowerReceived;
         'dB' for Attenuation, AttenuationOfVoa, OscGain, BackreflectionPowerReceived, TxLineAttenuation, RxLineAttenuation;
         'no unit' for VariableGain."
    ::=  { intervalPmSnapshotEntry 3 }

intervalPmSnapshotValidFlag OBJECT-TYPE
    SYNTAX      TruthValue
    MAX-ACCESS  read-only
    STATUS      current
    DESCRIPTION
        "Valid Flag" 
    ::=  { intervalPmSnapshotEntry 4 }

intervalPmSnapshotTimeStamp OBJECT-TYPE
    SYNTAX      DateAndTime
    MAX-ACCESS  read-only
    STATUS      current
    DESCRIPTION
        "Timestamp" 
    ::=  { intervalPmSnapshotEntry 5 }

intervalPhysPerfOscOpticalOutputPwr15minTable OBJECT-TYPE
    SYNTAX      SEQUENCE OF IntervalPhysPerfOscOpticalOutputPwr15minEntry
    MAX-ACCESS  not-accessible
    STATUS      current
    DESCRIPTION   ""
    ::=  { performanceMonitoring 158 }

intervalPhysPerfOscOpticalOutputPwr15minEntry OBJECT-TYPE
    SYNTAX      IntervalPhysPerfOscOpticalOutputPwr15minEntry
    MAX-ACCESS  not-accessible
    STATUS      current
    DESCRIPTION   ""
    INDEX       {
                  entityIndex,
                  intervalPhysPerfOscOpticalOutputPwr15minNumber
                }
    ::=  { intervalPhysPerfOscOpticalOutputPwr15minTable 1 }

IntervalPhysPerfOscOpticalOutputPwr15minEntry ::=  SEQUENCE
  { intervalPhysPerfOscOpticalOutputPwr15minNumber Integer32,
    intervalPhysPerfOscOpticalOutputPwr15minLow Integer32,
    intervalPhysPerfOscOpticalOutputPwr15minMean Integer32,
    intervalPhysPerfOscOpticalOutputPwr15minHigh Integer32,
    intervalPhysPerfOscOpticalOutputPwr15minValidFlag TruthValue,
    intervalPhysPerfOscOpticalOutputPwr15minTimeStamp DateAndTime }

intervalPhysPerfOscOpticalOutputPwr15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfOscOpticalOutputPwr15minEntry 1 }

intervalPhysPerfOscOpticalOutputPwr15minLow OBJECT-TYPE
    SYNTAX      Integer32 
    UNITS       "0.1 dBm"
    MAX-ACCESS  read-only
    STATUS      current
    DESCRIPTION
        "OSC Optical Output Power Transmitted" 
    ::=  { intervalPhysPerfOscOpticalOutputPwr15minEntry 2 }

intervalPhysPerfOscOpticalOutputPwr15minMean OBJECT-TYPE
    SYNTAX      Integer32 
    UNITS       "0.1 dBm"
    MAX-ACCESS  read-only
    STATUS      current
    DESCRIPTION
        "OSC Optical Output Power Transmitted" 
    ::=  { intervalPhysPerfOscOpticalOutputPwr15minEntry 3 }

intervalPhysPerfOscOpticalOutputPwr15minHigh OBJECT-TYPE
    SYNTAX      Integer32 
    UNITS       "0.1 dBm"
    MAX-ACCESS  read-only
    STATUS      current
    DESCRIPTION
        "OSC Optical Output Power Transmitted" 
    ::=  { intervalPhysPerfOscOpticalOutputPwr15minEntry 4 }

intervalPhysPerfOscOpticalOutputPwr15minValidFlag OBJECT-TYPE
    SYNTAX      TruthValue
    MAX-ACCESS  read-only
    STATUS      current
    DESCRIPTION
        "Valid Flag" 
    ::=  { intervalPhysPerfOscOpticalOutputPwr15minEntry 5 }

intervalPhysPerfOscOpticalOutputPwr15minTimeStamp OBJECT-TYPE
    SYNTAX      DateAndTime
    MAX-ACCESS  read-only
    STATUS      current
    DESCRIPTION
        "Timestamp" 
    ::=  { intervalPhysPerfOscOpticalOutputPwr15minEntry 6 }

intervalPhysPerfOscOpticalOutputPwr1dayTable OBJECT-TYPE
    SYNTAX      SEQUENCE OF IntervalPhysPerfOscOpticalOutputPwr1dayEntry
    MAX-ACCESS  not-accessible
    STATUS      current
    DESCRIPTION   ""
    ::=  { performanceMonitoring 159 }

intervalPhysPerfOscOpticalOutputPwr1dayEntry OBJECT-TYPE
    SYNTAX      IntervalPhysPerfOscOpticalOutputPwr1dayEntry
    MAX-ACCESS  not-accessible
    STATUS      current
    DESCRIPTION   ""
    INDEX       {
                  entityIndex,
                  intervalPhysPerfOscOpticalOutputPwr1dayNumber
                }
    ::=  { intervalPhysPerfOscOpticalOutputPwr1dayTable 1 }

IntervalPhysPerfOscOpticalOutputPwr1dayEntry ::=  SEQUENCE
  { intervalPhysPerfOscOpticalOutputPwr1dayNumber Integer32,
    intervalPhysPerfOscOpticalOutputPwr1dayLow Integer32,
    intervalPhysPerfOscOpticalOutputPwr1dayMean Integer32,
    intervalPhysPerfOscOpticalOutputPwr1dayHigh Integer32,
    intervalPhysPerfOscOpticalOutputPwr1dayValidFlag TruthValue,
    intervalPhysPerfOscOpticalOutputPwr1dayTimeStamp DateAndTime }

intervalPhysPerfOscOpticalOutputPwr1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfOscOpticalOutputPwr1dayEntry 1 }

intervalPhysPerfOscOpticalOutputPwr1dayLow OBJECT-TYPE
    SYNTAX      Integer32 
    UNITS       "0.1 dBm"
    MAX-ACCESS  read-only
    STATUS      current
    DESCRIPTION
        "OSC Optical Output Power Transmitted" 
    ::=  { intervalPhysPerfOscOpticalOutputPwr1dayEntry 2 }

intervalPhysPerfOscOpticalOutputPwr1dayMean OBJECT-TYPE
    SYNTAX      Integer32 
    UNITS       "0.1 dBm"
    MAX-ACCESS  read-only
    STATUS      current
    DESCRIPTION
        "OSC Optical Output Power Transmitted" 
    ::=  { intervalPhysPerfOscOpticalOutputPwr1dayEntry 3 }

intervalPhysPerfOscOpticalOutputPwr1dayHigh OBJECT-TYPE
    SYNTAX      Integer32 
    UNITS       "0.1 dBm"
    MAX-ACCESS  read-only
    STATUS      current
    DESCRIPTION
        "OSC Optical Output Power Transmitted" 
    ::=  { intervalPhysPerfOscOpticalOutputPwr1dayEntry 4 }

intervalPhysPerfOscOpticalOutputPwr1dayValidFlag OBJECT-TYPE
    SYNTAX      TruthValue
    MAX-ACCESS  read-only
    STATUS      current
    DESCRIPTION
        "Valid Flag" 
    ::=  { intervalPhysPerfOscOpticalOutputPwr1dayEntry 5 }

intervalPhysPerfOscOpticalOutputPwr1dayTimeStamp OBJECT-TYPE
    SYNTAX      DateAndTime
    MAX-ACCESS  read-only
    STATUS      current
    DESCRIPTION
        "Timestamp" 
    ::=  { intervalPhysPerfOscOpticalOutputPwr1dayEntry 6 }

intervalPhysPerfOscOpticalOutputPwr1weekTable OBJECT-TYPE
    SYNTAX      SEQUENCE OF IntervalPhysPerfOscOpticalOutputPwr1weekEntry
    MAX-ACCESS  not-accessible
    STATUS      current
    DESCRIPTION   ""
    ::=  { performanceMonitoring 160 }

intervalPhysPerfOscOpticalOutputPwr1weekEntry OBJECT-TYPE
    SYNTAX      IntervalPhysPerfOscOpticalOutputPwr1weekEntry
    MAX-ACCESS  not-accessible
    STATUS      current
    DESCRIPTION   ""
    INDEX       {
                  entityIndex,
                  intervalPhysPerfOscOpticalOutputPwr1weekNumber
                }
    ::=  { intervalPhysPerfOscOpticalOutputPwr1weekTable 1 }

IntervalPhysPerfOscOpticalOutputPwr1weekEntry ::=  SEQUENCE
  { intervalPhysPerfOscOpticalOutputPwr1weekNumber Integer32,
    intervalPhysPerfOscOpticalOutputPwr1weekLow Integer32,
    intervalPhysPerfOscOpticalOutputPwr1weekMean Integer32,
    intervalPhysPerfOscOpticalOutputPwr1weekHigh Integer32,
    intervalPhysPerfOscOpticalOutputPwr1weekValidFlag TruthValue,
    intervalPhysPerfOscOpticalOutputPwr1weekTimeStamp DateAndTime }

intervalPhysPerfOscOpticalOutputPwr1weekNumber OBJECT-TYPE
    SYNTAX      Integer32 (1..52)
    MAX-ACCESS  not-accessible
    STATUS      current
    DESCRIPTION
        "Number 1week" 
    ::=  { intervalPhysPerfOscOpticalOutputPwr1weekEntry 1 }

intervalPhysPerfOscOpticalOutputPwr1weekLow OBJECT-TYPE
    SYNTAX      Integer32 
    UNITS       "0.1 dBm"
    MAX-ACCESS  read-only
    STATUS      current
    DESCRIPTION
        "OSC Optical Output Power Transmitted" 
    ::=  { intervalPhysPerfOscOpticalOutputPwr1weekEntry 2 }

intervalPhysPerfOscOpticalOutputPwr1weekMean OBJECT-TYPE
    SYNTAX      Integer32 
    UNITS       "0.1 dBm"
    MAX-ACCESS  read-only
    STATUS      current
    DESCRIPTION
        "OSC Optical Output Power Transmitted" 
    ::=  { intervalPhysPerfOscOpticalOutputPwr1weekEntry 3 }

intervalPhysPerfOscOpticalOutputPwr1weekHigh OBJECT-TYPE
    SYNTAX      Integer32 
    UNITS       "0.1 dBm"
    MAX-ACCESS  read-only
    STATUS      current
    DESCRIPTION
        "OSC Optical Output Power Transmitted" 
    ::=  { intervalPhysPerfOscOpticalOutputPwr1weekEntry 4 }

intervalPhysPerfOscOpticalOutputPwr1weekValidFlag OBJECT-TYPE
    SYNTAX      TruthValue
    MAX-ACCESS  read-only
    STATUS      current
    DESCRIPTION
        "Valid Flag" 
    ::=  { intervalPhysPerfOscOpticalOutputPwr1weekEntry 5 }

intervalPhysPerfOscOpticalOutputPwr1weekTimeStamp OBJECT-TYPE
    SYNTAX      DateAndTime
    MAX-ACCESS  read-only
    STATUS      current
    DESCRIPTION
        "Timestamp" 
    ::=  { intervalPhysPerfOscOpticalOutputPwr1weekEntry 6 }

currentPhysConvTxHighSpeed15minTable OBJECT-TYPE
    SYNTAX      SEQUENCE OF CurrentPhysConvTxHighSpeed15minEntry
    MAX-ACCESS  not-accessible
    STATUS      current
    DESCRIPTION   ""
    ::=  { performanceMonitoring 161 }

currentPhysConvTxHighSpeed15minEntry OBJECT-TYPE
    SYNTAX      CurrentPhysConvTxHighSpeed15minEntry
    MAX-ACCESS  not-accessible
    STATUS      current
    DESCRIPTION   ""
    INDEX       {
                  entityIndex
                }
    ::=  { currentPhysConvTxHighSpeed15minTable 1 }

CurrentPhysConvTxHighSpeed15minEntry ::=  SEQUENCE
  { currentPhysConvTxHighSpeed15minESTX Unsigned32,
    currentPhysConvTxHighSpeed15minCVTX Counter64String,
    currentPhysConvTxHighSpeed15minSETX Unsigned32,
    currentPhysConvTxHighSpeed15minElapsedTime Integer32 }

currentPhysConvTxHighSpeed15minESTX OBJECT-TYPE
    SYNTAX      Unsigned32
    MAX-ACCESS  read-only
    STATUS      current
    DESCRIPTION
        "Physical Coding Layer Transmit Errored Seconds" 
    ::=  { currentPhysConvTxHighSpeed15minEntry 1 }

currentPhysConvTxHighSpeed15minCVTX OBJECT-TYPE
    SYNTAX      Counter64String
    MAX-ACCESS  read-only
    STATUS      current
    DESCRIPTION
        "Physical Coding Layer Transmit Coding Violations" 
    ::=  { currentPhysConvTxHighSpeed15minEntry 2 }

currentPhysConvTxHighSpeed15minSETX OBJECT-TYPE
    SYNTAX      Unsigned32
    MAX-ACCESS  read-only
    STATUS      current
    DESCRIPTION
        "Physical Coding Layer Sync Header Errors Transmit" 
    ::=  { currentPhysConvTxHighSpeed15minEntry 3 }

currentPhysConvTxHighSpeed15minElapsedTime OBJECT-TYPE
    SYNTAX      Integer32 (0..9000 | -2147483648)
    MAX-ACCESS  read-only
    STATUS      current
    DESCRIPTION
        "Elapsed 15Min" 
    ::=  { currentPhysConvTxHighSpeed15minEntry 4 }

currentPhysConvTxHighSpeed1dayTable OBJECT-TYPE
    SYNTAX      SEQUENCE OF CurrentPhysConvTxHighSpeed1dayEntry
    MAX-ACCESS  not-accessible
    STATUS      current
    DESCRIPTION   ""
    ::=  { performanceMonitoring 162 }

currentPhysConvTxHighSpeed1dayEntry OBJECT-TYPE
    SYNTAX      CurrentPhysConvTxHighSpeed1dayEntry
    MAX-ACCESS  not-accessible
    STATUS      current
    DESCRIPTION   ""
    INDEX       {
                  entityIndex
                }
    ::=  { currentPhysConvTxHighSpeed1dayTable 1 }

CurrentPhysConvTxHighSpeed1dayEntry ::=  SEQUENCE
  { currentPhysConvTxHighSpeed1dayESTX Unsigned32,
    currentPhysConvTxHighSpeed1dayCVTX Counter64String,
    currentPhysConvTxHighSpeed1daySETX Unsigned32,
    currentPhysConvTxHighSpeed1dayElapsedTime Integer32 }

currentPhysConvTxHighSpeed1dayESTX OBJECT-TYPE
    SYNTAX      Unsigned32
    MAX-ACCESS  read-only
    STATUS      current
    DESCRIPTION
        "Physical Coding Layer Transmit Errored Seconds" 
    ::=  { currentPhysConvTxHighSpeed1dayEntry 1 }

currentPhysConvTxHighSpeed1dayCVTX OBJECT-TYPE
    SYNTAX      Counter64String
    MAX-ACCESS  read-only
    STATUS      current
    DESCRIPTION
        "Physical Coding Layer Transmit Coding Violations" 
    ::=  { currentPhysConvTxHighSpeed1dayEntry 2 }

currentPhysConvTxHighSpeed1daySETX OBJECT-TYPE
    SYNTAX      Unsigned32
    MAX-ACCESS  read-only
    STATUS      current
    DESCRIPTION
        "Physical Coding Layer Sync Header Errors Transmit" 
    ::=  { currentPhysConvTxHighSpeed1dayEntry 3 }

currentPhysConvTxHighSpeed1dayElapsedTime OBJECT-TYPE
    SYNTAX      Integer32 (0..86400 | -2147483648)
    MAX-ACCESS  read-only
    STATUS      current
    DESCRIPTION
        "Elapsed 1Day" 
    ::=  { currentPhysConvTxHighSpeed1dayEntry 4 }

intervalPhysConvTxHighSpeed15minTable OBJECT-TYPE
    SYNTAX      SEQUENCE OF IntervalPhysConvTxHighSpeed15minEntry
    MAX-ACCESS  not-accessible
    STATUS      current
    DESCRIPTION   ""
    ::=  { performanceMonitoring 163 }

intervalPhysConvTxHighSpeed15minEntry OBJECT-TYPE
    SYNTAX      IntervalPhysConvTxHighSpeed15minEntry
    MAX-ACCESS  not-accessible
    STATUS      current
    DESCRIPTION   ""
    INDEX       {
                  entityIndex,
                  intervalPhysConvTxHighSpeed15minNumber
                }
    ::=  { intervalPhysConvTxHighSpeed15minTable 1 }

IntervalPhysConvTxHighSpeed15minEntry ::=  SEQUENCE
  { intervalPhysConvTxHighSpeed15minNumber Integer32,
    intervalPhysConvTxHighSpeed15minESTX Unsigned32,
    intervalPhysConvTxHighSpeed15minCVTX Counter64String,
    intervalPhysConvTxHighSpeed15minSETX Unsigned32,
    intervalPhysConvTxHighSpeed15minValidFlag TruthValue,
    intervalPhysConvTxHighSpeed15minTimeStamp DateAndTime }

intervalPhysConvTxHighSpeed15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysConvTxHighSpeed15minEntry 1 }

intervalPhysConvTxHighSpeed15minESTX OBJECT-TYPE
    SYNTAX      Unsigned32
    MAX-ACCESS  read-only
    STATUS      current
    DESCRIPTION
        "Physical Coding Layer Transmit Errored Seconds" 
    ::=  { intervalPhysConvTxHighSpeed15minEntry 2 }

intervalPhysConvTxHighSpeed15minCVTX OBJECT-TYPE
    SYNTAX      Counter64String
    MAX-ACCESS  read-only
    STATUS      current
    DESCRIPTION
        "Physical Coding Layer Transmit Coding Violations" 
    ::=  { intervalPhysConvTxHighSpeed15minEntry 3 }

intervalPhysConvTxHighSpeed15minSETX OBJECT-TYPE
    SYNTAX      Unsigned32
    MAX-ACCESS  read-only
    STATUS      current
    DESCRIPTION
        "Physical Coding Layer Sync Header Errors Transmit" 
    ::=  { intervalPhysConvTxHighSpeed15minEntry 4 }

intervalPhysConvTxHighSpeed15minValidFlag OBJECT-TYPE
    SYNTAX      TruthValue
    MAX-ACCESS  read-only
    STATUS      current
    DESCRIPTION
        "Valid Flag" 
    ::=  { intervalPhysConvTxHighSpeed15minEntry 5 }

intervalPhysConvTxHighSpeed15minTimeStamp OBJECT-TYPE
    SYNTAX      DateAndTime
    MAX-ACCESS  read-only
    STATUS      current
    DESCRIPTION
        "Timestamp" 
    ::=  { intervalPhysConvTxHighSpeed15minEntry 6 }

intervalPhysConvTxHighSpeed1dayTable OBJECT-TYPE
    SYNTAX      SEQUENCE OF IntervalPhysConvTxHighSpeed1dayEntry
    MAX-ACCESS  not-accessible
    STATUS      current
    DESCRIPTION   ""
    ::=  { performanceMonitoring 164 }

intervalPhysConvTxHighSpeed1dayEntry OBJECT-TYPE
    SYNTAX      IntervalPhysConvTxHighSpeed1dayEntry
    MAX-ACCESS  not-accessible
    STATUS      current
    DESCRIPTION   ""
    INDEX       {
                  entityIndex,
                  intervalPhysConvTxHighSpeed1dayNumber
                }
    ::=  { intervalPhysConvTxHighSpeed1dayTable 1 }

IntervalPhysConvTxHighSpeed1dayEntry ::=  SEQUENCE
  { intervalPhysConvTxHighSpeed1dayNumber Integer32,
    intervalPhysConvTxHighSpeed1dayESTX Unsigned32,
    intervalPhysConvTxHighSpeed1dayCVTX Counter64String,
    intervalPhysConvTxHighSpeed1daySETX Unsigned32,
    intervalPhysConvTxHighSpeed1dayValidFlag TruthValue,
    intervalPhysConvTxHighSpeed1dayTimeStamp DateAndTime }

intervalPhysConvTxHighSpeed1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysConvTxHighSpeed1dayEntry 1 }

intervalPhysConvTxHighSpeed1dayESTX OBJECT-TYPE
    SYNTAX      Unsigned32
    MAX-ACCESS  read-only
    STATUS      current
    DESCRIPTION
        "Physical Coding Layer Transmit Errored Seconds" 
    ::=  { intervalPhysConvTxHighSpeed1dayEntry 2 }

intervalPhysConvTxHighSpeed1dayCVTX OBJECT-TYPE
    SYNTAX      Counter64String
    MAX-ACCESS  read-only
    STATUS      current
    DESCRIPTION
        "Physical Coding Layer Transmit Coding Violations" 
    ::=  { intervalPhysConvTxHighSpeed1dayEntry 3 }

intervalPhysConvTxHighSpeed1daySETX OBJECT-TYPE
    SYNTAX      Unsigned32
    MAX-ACCESS  read-only
    STATUS      current
    DESCRIPTION
        "Physical Coding Layer Sync Header Errors Transmit" 
    ::=  { intervalPhysConvTxHighSpeed1dayEntry 4 }

intervalPhysConvTxHighSpeed1dayValidFlag OBJECT-TYPE
    SYNTAX      TruthValue
    MAX-ACCESS  read-only
    STATUS      current
    DESCRIPTION
        "Valid Flag" 
    ::=  { intervalPhysConvTxHighSpeed1dayEntry 5 }

intervalPhysConvTxHighSpeed1dayTimeStamp OBJECT-TYPE
    SYNTAX      DateAndTime
    MAX-ACCESS  read-only
    STATUS      current
    DESCRIPTION
        "Timestamp" 
    ::=  { intervalPhysConvTxHighSpeed1dayEntry 6 }

intervalPhysPerfDiffGrDelay15minTable OBJECT-TYPE
    SYNTAX      SEQUENCE OF IntervalPhysPerfDiffGrDelay15minEntry
    MAX-ACCESS  not-accessible
    STATUS      current
    DESCRIPTION   ""
    ::=  { performanceMonitoring 165 }

intervalPhysPerfDiffGrDelay15minEntry OBJECT-TYPE
    SYNTAX      IntervalPhysPerfDiffGrDelay15minEntry
    MAX-ACCESS  not-accessible
    STATUS      current
    DESCRIPTION   ""
    INDEX       {
                  entityIndex,
                  intervalPhysPerfDiffGrDelay15minNumber
                }
    ::=  { intervalPhysPerfDiffGrDelay15minTable 1 }

IntervalPhysPerfDiffGrDelay15minEntry ::=  SEQUENCE
  { intervalPhysPerfDiffGrDelay15minNumber Integer32,
    intervalPhysPerfDiffGrDelay15minLow Integer32,
    intervalPhysPerfDiffGrDelay15minMean Integer32,
    intervalPhysPerfDiffGrDelay15minHigh Integer32,
    intervalPhysPerfDiffGrDelay15minValidFlag TruthValue,
    intervalPhysPerfDiffGrDelay15minTimeStamp DateAndTime }

intervalPhysPerfDiffGrDelay15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfDiffGrDelay15minEntry 1 }

intervalPhysPerfDiffGrDelay15minLow OBJECT-TYPE
    SYNTAX      Integer32 
    UNITS       "ps"
    MAX-ACCESS  read-only
    STATUS      current
    DESCRIPTION
        "Differential Group Delay Low" 
    ::=  { intervalPhysPerfDiffGrDelay15minEntry 2 }

intervalPhysPerfDiffGrDelay15minMean OBJECT-TYPE
    SYNTAX      Integer32 
    UNITS       "ps"
    MAX-ACCESS  read-only
    STATUS      current
    DESCRIPTION
        "Differential Group Delay Mean" 
    ::=  { intervalPhysPerfDiffGrDelay15minEntry 3 }

intervalPhysPerfDiffGrDelay15minHigh OBJECT-TYPE
    SYNTAX      Integer32 
    UNITS       "ps"
    MAX-ACCESS  read-only
    STATUS      current
    DESCRIPTION
        "Differential Group Delay High" 
    ::=  { intervalPhysPerfDiffGrDelay15minEntry 4 }

intervalPhysPerfDiffGrDelay15minValidFlag OBJECT-TYPE
    SYNTAX      TruthValue
    MAX-ACCESS  read-only
    STATUS      current
    DESCRIPTION
        "Valid Flag" 
    ::=  { intervalPhysPerfDiffGrDelay15minEntry 5 }

intervalPhysPerfDiffGrDelay15minTimeStamp OBJECT-TYPE
    SYNTAX      DateAndTime
    MAX-ACCESS  read-only
    STATUS      current
    DESCRIPTION
        "Timestamp" 
    ::=  { intervalPhysPerfDiffGrDelay15minEntry 6 }

intervalPhysPerfDiffGrDelay1dayTable OBJECT-TYPE
    SYNTAX      SEQUENCE OF IntervalPhysPerfDiffGrDelay1dayEntry
    MAX-ACCESS  not-accessible
    STATUS      current
    DESCRIPTION   ""
    ::=  { performanceMonitoring 166 }

intervalPhysPerfDiffGrDelay1dayEntry OBJECT-TYPE
    SYNTAX      IntervalPhysPerfDiffGrDelay1dayEntry
    MAX-ACCESS  not-accessible
    STATUS      current
    DESCRIPTION   ""
    INDEX       {
                  entityIndex,
                  intervalPhysPerfDiffGrDelay1dayNumber
                }
    ::=  { intervalPhysPerfDiffGrDelay1dayTable 1 }

IntervalPhysPerfDiffGrDelay1dayEntry ::=  SEQUENCE
  { intervalPhysPerfDiffGrDelay1dayNumber Integer32,
    intervalPhysPerfDiffGrDelay1dayLow Integer32,
    intervalPhysPerfDiffGrDelay1dayMean Integer32,
    intervalPhysPerfDiffGrDelay1dayHigh Integer32,
    intervalPhysPerfDiffGrDelay1dayValidFlag TruthValue,
    intervalPhysPerfDiffGrDelay1dayTimeStamp DateAndTime }

intervalPhysPerfDiffGrDelay1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfDiffGrDelay1dayEntry 1 }

intervalPhysPerfDiffGrDelay1dayLow OBJECT-TYPE
    SYNTAX      Integer32 
    UNITS       "ps"
    MAX-ACCESS  read-only
    STATUS      current
    DESCRIPTION
        "Differential Group Delay Low" 
    ::=  { intervalPhysPerfDiffGrDelay1dayEntry 2 }

intervalPhysPerfDiffGrDelay1dayMean OBJECT-TYPE
    SYNTAX      Integer32 
    UNITS       "ps"
    MAX-ACCESS  read-only
    STATUS      current
    DESCRIPTION
        "Differential Group Delay Mean" 
    ::=  { intervalPhysPerfDiffGrDelay1dayEntry 3 }

intervalPhysPerfDiffGrDelay1dayHigh OBJECT-TYPE
    SYNTAX      Integer32 
    UNITS       "ps"
    MAX-ACCESS  read-only
    STATUS      current
    DESCRIPTION
        "Differential Group Delay High" 
    ::=  { intervalPhysPerfDiffGrDelay1dayEntry 4 }

intervalPhysPerfDiffGrDelay1dayValidFlag OBJECT-TYPE
    SYNTAX      TruthValue
    MAX-ACCESS  read-only
    STATUS      current
    DESCRIPTION
        "Valid Flag" 
    ::=  { intervalPhysPerfDiffGrDelay1dayEntry 5 }

intervalPhysPerfDiffGrDelay1dayTimeStamp OBJECT-TYPE
    SYNTAX      DateAndTime
    MAX-ACCESS  read-only
    STATUS      current
    DESCRIPTION
        "Timestamp" 
    ::=  { intervalPhysPerfDiffGrDelay1dayEntry 6 }

intervalPhysPerfDiffGrDelay1weekTable OBJECT-TYPE
    SYNTAX      SEQUENCE OF IntervalPhysPerfDiffGrDelay1weekEntry
    MAX-ACCESS  not-accessible
    STATUS      current
    DESCRIPTION   ""
    ::=  { performanceMonitoring 167 }

intervalPhysPerfDiffGrDelay1weekEntry OBJECT-TYPE
    SYNTAX      IntervalPhysPerfDiffGrDelay1weekEntry
    MAX-ACCESS  not-accessible
    STATUS      current
    DESCRIPTION   ""
    INDEX       {
                  entityIndex,
                  intervalPhysPerfDiffGrDelay1weekNumber
                }
    ::=  { intervalPhysPerfDiffGrDelay1weekTable 1 }

IntervalPhysPerfDiffGrDelay1weekEntry ::=  SEQUENCE
  { intervalPhysPerfDiffGrDelay1weekNumber Integer32,
    intervalPhysPerfDiffGrDelay1weekLow Integer32,
    intervalPhysPerfDiffGrDelay1weekMean Integer32,
    intervalPhysPerfDiffGrDelay1weekHigh Integer32,
    intervalPhysPerfDiffGrDelay1weekValidFlag TruthValue,
    intervalPhysPerfDiffGrDelay1weekTimeStamp DateAndTime }

intervalPhysPerfDiffGrDelay1weekNumber OBJECT-TYPE
    SYNTAX      Integer32 (1..52)
    MAX-ACCESS  not-accessible
    STATUS      current
    DESCRIPTION
        "Number 1week" 
    ::=  { intervalPhysPerfDiffGrDelay1weekEntry 1 }

intervalPhysPerfDiffGrDelay1weekLow OBJECT-TYPE
    SYNTAX      Integer32 
    UNITS       "ps"
    MAX-ACCESS  read-only
    STATUS      current
    DESCRIPTION
        "Differential Group Delay Low" 
    ::=  { intervalPhysPerfDiffGrDelay1weekEntry 2 }

intervalPhysPerfDiffGrDelay1weekMean OBJECT-TYPE
    SYNTAX      Integer32 
    UNITS       "ps"
    MAX-ACCESS  read-only
    STATUS      current
    DESCRIPTION
        "Differential Group Delay Mean" 
    ::=  { intervalPhysPerfDiffGrDelay1weekEntry 3 }

intervalPhysPerfDiffGrDelay1weekHigh OBJECT-TYPE
    SYNTAX      Integer32 
    UNITS       "ps"
    MAX-ACCESS  read-only
    STATUS      current
    DESCRIPTION
        "Differential Group Delay High" 
    ::=  { intervalPhysPerfDiffGrDelay1weekEntry 4 }

intervalPhysPerfDiffGrDelay1weekValidFlag OBJECT-TYPE
    SYNTAX      TruthValue
    MAX-ACCESS  read-only
    STATUS      current
    DESCRIPTION
        "Valid Flag" 
    ::=  { intervalPhysPerfDiffGrDelay1weekEntry 5 }

intervalPhysPerfDiffGrDelay1weekTimeStamp OBJECT-TYPE
    SYNTAX      DateAndTime
    MAX-ACCESS  read-only
    STATUS      current
    DESCRIPTION
        "Timestamp" 
    ::=  { intervalPhysPerfDiffGrDelay1weekEntry 6 }

intervalPhysPerfChromaticDispersion15minTable OBJECT-TYPE
    SYNTAX      SEQUENCE OF IntervalPhysPerfChromaticDispersion15minEntry
    MAX-ACCESS  not-accessible
    STATUS      current
    DESCRIPTION   ""
    ::=  { performanceMonitoring 168 }

intervalPhysPerfChromaticDispersion15minEntry OBJECT-TYPE
    SYNTAX      IntervalPhysPerfChromaticDispersion15minEntry
    MAX-ACCESS  not-accessible
    STATUS      current
    DESCRIPTION   ""
    INDEX       {
                  entityIndex,
                  intervalPhysPerfChromaticDispersion15minNumber
                }
    ::=  { intervalPhysPerfChromaticDispersion15minTable 1 }

IntervalPhysPerfChromaticDispersion15minEntry ::=  SEQUENCE
  { intervalPhysPerfChromaticDispersion15minNumber Integer32,
    intervalPhysPerfChromaticDispersion15minLow Integer32,
    intervalPhysPerfChromaticDispersion15minMean Integer32,
    intervalPhysPerfChromaticDispersion15minHigh Integer32,
    intervalPhysPerfChromaticDispersion15minValidFlag TruthValue,
    intervalPhysPerfChromaticDispersion15minTimeStamp DateAndTime }

intervalPhysPerfChromaticDispersion15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfChromaticDispersion15minEntry 1 }

intervalPhysPerfChromaticDispersion15minLow OBJECT-TYPE
    SYNTAX      Integer32 
    UNITS       "ps/nm"
    MAX-ACCESS  read-only
    STATUS      current
    DESCRIPTION
        "Chromatic Dispersion Compensation Low" 
    ::=  { intervalPhysPerfChromaticDispersion15minEntry 2 }

intervalPhysPerfChromaticDispersion15minMean OBJECT-TYPE
    SYNTAX      Integer32 
    UNITS       "ps/nm"
    MAX-ACCESS  read-only
    STATUS      current
    DESCRIPTION
        "Chromatic Dispersion Compensation Mean" 
    ::=  { intervalPhysPerfChromaticDispersion15minEntry 3 }

intervalPhysPerfChromaticDispersion15minHigh OBJECT-TYPE
    SYNTAX      Integer32 
    UNITS       "ps/nm"
    MAX-ACCESS  read-only
    STATUS      current
    DESCRIPTION
        "Chromatic Dispersion Compensation High" 
    ::=  { intervalPhysPerfChromaticDispersion15minEntry 4 }

intervalPhysPerfChromaticDispersion15minValidFlag OBJECT-TYPE
    SYNTAX      TruthValue
    MAX-ACCESS  read-only
    STATUS      current
    DESCRIPTION
        "Valid Flag" 
    ::=  { intervalPhysPerfChromaticDispersion15minEntry 5 }

intervalPhysPerfChromaticDispersion15minTimeStamp OBJECT-TYPE
    SYNTAX      DateAndTime
    MAX-ACCESS  read-only
    STATUS      current
    DESCRIPTION
        "Timestamp" 
    ::=  { intervalPhysPerfChromaticDispersion15minEntry 6 }

intervalPhysPerfChromaticDispersion1dayTable OBJECT-TYPE
    SYNTAX      SEQUENCE OF IntervalPhysPerfChromaticDispersion1dayEntry
    MAX-ACCESS  not-accessible
    STATUS      current
    DESCRIPTION   ""
    ::=  { performanceMonitoring 169 }

intervalPhysPerfChromaticDispersion1dayEntry OBJECT-TYPE
    SYNTAX      IntervalPhysPerfChromaticDispersion1dayEntry
    MAX-ACCESS  not-accessible
    STATUS      current
    DESCRIPTION   ""
    INDEX       {
                  entityIndex,
                  intervalPhysPerfChromaticDispersion1dayNumber
                }
    ::=  { intervalPhysPerfChromaticDispersion1dayTable 1 }

IntervalPhysPerfChromaticDispersion1dayEntry ::=  SEQUENCE
  { intervalPhysPerfChromaticDispersion1dayNumber Integer32,
    intervalPhysPerfChromaticDispersion1dayLow Integer32,
    intervalPhysPerfChromaticDispersion1dayMean Integer32,
    intervalPhysPerfChromaticDispersion1dayHigh Integer32,
    intervalPhysPerfChromaticDispersion1dayValidFlag TruthValue,
    intervalPhysPerfChromaticDispersion1dayTimeStamp DateAndTime }

intervalPhysPerfChromaticDispersion1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfChromaticDispersion1dayEntry 1 }

intervalPhysPerfChromaticDispersion1dayLow OBJECT-TYPE
    SYNTAX      Integer32 
    UNITS       "ps/nm"
    MAX-ACCESS  read-only
    STATUS      current
    DESCRIPTION
        "Chromatic Dispersion Compensation Low" 
    ::=  { intervalPhysPerfChromaticDispersion1dayEntry 2 }

intervalPhysPerfChromaticDispersion1dayMean OBJECT-TYPE
    SYNTAX      Integer32 
    UNITS       "ps/nm"
    MAX-ACCESS  read-only
    STATUS      current
    DESCRIPTION
        "Chromatic Dispersion Compensation Mean" 
    ::=  { intervalPhysPerfChromaticDispersion1dayEntry 3 }

intervalPhysPerfChromaticDispersion1dayHigh OBJECT-TYPE
    SYNTAX      Integer32 
    UNITS       "ps/nm"
    MAX-ACCESS  read-only
    STATUS      current
    DESCRIPTION
        "Chromatic Dispersion Compensation High" 
    ::=  { intervalPhysPerfChromaticDispersion1dayEntry 4 }

intervalPhysPerfChromaticDispersion1dayValidFlag OBJECT-TYPE
    SYNTAX      TruthValue
    MAX-ACCESS  read-only
    STATUS      current
    DESCRIPTION
        "Valid Flag" 
    ::=  { intervalPhysPerfChromaticDispersion1dayEntry 5 }

intervalPhysPerfChromaticDispersion1dayTimeStamp OBJECT-TYPE
    SYNTAX      DateAndTime
    MAX-ACCESS  read-only
    STATUS      current
    DESCRIPTION
        "Timestamp" 
    ::=  { intervalPhysPerfChromaticDispersion1dayEntry 6 }

intervalPhysPerfChromaticDispersion1weekTable OBJECT-TYPE
    SYNTAX      SEQUENCE OF IntervalPhysPerfChromaticDispersion1weekEntry
    MAX-ACCESS  not-accessible
    STATUS      current
    DESCRIPTION   ""
    ::=  { performanceMonitoring 170 }

intervalPhysPerfChromaticDispersion1weekEntry OBJECT-TYPE
    SYNTAX      IntervalPhysPerfChromaticDispersion1weekEntry
    MAX-ACCESS  not-accessible
    STATUS      current
    DESCRIPTION   ""
    INDEX       {
                  entityIndex,
                  intervalPhysPerfChromaticDispersion1weekNumber
                }
    ::=  { intervalPhysPerfChromaticDispersion1weekTable 1 }

IntervalPhysPerfChromaticDispersion1weekEntry ::=  SEQUENCE
  { intervalPhysPerfChromaticDispersion1weekNumber Integer32,
    intervalPhysPerfChromaticDispersion1weekLow Integer32,
    intervalPhysPerfChromaticDispersion1weekMean Integer32,
    intervalPhysPerfChromaticDispersion1weekHigh Integer32,
    intervalPhysPerfChromaticDispersion1weekValidFlag TruthValue,
    intervalPhysPerfChromaticDispersion1weekTimeStamp DateAndTime }

intervalPhysPerfChromaticDispersion1weekNumber OBJECT-TYPE
    SYNTAX      Integer32 (1..52)
    MAX-ACCESS  not-accessible
    STATUS      current
    DESCRIPTION
        "Number 1week" 
    ::=  { intervalPhysPerfChromaticDispersion1weekEntry 1 }

intervalPhysPerfChromaticDispersion1weekLow OBJECT-TYPE
    SYNTAX      Integer32 
    UNITS       "ps/nm"
    MAX-ACCESS  read-only
    STATUS      current
    DESCRIPTION
        "Chromatic Dispersion Compensation Low" 
    ::=  { intervalPhysPerfChromaticDispersion1weekEntry 2 }

intervalPhysPerfChromaticDispersion1weekMean OBJECT-TYPE
    SYNTAX      Integer32 
    UNITS       "ps/nm"
    MAX-ACCESS  read-only
    STATUS      current
    DESCRIPTION
        "Chromatic Dispersion Compensation Mean" 
    ::=  { intervalPhysPerfChromaticDispersion1weekEntry 3 }

intervalPhysPerfChromaticDispersion1weekHigh OBJECT-TYPE
    SYNTAX      Integer32 
    UNITS       "ps/nm"
    MAX-ACCESS  read-only
    STATUS      current
    DESCRIPTION
        "Chromatic Dispersion Compensation High" 
    ::=  { intervalPhysPerfChromaticDispersion1weekEntry 4 }

intervalPhysPerfChromaticDispersion1weekValidFlag OBJECT-TYPE
    SYNTAX      TruthValue
    MAX-ACCESS  read-only
    STATUS      current
    DESCRIPTION
        "Valid Flag" 
    ::=  { intervalPhysPerfChromaticDispersion1weekEntry 5 }

intervalPhysPerfChromaticDispersion1weekTimeStamp OBJECT-TYPE
    SYNTAX      DateAndTime
    MAX-ACCESS  read-only
    STATUS      current
    DESCRIPTION
        "Timestamp" 
    ::=  { intervalPhysPerfChromaticDispersion1weekEntry 6 }

intervalPhysPerfSignalToNoiseRatio15minTable OBJECT-TYPE
    SYNTAX      SEQUENCE OF IntervalPhysPerfSignalToNoiseRatio15minEntry
    MAX-ACCESS  not-accessible
    STATUS      current
    DESCRIPTION   ""
    ::=  { performanceMonitoring 171 }

intervalPhysPerfSignalToNoiseRatio15minEntry OBJECT-TYPE
    SYNTAX      IntervalPhysPerfSignalToNoiseRatio15minEntry
    MAX-ACCESS  not-accessible
    STATUS      current
    DESCRIPTION   ""
    INDEX       {
                  entityIndex,
                  intervalPhysPerfSignalToNoiseRatio15minNumber
                }
    ::=  { intervalPhysPerfSignalToNoiseRatio15minTable 1 }

IntervalPhysPerfSignalToNoiseRatio15minEntry ::=  SEQUENCE
  { intervalPhysPerfSignalToNoiseRatio15minNumber Integer32,
    intervalPhysPerfSignalToNoiseRatio15minLow Integer32,
    intervalPhysPerfSignalToNoiseRatio15minMean Integer32,
    intervalPhysPerfSignalToNoiseRatio15minHigh Integer32,
    intervalPhysPerfSignalToNoiseRatio15minValidFlag TruthValue,
    intervalPhysPerfSignalToNoiseRatio15minTimeStamp DateAndTime }

intervalPhysPerfSignalToNoiseRatio15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfSignalToNoiseRatio15minEntry 1 }

intervalPhysPerfSignalToNoiseRatio15minLow OBJECT-TYPE
    SYNTAX      Integer32 
    UNITS       "0.1 dB"
    MAX-ACCESS  read-only
    STATUS      current
    DESCRIPTION
        "Signal-to-Noise Ratio Low" 
    ::=  { intervalPhysPerfSignalToNoiseRatio15minEntry 2 }

intervalPhysPerfSignalToNoiseRatio15minMean OBJECT-TYPE
    SYNTAX      Integer32 
    UNITS       "0.1 dB"
    MAX-ACCESS  read-only
    STATUS      current
    DESCRIPTION
        "Signal-to-Noise Ratio Mean" 
    ::=  { intervalPhysPerfSignalToNoiseRatio15minEntry 3 }

intervalPhysPerfSignalToNoiseRatio15minHigh OBJECT-TYPE
    SYNTAX      Integer32 
    UNITS       "0.1 dB"
    MAX-ACCESS  read-only
    STATUS      current
    DESCRIPTION
        "Signal-to-Noise Ratio High" 
    ::=  { intervalPhysPerfSignalToNoiseRatio15minEntry 4 }

intervalPhysPerfSignalToNoiseRatio15minValidFlag OBJECT-TYPE
    SYNTAX      TruthValue
    MAX-ACCESS  read-only
    STATUS      current
    DESCRIPTION
        "Valid Flag" 
    ::=  { intervalPhysPerfSignalToNoiseRatio15minEntry 5 }

intervalPhysPerfSignalToNoiseRatio15minTimeStamp OBJECT-TYPE
    SYNTAX      DateAndTime
    MAX-ACCESS  read-only
    STATUS      current
    DESCRIPTION
        "Timestamp" 
    ::=  { intervalPhysPerfSignalToNoiseRatio15minEntry 6 }

intervalPhysPerfSignalToNoiseRatio1dayTable OBJECT-TYPE
    SYNTAX      SEQUENCE OF IntervalPhysPerfSignalToNoiseRatio1dayEntry
    MAX-ACCESS  not-accessible
    STATUS      current
    DESCRIPTION   ""
    ::=  { performanceMonitoring 172 }

intervalPhysPerfSignalToNoiseRatio1dayEntry OBJECT-TYPE
    SYNTAX      IntervalPhysPerfSignalToNoiseRatio1dayEntry
    MAX-ACCESS  not-accessible
    STATUS      current
    DESCRIPTION   ""
    INDEX       {
                  entityIndex,
                  intervalPhysPerfSignalToNoiseRatio1dayNumber
                }
    ::=  { intervalPhysPerfSignalToNoiseRatio1dayTable 1 }

IntervalPhysPerfSignalToNoiseRatio1dayEntry ::=  SEQUENCE
  { intervalPhysPerfSignalToNoiseRatio1dayNumber Integer32,
    intervalPhysPerfSignalToNoiseRatio1dayLow Integer32,
    intervalPhysPerfSignalToNoiseRatio1dayMean Integer32,
    intervalPhysPerfSignalToNoiseRatio1dayHigh Integer32,
    intervalPhysPerfSignalToNoiseRatio1dayValidFlag TruthValue,
    intervalPhysPerfSignalToNoiseRatio1dayTimeStamp DateAndTime }

intervalPhysPerfSignalToNoiseRatio1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfSignalToNoiseRatio1dayEntry 1 }

intervalPhysPerfSignalToNoiseRatio1dayLow OBJECT-TYPE
    SYNTAX      Integer32 
    UNITS       "0.1 dB"
    MAX-ACCESS  read-only
    STATUS      current
    DESCRIPTION
        "Signal-to-Noise Ratio Low" 
    ::=  { intervalPhysPerfSignalToNoiseRatio1dayEntry 2 }

intervalPhysPerfSignalToNoiseRatio1dayMean OBJECT-TYPE
    SYNTAX      Integer32 
    UNITS       "0.1 dB"
    MAX-ACCESS  read-only
    STATUS      current
    DESCRIPTION
        "Signal-to-Noise Ratio Mean" 
    ::=  { intervalPhysPerfSignalToNoiseRatio1dayEntry 3 }

intervalPhysPerfSignalToNoiseRatio1dayHigh OBJECT-TYPE
    SYNTAX      Integer32 
    UNITS       "0.1 dB"
    MAX-ACCESS  read-only
    STATUS      current
    DESCRIPTION
        "Signal-to-Noise Ratio High" 
    ::=  { intervalPhysPerfSignalToNoiseRatio1dayEntry 4 }

intervalPhysPerfSignalToNoiseRatio1dayValidFlag OBJECT-TYPE
    SYNTAX      TruthValue
    MAX-ACCESS  read-only
    STATUS      current
    DESCRIPTION
        "Valid Flag" 
    ::=  { intervalPhysPerfSignalToNoiseRatio1dayEntry 5 }

intervalPhysPerfSignalToNoiseRatio1dayTimeStamp OBJECT-TYPE
    SYNTAX      DateAndTime
    MAX-ACCESS  read-only
    STATUS      current
    DESCRIPTION
        "Timestamp" 
    ::=  { intervalPhysPerfSignalToNoiseRatio1dayEntry 6 }

intervalPhysPerfSignalToNoiseRatio1weekTable OBJECT-TYPE
    SYNTAX      SEQUENCE OF IntervalPhysPerfSignalToNoiseRatio1weekEntry
    MAX-ACCESS  not-accessible
    STATUS      current
    DESCRIPTION   ""
    ::=  { performanceMonitoring 173 }

intervalPhysPerfSignalToNoiseRatio1weekEntry OBJECT-TYPE
    SYNTAX      IntervalPhysPerfSignalToNoiseRatio1weekEntry
    MAX-ACCESS  not-accessible
    STATUS      current
    DESCRIPTION   ""
    INDEX       {
                  entityIndex,
                  intervalPhysPerfSignalToNoiseRatio1weekNumber
                }
    ::=  { intervalPhysPerfSignalToNoiseRatio1weekTable 1 }

IntervalPhysPerfSignalToNoiseRatio1weekEntry ::=  SEQUENCE
  { intervalPhysPerfSignalToNoiseRatio1weekNumber Integer32,
    intervalPhysPerfSignalToNoiseRatio1weekLow Integer32,
    intervalPhysPerfSignalToNoiseRatio1weekMean Integer32,
    intervalPhysPerfSignalToNoiseRatio1weekHigh Integer32,
    intervalPhysPerfSignalToNoiseRatio1weekValidFlag TruthValue,
    intervalPhysPerfSignalToNoiseRatio1weekTimeStamp DateAndTime }

intervalPhysPerfSignalToNoiseRatio1weekNumber OBJECT-TYPE
    SYNTAX      Integer32 (1..52)
    MAX-ACCESS  not-accessible
    STATUS      current
    DESCRIPTION
        "Number 1week" 
    ::=  { intervalPhysPerfSignalToNoiseRatio1weekEntry 1 }

intervalPhysPerfSignalToNoiseRatio1weekLow OBJECT-TYPE
    SYNTAX      Integer32 
    UNITS       "0.1 dB"
    MAX-ACCESS  read-only
    STATUS      current
    DESCRIPTION
        "Signal-to-Noise Ratio Low" 
    ::=  { intervalPhysPerfSignalToNoiseRatio1weekEntry 2 }

intervalPhysPerfSignalToNoiseRatio1weekMean OBJECT-TYPE
    SYNTAX      Integer32 
    UNITS       "0.1 dB"
    MAX-ACCESS  read-only
    STATUS      current
    DESCRIPTION
        "Signal-to-Noise Ratio Mean" 
    ::=  { intervalPhysPerfSignalToNoiseRatio1weekEntry 3 }

intervalPhysPerfSignalToNoiseRatio1weekHigh OBJECT-TYPE
    SYNTAX      Integer32 
    UNITS       "0.1 dB"
    MAX-ACCESS  read-only
    STATUS      current
    DESCRIPTION
        "Signal-to-Noise Ratio High" 
    ::=  { intervalPhysPerfSignalToNoiseRatio1weekEntry 4 }

intervalPhysPerfSignalToNoiseRatio1weekValidFlag OBJECT-TYPE
    SYNTAX      TruthValue
    MAX-ACCESS  read-only
    STATUS      current
    DESCRIPTION
        "Valid Flag" 
    ::=  { intervalPhysPerfSignalToNoiseRatio1weekEntry 5 }

intervalPhysPerfSignalToNoiseRatio1weekTimeStamp OBJECT-TYPE
    SYNTAX      DateAndTime
    MAX-ACCESS  read-only
    STATUS      current
    DESCRIPTION
        "Timestamp" 
    ::=  { intervalPhysPerfSignalToNoiseRatio1weekEntry 6 }

intervalPhysPerfCarrierFreqOffset15minTable OBJECT-TYPE
    SYNTAX      SEQUENCE OF IntervalPhysPerfCarrierFreqOffset15minEntry
    MAX-ACCESS  not-accessible
    STATUS      current
    DESCRIPTION   ""
    ::=  { performanceMonitoring 174 }

intervalPhysPerfCarrierFreqOffset15minEntry OBJECT-TYPE
    SYNTAX      IntervalPhysPerfCarrierFreqOffset15minEntry
    MAX-ACCESS  not-accessible
    STATUS      current
    DESCRIPTION   ""
    INDEX       {
                  entityIndex,
                  intervalPhysPerfCarrierFreqOffset15minNumber
                }
    ::=  { intervalPhysPerfCarrierFreqOffset15minTable 1 }

IntervalPhysPerfCarrierFreqOffset15minEntry ::=  SEQUENCE
  { intervalPhysPerfCarrierFreqOffset15minNumber Integer32,
    intervalPhysPerfCarrierFreqOffset15minLow Integer32,
    intervalPhysPerfCarrierFreqOffset15minMean Integer32,
    intervalPhysPerfCarrierFreqOffset15minHigh Integer32,
    intervalPhysPerfCarrierFreqOffset15minValidFlag TruthValue,
    intervalPhysPerfCarrierFreqOffset15minTimeStamp DateAndTime }

intervalPhysPerfCarrierFreqOffset15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfCarrierFreqOffset15minEntry 1 }

intervalPhysPerfCarrierFreqOffset15minLow OBJECT-TYPE
    SYNTAX      Integer32 
    UNITS       "0.001 GHz"
    MAX-ACCESS  read-only
    STATUS      current
    DESCRIPTION
        "Carrier Frequency Offset Low" 
    ::=  { intervalPhysPerfCarrierFreqOffset15minEntry 2 }

intervalPhysPerfCarrierFreqOffset15minMean OBJECT-TYPE
    SYNTAX      Integer32 
    UNITS       "0.001 GHz"
    MAX-ACCESS  read-only
    STATUS      current
    DESCRIPTION
        "Carrier Frequency Offset Mean" 
    ::=  { intervalPhysPerfCarrierFreqOffset15minEntry 3 }

intervalPhysPerfCarrierFreqOffset15minHigh OBJECT-TYPE
    SYNTAX      Integer32 
    UNITS       "0.001 GHz"
    MAX-ACCESS  read-only
    STATUS      current
    DESCRIPTION
        "Carrier Frequency Offset High" 
    ::=  { intervalPhysPerfCarrierFreqOffset15minEntry 4 }

intervalPhysPerfCarrierFreqOffset15minValidFlag OBJECT-TYPE
    SYNTAX      TruthValue
    MAX-ACCESS  read-only
    STATUS      current
    DESCRIPTION
        "Valid Flag" 
    ::=  { intervalPhysPerfCarrierFreqOffset15minEntry 5 }

intervalPhysPerfCarrierFreqOffset15minTimeStamp OBJECT-TYPE
    SYNTAX      DateAndTime
    MAX-ACCESS  read-only
    STATUS      current
    DESCRIPTION
        "Timestamp" 
    ::=  { intervalPhysPerfCarrierFreqOffset15minEntry 6 }

intervalPhysPerfCarrierFreqOffset1dayTable OBJECT-TYPE
    SYNTAX      SEQUENCE OF IntervalPhysPerfCarrierFreqOffset1dayEntry
    MAX-ACCESS  not-accessible
    STATUS      current
    DESCRIPTION   ""
    ::=  { performanceMonitoring 175 }

intervalPhysPerfCarrierFreqOffset1dayEntry OBJECT-TYPE
    SYNTAX      IntervalPhysPerfCarrierFreqOffset1dayEntry
    MAX-ACCESS  not-accessible
    STATUS      current
    DESCRIPTION   ""
    INDEX       {
                  entityIndex,
                  intervalPhysPerfCarrierFreqOffset1dayNumber
                }
    ::=  { intervalPhysPerfCarrierFreqOffset1dayTable 1 }

IntervalPhysPerfCarrierFreqOffset1dayEntry ::=  SEQUENCE
  { intervalPhysPerfCarrierFreqOffset1dayNumber Integer32,
    intervalPhysPerfCarrierFreqOffset1dayLow Integer32,
    intervalPhysPerfCarrierFreqOffset1dayMean Integer32,
    intervalPhysPerfCarrierFreqOffset1dayHigh Integer32,
    intervalPhysPerfCarrierFreqOffset1dayValidFlag TruthValue,
    intervalPhysPerfCarrierFreqOffset1dayTimeStamp DateAndTime }

intervalPhysPerfCarrierFreqOffset1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfCarrierFreqOffset1dayEntry 1 }

intervalPhysPerfCarrierFreqOffset1dayLow OBJECT-TYPE
    SYNTAX      Integer32 
    UNITS       "0.001 GHz"
    MAX-ACCESS  read-only
    STATUS      current
    DESCRIPTION
        "Carrier Frequency Offset Low" 
    ::=  { intervalPhysPerfCarrierFreqOffset1dayEntry 2 }

intervalPhysPerfCarrierFreqOffset1dayMean OBJECT-TYPE
    SYNTAX      Integer32 
    UNITS       "0.001 GHz"
    MAX-ACCESS  read-only
    STATUS      current
    DESCRIPTION
        "Carrier Frequency Offset Mean" 
    ::=  { intervalPhysPerfCarrierFreqOffset1dayEntry 3 }

intervalPhysPerfCarrierFreqOffset1dayHigh OBJECT-TYPE
    SYNTAX      Integer32 
    UNITS       "0.001 GHz"
    MAX-ACCESS  read-only
    STATUS      current
    DESCRIPTION
        "Carrier Frequency Offset High" 
    ::=  { intervalPhysPerfCarrierFreqOffset1dayEntry 4 }

intervalPhysPerfCarrierFreqOffset1dayValidFlag OBJECT-TYPE
    SYNTAX      TruthValue
    MAX-ACCESS  read-only
    STATUS      current
    DESCRIPTION
        "Valid Flag" 
    ::=  { intervalPhysPerfCarrierFreqOffset1dayEntry 5 }

intervalPhysPerfCarrierFreqOffset1dayTimeStamp OBJECT-TYPE
    SYNTAX      DateAndTime
    MAX-ACCESS  read-only
    STATUS      current
    DESCRIPTION
        "Timestamp" 
    ::=  { intervalPhysPerfCarrierFreqOffset1dayEntry 6 }

intervalPhysPerfCarrierFreqOffset1weekTable OBJECT-TYPE
    SYNTAX      SEQUENCE OF IntervalPhysPerfCarrierFreqOffset1weekEntry
    MAX-ACCESS  not-accessible
    STATUS      current
    DESCRIPTION   ""
    ::=  { performanceMonitoring 176 }

intervalPhysPerfCarrierFreqOffset1weekEntry OBJECT-TYPE
    SYNTAX      IntervalPhysPerfCarrierFreqOffset1weekEntry
    MAX-ACCESS  not-accessible
    STATUS      current
    DESCRIPTION   ""
    INDEX       {
                  entityIndex,
                  intervalPhysPerfCarrierFreqOffset1weekNumber
                }
    ::=  { intervalPhysPerfCarrierFreqOffset1weekTable 1 }

IntervalPhysPerfCarrierFreqOffset1weekEntry ::=  SEQUENCE
  { intervalPhysPerfCarrierFreqOffset1weekNumber Integer32,
    intervalPhysPerfCarrierFreqOffset1weekLow Integer32,
    intervalPhysPerfCarrierFreqOffset1weekMean Integer32,
    intervalPhysPerfCarrierFreqOffset1weekHigh Integer32,
    intervalPhysPerfCarrierFreqOffset1weekValidFlag TruthValue,
    intervalPhysPerfCarrierFreqOffset1weekTimeStamp DateAndTime }

intervalPhysPerfCarrierFreqOffset1weekNumber OBJECT-TYPE
    SYNTAX      Integer32 (1..52)
    MAX-ACCESS  not-accessible
    STATUS      current
    DESCRIPTION
        "Number 1week" 
    ::=  { intervalPhysPerfCarrierFreqOffset1weekEntry 1 }

intervalPhysPerfCarrierFreqOffset1weekLow OBJECT-TYPE
    SYNTAX      Integer32 
    UNITS       "0.001 GHz"
    MAX-ACCESS  read-only
    STATUS      current
    DESCRIPTION
        "Carrier Frequency Offset Low" 
    ::=  { intervalPhysPerfCarrierFreqOffset1weekEntry 2 }

intervalPhysPerfCarrierFreqOffset1weekMean OBJECT-TYPE
    SYNTAX      Integer32 
    UNITS       "0.001 GHz"
    MAX-ACCESS  read-only
    STATUS      current
    DESCRIPTION
        "Carrier Frequency Offset Mean" 
    ::=  { intervalPhysPerfCarrierFreqOffset1weekEntry 3 }

intervalPhysPerfCarrierFreqOffset1weekHigh OBJECT-TYPE
    SYNTAX      Integer32 
    UNITS       "0.001 GHz"
    MAX-ACCESS  read-only
    STATUS      current
    DESCRIPTION
        "Carrier Frequency Offset High" 
    ::=  { intervalPhysPerfCarrierFreqOffset1weekEntry 4 }

intervalPhysPerfCarrierFreqOffset1weekValidFlag OBJECT-TYPE
    SYNTAX      TruthValue
    MAX-ACCESS  read-only
    STATUS      current
    DESCRIPTION
        "Valid Flag" 
    ::=  { intervalPhysPerfCarrierFreqOffset1weekEntry 5 }

intervalPhysPerfCarrierFreqOffset1weekTimeStamp OBJECT-TYPE
    SYNTAX      DateAndTime
    MAX-ACCESS  read-only
    STATUS      current
    DESCRIPTION
        "Timestamp" 
    ::=  { intervalPhysPerfCarrierFreqOffset1weekEntry 6 }

thresholdOtuFecSublayerExTable OBJECT-TYPE
    SYNTAX      SEQUENCE OF ThresholdOtuFecSublayerExEntry
    MAX-ACCESS  not-accessible
    STATUS      current
    DESCRIPTION   ""
    ::=  { performanceMonitoring 177 }

thresholdOtuFecSublayerExEntry OBJECT-TYPE
    SYNTAX      ThresholdOtuFecSublayerExEntry
    MAX-ACCESS  not-accessible
    STATUS      current
    DESCRIPTION   ""
    INDEX       {
                  entityIndex
                }
    ::=  { thresholdOtuFecSublayerExTable 1 }

ThresholdOtuFecSublayerExEntry ::=  SEQUENCE
  { thresholdOtuFecSublayerExCEHighThres15min Counter64String,
    thresholdOtuFecSublayerExCEHighThres1day Counter64String,
    thresholdOtuFecSublayerExUBEHighThres15min Counter64String,
    thresholdOtuFecSublayerExUBEHighThres1day Counter64String }

thresholdOtuFecSublayerExCEHighThres15min OBJECT-TYPE
    SYNTAX      Counter64String
    MAX-ACCESS  read-write
    STATUS      current
    DESCRIPTION
        "FEC Corrected Errors 15 Minute Threshold" 
    ::=  { thresholdOtuFecSublayerExEntry 1 }

thresholdOtuFecSublayerExCEHighThres1day OBJECT-TYPE
    SYNTAX      Counter64String
    MAX-ACCESS  read-write
    STATUS      current
    DESCRIPTION
        "FEC Corrected Errors 1 Day Threshold" 
    ::=  { thresholdOtuFecSublayerExEntry 2 }

thresholdOtuFecSublayerExUBEHighThres15min OBJECT-TYPE
    SYNTAX      Counter64String
    MAX-ACCESS  read-write
    STATUS      current
    DESCRIPTION
        "Uncorrected Block Errors 15 Minute Threshold" 
    ::=  { thresholdOtuFecSublayerExEntry 3 }

thresholdOtuFecSublayerExUBEHighThres1day OBJECT-TYPE
    SYNTAX      Counter64String
    MAX-ACCESS  read-write
    STATUS      current
    DESCRIPTION
        "Uncorrected Block Errors 1 Day Threshold" 
    ::=  { thresholdOtuFecSublayerExEntry 4 }

currentOtuFec15minExTable OBJECT-TYPE
    SYNTAX      SEQUENCE OF CurrentOtuFec15minExEntry
    MAX-ACCESS  not-accessible
    STATUS      current
    DESCRIPTION   ""
    ::=  { performanceMonitoring 178 }

currentOtuFec15minExEntry OBJECT-TYPE
    SYNTAX      CurrentOtuFec15minExEntry
    MAX-ACCESS  not-accessible
    STATUS      current
    DESCRIPTION   ""
    INDEX       {
                  entityIndex
                }
    ::=  { currentOtuFec15minExTable 1 }

CurrentOtuFec15minExEntry ::=  SEQUENCE
  { currentOtuFec15minExCE Counter64String,
    currentOtuFec15minExUBE Counter64String,
    currentOtuFec15minExBERCE Counter64String,
    currentOtuFec15minExElapsedTime Integer32 }

currentOtuFec15minExCE OBJECT-TYPE
    SYNTAX      Counter64String
    MAX-ACCESS  read-only
    STATUS      current
    DESCRIPTION
        "OTU FEC Corrected Errors" 
    ::=  { currentOtuFec15minExEntry 1 }

currentOtuFec15minExUBE OBJECT-TYPE
    SYNTAX      Counter64String
    MAX-ACCESS  read-only
    STATUS      current
    DESCRIPTION
        "OTU FEC Uncorrected Block Errors" 
    ::=  { currentOtuFec15minExEntry 2 }

currentOtuFec15minExBERCE OBJECT-TYPE
    SYNTAX      Counter64String 
    UNITS       "1.0E-18"
    MAX-ACCESS  read-only
    STATUS      current
    DESCRIPTION
        "Bit Error Rate before Foward Error Correction (FEC) calculated from corrected errors" 
    ::=  { currentOtuFec15minExEntry 3 }

currentOtuFec15minExElapsedTime OBJECT-TYPE
    SYNTAX      Integer32 (0..9000 | -2147483648)
    MAX-ACCESS  read-only
    STATUS      current
    DESCRIPTION
        "Elapsed 15Min" 
    ::=  { currentOtuFec15minExEntry 4 }

currentOtuFec1dayExTable OBJECT-TYPE
    SYNTAX      SEQUENCE OF CurrentOtuFec1dayExEntry
    MAX-ACCESS  not-accessible
    STATUS      current
    DESCRIPTION   ""
    ::=  { performanceMonitoring 179 }

currentOtuFec1dayExEntry OBJECT-TYPE
    SYNTAX      CurrentOtuFec1dayExEntry
    MAX-ACCESS  not-accessible
    STATUS      current
    DESCRIPTION   ""
    INDEX       {
                  entityIndex
                }
    ::=  { currentOtuFec1dayExTable 1 }

CurrentOtuFec1dayExEntry ::=  SEQUENCE
  { currentOtuFec1dayExCE Counter64String,
    currentOtuFec1dayExUBE Counter64String,
    currentOtuFec1dayExBERCE Counter64String,
    currentOtuFec1dayExElapsedTime Integer32 }

currentOtuFec1dayExCE OBJECT-TYPE
    SYNTAX      Counter64String
    MAX-ACCESS  read-only
    STATUS      current
    DESCRIPTION
        "OTU FEC Corrected Errors" 
    ::=  { currentOtuFec1dayExEntry 1 }

currentOtuFec1dayExUBE OBJECT-TYPE
    SYNTAX      Counter64String
    MAX-ACCESS  read-only
    STATUS      current
    DESCRIPTION
        "OTU FEC Uncorrected Block Errors" 
    ::=  { currentOtuFec1dayExEntry 2 }

currentOtuFec1dayExBERCE OBJECT-TYPE
    SYNTAX      Counter64String 
    UNITS       "1.0E-18"
    MAX-ACCESS  read-only
    STATUS      current
    DESCRIPTION
        "Bit Error Rate before Foward Error Correction (FEC) calculated from corrected errors" 
    ::=  { currentOtuFec1dayExEntry 3 }

currentOtuFec1dayExElapsedTime OBJECT-TYPE
    SYNTAX      Integer32 (0..86400 | -2147483648)
    MAX-ACCESS  read-only
    STATUS      current
    DESCRIPTION
        "Elapsed 1Day" 
    ::=  { currentOtuFec1dayExEntry 4 }

intervalOtuFec15minExTable OBJECT-TYPE
    SYNTAX      SEQUENCE OF IntervalOtuFec15minExEntry
    MAX-ACCESS  not-accessible
    STATUS      current
    DESCRIPTION   ""
    ::=  { performanceMonitoring 180 }

intervalOtuFec15minExEntry OBJECT-TYPE
    SYNTAX      IntervalOtuFec15minExEntry
    MAX-ACCESS  not-accessible
    STATUS      current
    DESCRIPTION   ""
    INDEX       {
                  entityIndex,
                  intervalOtuFec15minExNumber
                }
    ::=  { intervalOtuFec15minExTable 1 }

IntervalOtuFec15minExEntry ::=  SEQUENCE
  { intervalOtuFec15minExNumber Integer32,
    intervalOtuFec15minExCE Counter64String,
    intervalOtuFec15minExUBE Counter64String,
    intervalOtuFec15minExBERCE Counter64String,
    intervalOtuFec15minExValidFlag TruthValue,
    intervalOtuFec15minExTimeStamp DateAndTime }

intervalOtuFec15minExNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalOtuFec15minExEntry 1 }

intervalOtuFec15minExCE OBJECT-TYPE
    SYNTAX      Counter64String
    MAX-ACCESS  read-only
    STATUS      current
    DESCRIPTION
        "OTU FEC Corrected Errors" 
    ::=  { intervalOtuFec15minExEntry 2 }

intervalOtuFec15minExUBE OBJECT-TYPE
    SYNTAX      Counter64String
    MAX-ACCESS  read-only
    STATUS      current
    DESCRIPTION
        "OTU FEC Uncorrected Block Errors" 
    ::=  { intervalOtuFec15minExEntry 3 }

intervalOtuFec15minExBERCE OBJECT-TYPE
    SYNTAX      Counter64String 
    UNITS       "1.0E-18"
    MAX-ACCESS  read-only
    STATUS      current
    DESCRIPTION
        "Bit Error Rate before Foward Error Correction (FEC) calculated from corrected errors" 
    ::=  { intervalOtuFec15minExEntry 4 }

intervalOtuFec15minExValidFlag OBJECT-TYPE
    SYNTAX      TruthValue
    MAX-ACCESS  read-only
    STATUS      current
    DESCRIPTION
        "Valid Flag" 
    ::=  { intervalOtuFec15minExEntry 5 }

intervalOtuFec15minExTimeStamp OBJECT-TYPE
    SYNTAX      DateAndTime
    MAX-ACCESS  read-only
    STATUS      current
    DESCRIPTION
        "Timestamp" 
    ::=  { intervalOtuFec15minExEntry 6 }

intervalOtuFec1dayExTable OBJECT-TYPE
    SYNTAX      SEQUENCE OF IntervalOtuFec1dayExEntry
    MAX-ACCESS  not-accessible
    STATUS      current
    DESCRIPTION   ""
    ::=  { performanceMonitoring 181 }

intervalOtuFec1dayExEntry OBJECT-TYPE
    SYNTAX      IntervalOtuFec1dayExEntry
    MAX-ACCESS  not-accessible
    STATUS      current
    DESCRIPTION   ""
    INDEX       {
                  entityIndex,
                  intervalOtuFec1dayExNumber
                }
    ::=  { intervalOtuFec1dayExTable 1 }

IntervalOtuFec1dayExEntry ::=  SEQUENCE
  { intervalOtuFec1dayExNumber Integer32,
    intervalOtuFec1dayExCE Counter64String,
    intervalOtuFec1dayExUBE Counter64String,
    intervalOtuFec1dayExBERCE Counter64String,
    intervalOtuFec1dayExValidFlag TruthValue,
    intervalOtuFec1dayExTimeStamp DateAndTime }

intervalOtuFec1dayExNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalOtuFec1dayExEntry 1 }

intervalOtuFec1dayExCE OBJECT-TYPE
    SYNTAX      Counter64String
    MAX-ACCESS  read-only
    STATUS      current
    DESCRIPTION
        "OTU FEC Corrected Errors" 
    ::=  { intervalOtuFec1dayExEntry 2 }

intervalOtuFec1dayExUBE OBJECT-TYPE
    SYNTAX      Counter64String
    MAX-ACCESS  read-only
    STATUS      current
    DESCRIPTION
        "OTU FEC Uncorrected Block Errors" 
    ::=  { intervalOtuFec1dayExEntry 3 }

intervalOtuFec1dayExBERCE OBJECT-TYPE
    SYNTAX      Counter64String 
    UNITS       "1.0E-18"
    MAX-ACCESS  read-only
    STATUS      current
    DESCRIPTION
        "Bit Error Rate before Foward Error Correction (FEC) calculated from corrected errors" 
    ::=  { intervalOtuFec1dayExEntry 4 }

intervalOtuFec1dayExValidFlag OBJECT-TYPE
    SYNTAX      TruthValue
    MAX-ACCESS  read-only
    STATUS      current
    DESCRIPTION
        "Valid Flag" 
    ::=  { intervalOtuFec1dayExEntry 5 }

intervalOtuFec1dayExTimeStamp OBJECT-TYPE
    SYNTAX      DateAndTime
    MAX-ACCESS  read-only
    STATUS      current
    DESCRIPTION
        "Timestamp" 
    ::=  { intervalOtuFec1dayExEntry 6 }

currentEthRx3HS15minTable OBJECT-TYPE
    SYNTAX      SEQUENCE OF CurrentEthRx3HS15minEntry
    MAX-ACCESS  not-accessible
    STATUS      current
    DESCRIPTION   ""
    ::=  { performanceMonitoring 182 }

currentEthRx3HS15minEntry OBJECT-TYPE
    SYNTAX      CurrentEthRx3HS15minEntry
    MAX-ACCESS  not-accessible
    STATUS      current
    DESCRIPTION   ""
    INDEX       {
                  entityIndex
                }
    ::=  { currentEthRx3HS15minTable 1 }

CurrentEthRx3HS15minEntry ::=  SEQUENCE
  { currentEthRx3HS15minGoodFrames Counter64String,
    currentEthRx3HS15minPauseFrames Counter64String,
    currentEthRx3HS15minCrcFrames Counter64String,
    currentEthRx3HS15minBytes Counter64String,
    currentEthRx3HS15minBroadcastFramesRcv Counter64String,
    currentEthRx3HS15minMulticastFramesRcv Counter64String,
    currentEthRx3HS15minUndersizedFramesRcv Counter64String,
    currentEthRx3HS15minOversizedFramesRcv Counter64String,
    currentEthRx3HS15minFragmentFramesRcv Counter64String,
    currentEthRx3HS15minJabberFrameRcv Counter64String,
    currentEthRx3HS15minControlFrameRcv Counter64String,
    currentEthRx3HS15minBytesFrames64Rcv Counter64String,
    currentEthRx3HS15minBytesFrames65Rcv Counter64String,
    currentEthRx3HS15minBytesFrames128Rcv Counter64String,
    currentEthRx3HS15minBytesFrames256Rcv Counter64String,
    currentEthRx3HS15minBytesFrames512Rcv Counter64String,
    currentEthRx3HS15minBytesFrames1024Rcv Counter64String,
    currentEthRx3HS15minBytesFrames1519Rcv Counter64String,
    currentEthRx3HS15minElapsedTime Integer32 }

currentEthRx3HS15minGoodFrames OBJECT-TYPE
    SYNTAX      Counter64String
    MAX-ACCESS  read-only
    STATUS      current
    DESCRIPTION
        "Frames Received" 
    ::=  { currentEthRx3HS15minEntry 1 }

currentEthRx3HS15minPauseFrames OBJECT-TYPE
    SYNTAX      Counter64String
    MAX-ACCESS  read-only
    STATUS      current
    DESCRIPTION
        "Pause Frames Received" 
    ::=  { currentEthRx3HS15minEntry 2 }

currentEthRx3HS15minCrcFrames OBJECT-TYPE
    SYNTAX      Counter64String
    MAX-ACCESS  read-only
    STATUS      current
    DESCRIPTION
        "Received CRC Errors" 
    ::=  { currentEthRx3HS15minEntry 3 }

currentEthRx3HS15minBytes OBJECT-TYPE
    SYNTAX      Counter64String
    MAX-ACCESS  read-only
    STATUS      current
    DESCRIPTION
        "Bytes Received" 
    ::=  { currentEthRx3HS15minEntry 4 }

currentEthRx3HS15minBroadcastFramesRcv OBJECT-TYPE
    SYNTAX      Counter64String
    MAX-ACCESS  read-only
    STATUS      current
    DESCRIPTION
        "Broadcast Frames Received" 
    ::=  { currentEthRx3HS15minEntry 5 }

currentEthRx3HS15minMulticastFramesRcv OBJECT-TYPE
    SYNTAX      Counter64String
    MAX-ACCESS  read-only
    STATUS      current
    DESCRIPTION
        "Multicast Frames Received" 
    ::=  { currentEthRx3HS15minEntry 6 }

currentEthRx3HS15minUndersizedFramesRcv OBJECT-TYPE
    SYNTAX      Counter64String
    MAX-ACCESS  read-only
    STATUS      current
    DESCRIPTION
        "Undersized Frames Received" 
    ::=  { currentEthRx3HS15minEntry 7 }

currentEthRx3HS15minOversizedFramesRcv OBJECT-TYPE
    SYNTAX      Counter64String
    MAX-ACCESS  read-only
    STATUS      current
    DESCRIPTION
        "Oversized Frames Received" 
    ::=  { currentEthRx3HS15minEntry 8 }

currentEthRx3HS15minFragmentFramesRcv OBJECT-TYPE
    SYNTAX      Counter64String
    MAX-ACCESS  read-only
    STATUS      current
    DESCRIPTION
        "Fragment Frames Received" 
    ::=  { currentEthRx3HS15minEntry 9 }

currentEthRx3HS15minJabberFrameRcv OBJECT-TYPE
    SYNTAX      Counter64String
    MAX-ACCESS  read-only
    STATUS      current
    DESCRIPTION
        "Rx Jabber Frame" 
    ::=  { currentEthRx3HS15minEntry 10 }

currentEthRx3HS15minControlFrameRcv OBJECT-TYPE
    SYNTAX      Counter64String
    MAX-ACCESS  read-only
    STATUS      current
    DESCRIPTION
        "Control Frames Received" 
    ::=  { currentEthRx3HS15minEntry 11 }

currentEthRx3HS15minBytesFrames64Rcv OBJECT-TYPE
    SYNTAX      Counter64String
    MAX-ACCESS  read-only
    STATUS      current
    DESCRIPTION
        "64 Byte Frames Received" 
    ::=  { currentEthRx3HS15minEntry 12 }

currentEthRx3HS15minBytesFrames65Rcv OBJECT-TYPE
    SYNTAX      Counter64String
    MAX-ACCESS  read-only
    STATUS      current
    DESCRIPTION
        "65-127 Byte Frames Received" 
    ::=  { currentEthRx3HS15minEntry 13 }

currentEthRx3HS15minBytesFrames128Rcv OBJECT-TYPE
    SYNTAX      Counter64String
    MAX-ACCESS  read-only
    STATUS      current
    DESCRIPTION
        "128-255 Byte Frames Received" 
    ::=  { currentEthRx3HS15minEntry 14 }

currentEthRx3HS15minBytesFrames256Rcv OBJECT-TYPE
    SYNTAX      Counter64String
    MAX-ACCESS  read-only
    STATUS      current
    DESCRIPTION
        "256-511 Byte Frames Received" 
    ::=  { currentEthRx3HS15minEntry 15 }

currentEthRx3HS15minBytesFrames512Rcv OBJECT-TYPE
    SYNTAX      Counter64String
    MAX-ACCESS  read-only
    STATUS      current
    DESCRIPTION
        "512-1023 Byte Frames Received" 
    ::=  { currentEthRx3HS15minEntry 16 }

currentEthRx3HS15minBytesFrames1024Rcv OBJECT-TYPE
    SYNTAX      Counter64String
    MAX-ACCESS  read-only
    STATUS      current
    DESCRIPTION
        "1024-1518 Byte Frames Received" 
    ::=  { currentEthRx3HS15minEntry 17 }

currentEthRx3HS15minBytesFrames1519Rcv OBJECT-TYPE
    SYNTAX      Counter64String
    MAX-ACCESS  read-only
    STATUS      current
    DESCRIPTION
        "1519-Max Byte Frames Received" 
    ::=  { currentEthRx3HS15minEntry 18 }

currentEthRx3HS15minElapsedTime OBJECT-TYPE
    SYNTAX      Integer32 (0..9000 | -2147483648)
    MAX-ACCESS  read-only
    STATUS      current
    DESCRIPTION
        "Elapsed 15Min" 
    ::=  { currentEthRx3HS15minEntry 19 }

currentEthRx3HS1dayTable OBJECT-TYPE
    SYNTAX      SEQUENCE OF CurrentEthRx3HS1dayEntry
    MAX-ACCESS  not-accessible
    STATUS      current
    DESCRIPTION   ""
    ::=  { performanceMonitoring 183 }

currentEthRx3HS1dayEntry OBJECT-TYPE
    SYNTAX      CurrentEthRx3HS1dayEntry
    MAX-ACCESS  not-accessible
    STATUS      current
    DESCRIPTION   ""
    INDEX       {
                  entityIndex
                }
    ::=  { currentEthRx3HS1dayTable 1 }

CurrentEthRx3HS1dayEntry ::=  SEQUENCE
  { currentEthRx3HS1dayGoodFrames Counter64String,
    currentEthRx3HS1dayPauseFrames Counter64String,
    currentEthRx3HS1dayCrcFrames Counter64String,
    currentEthRx3HS1dayBytes Counter64String,
    currentEthRx3HS1dayBroadcastFramesRcv Counter64String,
    currentEthRx3HS1dayMulticastFramesRcv Counter64String,
    currentEthRx3HS1dayUndersizedFramesRcv Counter64String,
    currentEthRx3HS1dayOversizedFramesRcv Counter64String,
    currentEthRx3HS1dayFragmentFramesRcv Counter64String,
    currentEthRx3HS1dayJabberFrameRcv Counter64String,
    currentEthRx3HS1dayControlFrameRcv Counter64String,
    currentEthRx3HS1dayBytesFrames64Rcv Counter64String,
    currentEthRx3HS1dayBytesFrames65Rcv Counter64String,
    currentEthRx3HS1dayBytesFrames128Rcv Counter64String,
    currentEthRx3HS1dayBytesFrames256Rcv Counter64String,
    currentEthRx3HS1dayBytesFrames512Rcv Counter64String,
    currentEthRx3HS1dayBytesFrames1024Rcv Counter64String,
    currentEthRx3HS1dayBytesFrames1519Rcv Counter64String,
    currentEthRx3HS1dayElapsedTime Integer32 }

currentEthRx3HS1dayGoodFrames OBJECT-TYPE
    SYNTAX      Counter64String
    MAX-ACCESS  read-only
    STATUS      current
    DESCRIPTION
        "Frames Received" 
    ::=  { currentEthRx3HS1dayEntry 1 }

currentEthRx3HS1dayPauseFrames OBJECT-TYPE
    SYNTAX      Counter64String
    MAX-ACCESS  read-only
    STATUS      current
    DESCRIPTION
        "Pause Frames Received" 
    ::=  { currentEthRx3HS1dayEntry 2 }

currentEthRx3HS1dayCrcFrames OBJECT-TYPE
    SYNTAX      Counter64String
    MAX-ACCESS  read-only
    STATUS      current
    DESCRIPTION
        "Received CRC Errors" 
    ::=  { currentEthRx3HS1dayEntry 3 }

currentEthRx3HS1dayBytes OBJECT-TYPE
    SYNTAX      Counter64String
    MAX-ACCESS  read-only
    STATUS      current
    DESCRIPTION
        "Bytes Received" 
    ::=  { currentEthRx3HS1dayEntry 4 }

currentEthRx3HS1dayBroadcastFramesRcv OBJECT-TYPE
    SYNTAX      Counter64String
    MAX-ACCESS  read-only
    STATUS      current
    DESCRIPTION
        "Broadcast Frames Received" 
    ::=  { currentEthRx3HS1dayEntry 5 }

currentEthRx3HS1dayMulticastFramesRcv OBJECT-TYPE
    SYNTAX      Counter64String
    MAX-ACCESS  read-only
    STATUS      current
    DESCRIPTION
        "Multicast Frames Received" 
    ::=  { currentEthRx3HS1dayEntry 6 }

currentEthRx3HS1dayUndersizedFramesRcv OBJECT-TYPE
    SYNTAX      Counter64String
    MAX-ACCESS  read-only
    STATUS      current
    DESCRIPTION
        "Undersized Frames Received" 
    ::=  { currentEthRx3HS1dayEntry 7 }

currentEthRx3HS1dayOversizedFramesRcv OBJECT-TYPE
    SYNTAX      Counter64String
    MAX-ACCESS  read-only
    STATUS      current
    DESCRIPTION
        "Oversized Frames Received" 
    ::=  { currentEthRx3HS1dayEntry 8 }

currentEthRx3HS1dayFragmentFramesRcv OBJECT-TYPE
    SYNTAX      Counter64String
    MAX-ACCESS  read-only
    STATUS      current
    DESCRIPTION
        "Fragment Frames Received" 
    ::=  { currentEthRx3HS1dayEntry 9 }

currentEthRx3HS1dayJabberFrameRcv OBJECT-TYPE
    SYNTAX      Counter64String
    MAX-ACCESS  read-only
    STATUS      current
    DESCRIPTION
        "Rx Jabber Frame" 
    ::=  { currentEthRx3HS1dayEntry 10 }

currentEthRx3HS1dayControlFrameRcv OBJECT-TYPE
    SYNTAX      Counter64String
    MAX-ACCESS  read-only
    STATUS      current
    DESCRIPTION
        "Control Frames Received" 
    ::=  { currentEthRx3HS1dayEntry 11 }

currentEthRx3HS1dayBytesFrames64Rcv OBJECT-TYPE
    SYNTAX      Counter64String
    MAX-ACCESS  read-only
    STATUS      current
    DESCRIPTION
        "64 Byte Frames Received" 
    ::=  { currentEthRx3HS1dayEntry 12 }

currentEthRx3HS1dayBytesFrames65Rcv OBJECT-TYPE
    SYNTAX      Counter64String
    MAX-ACCESS  read-only
    STATUS      current
    DESCRIPTION
        "65-127 Byte Frames Received" 
    ::=  { currentEthRx3HS1dayEntry 13 }

currentEthRx3HS1dayBytesFrames128Rcv OBJECT-TYPE
    SYNTAX      Counter64String
    MAX-ACCESS  read-only
    STATUS      current
    DESCRIPTION
        "128-255 Byte Frames Received" 
    ::=  { currentEthRx3HS1dayEntry 14 }

currentEthRx3HS1dayBytesFrames256Rcv OBJECT-TYPE
    SYNTAX      Counter64String
    MAX-ACCESS  read-only
    STATUS      current
    DESCRIPTION
        "256-511 Byte Frames Received" 
    ::=  { currentEthRx3HS1dayEntry 15 }

currentEthRx3HS1dayBytesFrames512Rcv OBJECT-TYPE
    SYNTAX      Counter64String
    MAX-ACCESS  read-only
    STATUS      current
    DESCRIPTION
        "512-1023 Byte Frames Received" 
    ::=  { currentEthRx3HS1dayEntry 16 }

currentEthRx3HS1dayBytesFrames1024Rcv OBJECT-TYPE
    SYNTAX      Counter64String
    MAX-ACCESS  read-only
    STATUS      current
    DESCRIPTION
        "1024-1518 Byte Frames Received" 
    ::=  { currentEthRx3HS1dayEntry 17 }

currentEthRx3HS1dayBytesFrames1519Rcv OBJECT-TYPE
    SYNTAX      Counter64String
    MAX-ACCESS  read-only
    STATUS      current
    DESCRIPTION
        "1519-Max Byte Frames Received" 
    ::=  { currentEthRx3HS1dayEntry 18 }

currentEthRx3HS1dayElapsedTime OBJECT-TYPE
    SYNTAX      Integer32 (0..86400 | -2147483648)
    MAX-ACCESS  read-only
    STATUS      current
    DESCRIPTION
        "Elapsed 1Day" 
    ::=  { currentEthRx3HS1dayEntry 19 }

intervalEthRx3HS15minTable OBJECT-TYPE
    SYNTAX      SEQUENCE OF IntervalEthRx3HS15minEntry
    MAX-ACCESS  not-accessible
    STATUS      current
    DESCRIPTION   ""
    ::=  { performanceMonitoring 184 }

intervalEthRx3HS15minEntry OBJECT-TYPE
    SYNTAX      IntervalEthRx3HS15minEntry
    MAX-ACCESS  not-accessible
    STATUS      current
    DESCRIPTION   ""
    INDEX       {
                  entityIndex,
                  intervalEthRx3HS15minNumber
                }
    ::=  { intervalEthRx3HS15minTable 1 }

IntervalEthRx3HS15minEntry ::=  SEQUENCE
  { intervalEthRx3HS15minNumber Integer32,
    intervalEthRx3HS15minGoodFrames Counter64String,
    intervalEthRx3HS15minPauseFrames Counter64String,
    intervalEthRx3HS15minCrcFrames Counter64String,
    intervalEthRx3HS15minBytes Counter64String,
    intervalEthRx3HS15minBroadcastFramesRcv Counter64String,
    intervalEthRx3HS15minMulticastFramesRcv Counter64String,
    intervalEthRx3HS15minUndersizedFramesRcv Counter64String,
    intervalEthRx3HS15minOversizedFramesRcv Counter64String,
    intervalEthRx3HS15minFragmentFramesRcv Counter64String,
    intervalEthRx3HS15minJabberFrameRcv Counter64String,
    intervalEthRx3HS15minControlFrameRcv Counter64String,
    intervalEthRx3HS15minBytesFrames64Rcv Counter64String,
    intervalEthRx3HS15minBytesFrames65Rcv Counter64String,
    intervalEthRx3HS15minBytesFrames128Rcv Counter64String,
    intervalEthRx3HS15minBytesFrames256Rcv Counter64String,
    intervalEthRx3HS15minBytesFrames512Rcv Counter64String,
    intervalEthRx3HS15minBytesFrames1024Rcv Counter64String,
    intervalEthRx3HS15minBytesFrames1519Rcv Counter64String,
    intervalEthRx3HS15minValidFlag TruthValue,
    intervalEthRx3HS15minTimeStamp DateAndTime }

intervalEthRx3HS15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalEthRx3HS15minEntry 1 }

intervalEthRx3HS15minGoodFrames OBJECT-TYPE
    SYNTAX      Counter64String
    MAX-ACCESS  read-only
    STATUS      current
    DESCRIPTION
        "Frames Received" 
    ::=  { intervalEthRx3HS15minEntry 2 }

intervalEthRx3HS15minPauseFrames OBJECT-TYPE
    SYNTAX      Counter64String
    MAX-ACCESS  read-only
    STATUS      current
    DESCRIPTION
        "Pause Frames Received" 
    ::=  { intervalEthRx3HS15minEntry 3 }

intervalEthRx3HS15minCrcFrames OBJECT-TYPE
    SYNTAX      Counter64String
    MAX-ACCESS  read-only
    STATUS      current
    DESCRIPTION
        "Received CRC Errors" 
    ::=  { intervalEthRx3HS15minEntry 4 }

intervalEthRx3HS15minBytes OBJECT-TYPE
    SYNTAX      Counter64String
    MAX-ACCESS  read-only
    STATUS      current
    DESCRIPTION
        "Bytes Received" 
    ::=  { intervalEthRx3HS15minEntry 5 }

intervalEthRx3HS15minBroadcastFramesRcv OBJECT-TYPE
    SYNTAX      Counter64String
    MAX-ACCESS  read-only
    STATUS      current
    DESCRIPTION
        "Broadcast Frames Received" 
    ::=  { intervalEthRx3HS15minEntry 6 }

intervalEthRx3HS15minMulticastFramesRcv OBJECT-TYPE
    SYNTAX      Counter64String
    MAX-ACCESS  read-only
    STATUS      current
    DESCRIPTION
        "Multicast Frames Received" 
    ::=  { intervalEthRx3HS15minEntry 7 }

intervalEthRx3HS15minUndersizedFramesRcv OBJECT-TYPE
    SYNTAX      Counter64String
    MAX-ACCESS  read-only
    STATUS      current
    DESCRIPTION
        "Undersized Frames Received" 
    ::=  { intervalEthRx3HS15minEntry 8 }

intervalEthRx3HS15minOversizedFramesRcv OBJECT-TYPE
    SYNTAX      Counter64String
    MAX-ACCESS  read-only
    STATUS      current
    DESCRIPTION
        "Oversized Frames Received" 
    ::=  { intervalEthRx3HS15minEntry 9 }

intervalEthRx3HS15minFragmentFramesRcv OBJECT-TYPE
    SYNTAX      Counter64String
    MAX-ACCESS  read-only
    STATUS      current
    DESCRIPTION
        "Fragment Frames Received" 
    ::=  { intervalEthRx3HS15minEntry 10 }

intervalEthRx3HS15minJabberFrameRcv OBJECT-TYPE
    SYNTAX      Counter64String
    MAX-ACCESS  read-only
    STATUS      current
    DESCRIPTION
        "Rx Jabber Frame" 
    ::=  { intervalEthRx3HS15minEntry 11 }

intervalEthRx3HS15minControlFrameRcv OBJECT-TYPE
    SYNTAX      Counter64String
    MAX-ACCESS  read-only
    STATUS      current
    DESCRIPTION
        "Control Frames Received" 
    ::=  { intervalEthRx3HS15minEntry 12 }

intervalEthRx3HS15minBytesFrames64Rcv OBJECT-TYPE
    SYNTAX      Counter64String
    MAX-ACCESS  read-only
    STATUS      current
    DESCRIPTION
        "64 Byte Frames Received" 
    ::=  { intervalEthRx3HS15minEntry 13 }

intervalEthRx3HS15minBytesFrames65Rcv OBJECT-TYPE
    SYNTAX      Counter64String
    MAX-ACCESS  read-only
    STATUS      current
    DESCRIPTION
        "65-127 Byte Frames Received" 
    ::=  { intervalEthRx3HS15minEntry 14 }

intervalEthRx3HS15minBytesFrames128Rcv OBJECT-TYPE
    SYNTAX      Counter64String
    MAX-ACCESS  read-only
    STATUS      current
    DESCRIPTION
        "128-255 Byte Frames Received" 
    ::=  { intervalEthRx3HS15minEntry 15 }

intervalEthRx3HS15minBytesFrames256Rcv OBJECT-TYPE
    SYNTAX      Counter64String
    MAX-ACCESS  read-only
    STATUS      current
    DESCRIPTION
        "256-511 Byte Frames Received" 
    ::=  { intervalEthRx3HS15minEntry 16 }

intervalEthRx3HS15minBytesFrames512Rcv OBJECT-TYPE
    SYNTAX      Counter64String
    MAX-ACCESS  read-only
    STATUS      current
    DESCRIPTION
        "512-1023 Byte Frames Received" 
    ::=  { intervalEthRx3HS15minEntry 17 }

intervalEthRx3HS15minBytesFrames1024Rcv OBJECT-TYPE
    SYNTAX      Counter64String
    MAX-ACCESS  read-only
    STATUS      current
    DESCRIPTION
        "1024-1518 Byte Frames Received" 
    ::=  { intervalEthRx3HS15minEntry 18 }

intervalEthRx3HS15minBytesFrames1519Rcv OBJECT-TYPE
    SYNTAX      Counter64String
    MAX-ACCESS  read-only
    STATUS      current
    DESCRIPTION
        "1519-Max Byte Frames Received" 
    ::=  { intervalEthRx3HS15minEntry 19 }

intervalEthRx3HS15minValidFlag OBJECT-TYPE
    SYNTAX      TruthValue
    MAX-ACCESS  read-only
    STATUS      current
    DESCRIPTION
        "Valid Flag" 
    ::=  { intervalEthRx3HS15minEntry 20 }

intervalEthRx3HS15minTimeStamp OBJECT-TYPE
    SYNTAX      DateAndTime
    MAX-ACCESS  read-only
    STATUS      current
    DESCRIPTION
        "Timestamp" 
    ::=  { intervalEthRx3HS15minEntry 21 }

intervalEthRx3HS1dayTable OBJECT-TYPE
    SYNTAX      SEQUENCE OF IntervalEthRx3HS1dayEntry
    MAX-ACCESS  not-accessible
    STATUS      current
    DESCRIPTION   ""
    ::=  { performanceMonitoring 185 }

intervalEthRx3HS1dayEntry OBJECT-TYPE
    SYNTAX      IntervalEthRx3HS1dayEntry
    MAX-ACCESS  not-accessible
    STATUS      current
    DESCRIPTION   ""
    INDEX       {
                  entityIndex,
                  intervalEthRx3HS1dayNumber
                }
    ::=  { intervalEthRx3HS1dayTable 1 }

IntervalEthRx3HS1dayEntry ::=  SEQUENCE
  { intervalEthRx3HS1dayNumber Integer32,
    intervalEthRx3HS1dayGoodFrames Counter64String,
    intervalEthRx3HS1dayPauseFrames Counter64String,
    intervalEthRx3HS1dayCrcFrames Counter64String,
    intervalEthRx3HS1dayBytes Counter64String,
    intervalEthRx3HS1dayBroadcastFramesRcv Counter64String,
    intervalEthRx3HS1dayMulticastFramesRcv Counter64String,
    intervalEthRx3HS1dayUndersizedFramesRcv Counter64String,
    intervalEthRx3HS1dayOversizedFramesRcv Counter64String,
    intervalEthRx3HS1dayFragmentFramesRcv Counter64String,
    intervalEthRx3HS1dayJabberFrameRcv Counter64String,
    intervalEthRx3HS1dayControlFrameRcv Counter64String,
    intervalEthRx3HS1dayBytesFrames64Rcv Counter64String,
    intervalEthRx3HS1dayBytesFrames65Rcv Counter64String,
    intervalEthRx3HS1dayBytesFrames128Rcv Counter64String,
    intervalEthRx3HS1dayBytesFrames256Rcv Counter64String,
    intervalEthRx3HS1dayBytesFrames512Rcv Counter64String,
    intervalEthRx3HS1dayBytesFrames1024Rcv Counter64String,
    intervalEthRx3HS1dayBytesFrames1519Rcv Counter64String,
    intervalEthRx3HS1dayValidFlag TruthValue,
    intervalEthRx3HS1dayTimeStamp DateAndTime }

intervalEthRx3HS1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalEthRx3HS1dayEntry 1 }

intervalEthRx3HS1dayGoodFrames OBJECT-TYPE
    SYNTAX      Counter64String
    MAX-ACCESS  read-only
    STATUS      current
    DESCRIPTION
        "Frames Received" 
    ::=  { intervalEthRx3HS1dayEntry 2 }

intervalEthRx3HS1dayPauseFrames OBJECT-TYPE
    SYNTAX      Counter64String
    MAX-ACCESS  read-only
    STATUS      current
    DESCRIPTION
        "Pause Frames Received" 
    ::=  { intervalEthRx3HS1dayEntry 3 }

intervalEthRx3HS1dayCrcFrames OBJECT-TYPE
    SYNTAX      Counter64String
    MAX-ACCESS  read-only
    STATUS      current
    DESCRIPTION
        "Received CRC Errors" 
    ::=  { intervalEthRx3HS1dayEntry 4 }

intervalEthRx3HS1dayBytes OBJECT-TYPE
    SYNTAX      Counter64String
    MAX-ACCESS  read-only
    STATUS      current
    DESCRIPTION
        "Bytes Received" 
    ::=  { intervalEthRx3HS1dayEntry 5 }

intervalEthRx3HS1dayBroadcastFramesRcv OBJECT-TYPE
    SYNTAX      Counter64String
    MAX-ACCESS  read-only
    STATUS      current
    DESCRIPTION
        "Broadcast Frames Received" 
    ::=  { intervalEthRx3HS1dayEntry 6 }

intervalEthRx3HS1dayMulticastFramesRcv OBJECT-TYPE
    SYNTAX      Counter64String
    MAX-ACCESS  read-only
    STATUS      current
    DESCRIPTION
        "Multicast Frames Received" 
    ::=  { intervalEthRx3HS1dayEntry 7 }

intervalEthRx3HS1dayUndersizedFramesRcv OBJECT-TYPE
    SYNTAX      Counter64String
    MAX-ACCESS  read-only
    STATUS      current
    DESCRIPTION
        "Undersized Frames Received" 
    ::=  { intervalEthRx3HS1dayEntry 8 }

intervalEthRx3HS1dayOversizedFramesRcv OBJECT-TYPE
    SYNTAX      Counter64String
    MAX-ACCESS  read-only
    STATUS      current
    DESCRIPTION
        "Oversized Frames Received" 
    ::=  { intervalEthRx3HS1dayEntry 9 }

intervalEthRx3HS1dayFragmentFramesRcv OBJECT-TYPE
    SYNTAX      Counter64String
    MAX-ACCESS  read-only
    STATUS      current
    DESCRIPTION
        "Fragment Frames Received" 
    ::=  { intervalEthRx3HS1dayEntry 10 }

intervalEthRx3HS1dayJabberFrameRcv OBJECT-TYPE
    SYNTAX      Counter64String
    MAX-ACCESS  read-only
    STATUS      current
    DESCRIPTION
        "Rx Jabber Frame" 
    ::=  { intervalEthRx3HS1dayEntry 11 }

intervalEthRx3HS1dayControlFrameRcv OBJECT-TYPE
    SYNTAX      Counter64String
    MAX-ACCESS  read-only
    STATUS      current
    DESCRIPTION
        "Control Frames Received" 
    ::=  { intervalEthRx3HS1dayEntry 12 }

intervalEthRx3HS1dayBytesFrames64Rcv OBJECT-TYPE
    SYNTAX      Counter64String
    MAX-ACCESS  read-only
    STATUS      current
    DESCRIPTION
        "64 Byte Frames Received" 
    ::=  { intervalEthRx3HS1dayEntry 13 }

intervalEthRx3HS1dayBytesFrames65Rcv OBJECT-TYPE
    SYNTAX      Counter64String
    MAX-ACCESS  read-only
    STATUS      current
    DESCRIPTION
        "65-127 Byte Frames Received" 
    ::=  { intervalEthRx3HS1dayEntry 14 }

intervalEthRx3HS1dayBytesFrames128Rcv OBJECT-TYPE
    SYNTAX      Counter64String
    MAX-ACCESS  read-only
    STATUS      current
    DESCRIPTION
        "128-255 Byte Frames Received" 
    ::=  { intervalEthRx3HS1dayEntry 15 }

intervalEthRx3HS1dayBytesFrames256Rcv OBJECT-TYPE
    SYNTAX      Counter64String
    MAX-ACCESS  read-only
    STATUS      current
    DESCRIPTION
        "256-511 Byte Frames Received" 
    ::=  { intervalEthRx3HS1dayEntry 16 }

intervalEthRx3HS1dayBytesFrames512Rcv OBJECT-TYPE
    SYNTAX      Counter64String
    MAX-ACCESS  read-only
    STATUS      current
    DESCRIPTION
        "512-1023 Byte Frames Received" 
    ::=  { intervalEthRx3HS1dayEntry 17 }

intervalEthRx3HS1dayBytesFrames1024Rcv OBJECT-TYPE
    SYNTAX      Counter64String
    MAX-ACCESS  read-only
    STATUS      current
    DESCRIPTION
        "1024-1518 Byte Frames Received" 
    ::=  { intervalEthRx3HS1dayEntry 18 }

intervalEthRx3HS1dayBytesFrames1519Rcv OBJECT-TYPE
    SYNTAX      Counter64String
    MAX-ACCESS  read-only
    STATUS      current
    DESCRIPTION
        "1519-Max Byte Frames Received" 
    ::=  { intervalEthRx3HS1dayEntry 19 }

intervalEthRx3HS1dayValidFlag OBJECT-TYPE
    SYNTAX      TruthValue
    MAX-ACCESS  read-only
    STATUS      current
    DESCRIPTION
        "Valid Flag" 
    ::=  { intervalEthRx3HS1dayEntry 20 }

intervalEthRx3HS1dayTimeStamp OBJECT-TYPE
    SYNTAX      DateAndTime
    MAX-ACCESS  read-only
    STATUS      current
    DESCRIPTION
        "Timestamp" 
    ::=  { intervalEthRx3HS1dayEntry 21 }

intervalPhysPerfSkew15minTable OBJECT-TYPE
    SYNTAX      SEQUENCE OF IntervalPhysPerfSkew15minEntry
    MAX-ACCESS  not-accessible
    STATUS      current
    DESCRIPTION   ""
    ::=  { performanceMonitoring 186 }

intervalPhysPerfSkew15minEntry OBJECT-TYPE
    SYNTAX      IntervalPhysPerfSkew15minEntry
    MAX-ACCESS  not-accessible
    STATUS      current
    DESCRIPTION   ""
    INDEX       {
                  entityIndex,
                  intervalPhysPerfSkew15minNumber
                }
    ::=  { intervalPhysPerfSkew15minTable 1 }

IntervalPhysPerfSkew15minEntry ::=  SEQUENCE
  { intervalPhysPerfSkew15minNumber Integer32,
    intervalPhysPerfSkew15minLow Integer32,
    intervalPhysPerfSkew15minMean Integer32,
    intervalPhysPerfSkew15minHigh Integer32,
    intervalPhysPerfSkew15minValidFlag TruthValue,
    intervalPhysPerfSkew15minTimeStamp DateAndTime }

intervalPhysPerfSkew15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalPhysPerfSkew15minEntry 1 }

intervalPhysPerfSkew15minLow OBJECT-TYPE
    SYNTAX      Integer32 
    UNITS       "ns"
    MAX-ACCESS  read-only
    STATUS      current
    DESCRIPTION
        "Skew between logical lanes farthest apart low" 
    ::=  { intervalPhysPerfSkew15minEntry 2 }

intervalPhysPerfSkew15minMean OBJECT-TYPE
    SYNTAX      Integer32 
    UNITS       "ns"
    MAX-ACCESS  read-only
    STATUS      current
    DESCRIPTION
        "Skew between logical lanes farthest apart mean" 
    ::=  { intervalPhysPerfSkew15minEntry 3 }

intervalPhysPerfSkew15minHigh OBJECT-TYPE
    SYNTAX      Integer32 
    UNITS       "ns"
    MAX-ACCESS  read-only
    STATUS      current
    DESCRIPTION
        "Skew between logical lanes farthest apart high" 
    ::=  { intervalPhysPerfSkew15minEntry 4 }

intervalPhysPerfSkew15minValidFlag OBJECT-TYPE
    SYNTAX      TruthValue
    MAX-ACCESS  read-only
    STATUS      current
    DESCRIPTION
        "Valid Flag" 
    ::=  { intervalPhysPerfSkew15minEntry 5 }

intervalPhysPerfSkew15minTimeStamp OBJECT-TYPE
    SYNTAX      DateAndTime
    MAX-ACCESS  read-only
    STATUS      current
    DESCRIPTION
        "Timestamp" 
    ::=  { intervalPhysPerfSkew15minEntry 6 }

intervalPhysPerfSkew1dayTable OBJECT-TYPE
    SYNTAX      SEQUENCE OF IntervalPhysPerfSkew1dayEntry
    MAX-ACCESS  not-accessible
    STATUS      current
    DESCRIPTION   ""
    ::=  { performanceMonitoring 187 }

intervalPhysPerfSkew1dayEntry OBJECT-TYPE
    SYNTAX      IntervalPhysPerfSkew1dayEntry
    MAX-ACCESS  not-accessible
    STATUS      current
    DESCRIPTION   ""
    INDEX       {
                  entityIndex,
                  intervalPhysPerfSkew1dayNumber
                }
    ::=  { intervalPhysPerfSkew1dayTable 1 }

IntervalPhysPerfSkew1dayEntry ::=  SEQUENCE
  { intervalPhysPerfSkew1dayNumber Integer32,
    intervalPhysPerfSkew1dayLow Integer32,
    intervalPhysPerfSkew1dayMean Integer32,
    intervalPhysPerfSkew1dayHigh Integer32,
    intervalPhysPerfSkew1dayValidFlag TruthValue,
    intervalPhysPerfSkew1dayTimeStamp DateAndTime }

intervalPhysPerfSkew1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalPhysPerfSkew1dayEntry 1 }

intervalPhysPerfSkew1dayLow OBJECT-TYPE
    SYNTAX      Integer32 
    UNITS       "ns"
    MAX-ACCESS  read-only
    STATUS      current
    DESCRIPTION
        "Skew between logical lanes farthest apart low" 
    ::=  { intervalPhysPerfSkew1dayEntry 2 }

intervalPhysPerfSkew1dayMean OBJECT-TYPE
    SYNTAX      Integer32 
    UNITS       "ns"
    MAX-ACCESS  read-only
    STATUS      current
    DESCRIPTION
        "Skew between logical lanes farthest apart mean" 
    ::=  { intervalPhysPerfSkew1dayEntry 3 }

intervalPhysPerfSkew1dayHigh OBJECT-TYPE
    SYNTAX      Integer32 
    UNITS       "ns"
    MAX-ACCESS  read-only
    STATUS      current
    DESCRIPTION
        "Skew between logical lanes farthest apart high" 
    ::=  { intervalPhysPerfSkew1dayEntry 4 }

intervalPhysPerfSkew1dayValidFlag OBJECT-TYPE
    SYNTAX      TruthValue
    MAX-ACCESS  read-only
    STATUS      current
    DESCRIPTION
        "Valid Flag" 
    ::=  { intervalPhysPerfSkew1dayEntry 5 }

intervalPhysPerfSkew1dayTimeStamp OBJECT-TYPE
    SYNTAX      DateAndTime
    MAX-ACCESS  read-only
    STATUS      current
    DESCRIPTION
        "Timestamp" 
    ::=  { intervalPhysPerfSkew1dayEntry 6 }

intervalPhysPerfSkew1weekTable OBJECT-TYPE
    SYNTAX      SEQUENCE OF IntervalPhysPerfSkew1weekEntry
    MAX-ACCESS  not-accessible
    STATUS      current
    DESCRIPTION   ""
    ::=  { performanceMonitoring 188 }

intervalPhysPerfSkew1weekEntry OBJECT-TYPE
    SYNTAX      IntervalPhysPerfSkew1weekEntry
    MAX-ACCESS  not-accessible
    STATUS      current
    DESCRIPTION   ""
    INDEX       {
                  entityIndex,
                  intervalPhysPerfSkew1weekNumber
                }
    ::=  { intervalPhysPerfSkew1weekTable 1 }

IntervalPhysPerfSkew1weekEntry ::=  SEQUENCE
  { intervalPhysPerfSkew1weekNumber Integer32,
    intervalPhysPerfSkew1weekLow Integer32,
    intervalPhysPerfSkew1weekMean Integer32,
    intervalPhysPerfSkew1weekHigh Integer32,
    intervalPhysPerfSkew1weekValidFlag TruthValue,
    intervalPhysPerfSkew1weekTimeStamp DateAndTime }

intervalPhysPerfSkew1weekNumber OBJECT-TYPE
    SYNTAX      Integer32 (1..52)
    MAX-ACCESS  not-accessible
    STATUS      current
    DESCRIPTION
        "Number 1week" 
    ::=  { intervalPhysPerfSkew1weekEntry 1 }

intervalPhysPerfSkew1weekLow OBJECT-TYPE
    SYNTAX      Integer32 
    UNITS       "ns"
    MAX-ACCESS  read-only
    STATUS      current
    DESCRIPTION
        "Skew between logical lanes farthest apart low" 
    ::=  { intervalPhysPerfSkew1weekEntry 2 }

intervalPhysPerfSkew1weekMean OBJECT-TYPE
    SYNTAX      Integer32 
    UNITS       "ns"
    MAX-ACCESS  read-only
    STATUS      current
    DESCRIPTION
        "Skew between logical lanes farthest apart mean" 
    ::=  { intervalPhysPerfSkew1weekEntry 3 }

intervalPhysPerfSkew1weekHigh OBJECT-TYPE
    SYNTAX      Integer32 
    UNITS       "ns"
    MAX-ACCESS  read-only
    STATUS      current
    DESCRIPTION
        "Skew between logical lanes farthest apart high" 
    ::=  { intervalPhysPerfSkew1weekEntry 4 }

intervalPhysPerfSkew1weekValidFlag OBJECT-TYPE
    SYNTAX      TruthValue
    MAX-ACCESS  read-only
    STATUS      current
    DESCRIPTION
        "Valid Flag" 
    ::=  { intervalPhysPerfSkew1weekEntry 5 }

intervalPhysPerfSkew1weekTimeStamp OBJECT-TYPE
    SYNTAX      DateAndTime
    MAX-ACCESS  read-only
    STATUS      current
    DESCRIPTION
        "Timestamp" 
    ::=  { intervalPhysPerfSkew1weekEntry 6 }

currentType4PhysCodingLayer15minTable OBJECT-TYPE
    SYNTAX      SEQUENCE OF CurrentType4PhysCodingLayer15minEntry
    MAX-ACCESS  not-accessible
    STATUS      current
    DESCRIPTION   ""
    ::=  { performanceMonitoring 189 }

currentType4PhysCodingLayer15minEntry OBJECT-TYPE
    SYNTAX      CurrentType4PhysCodingLayer15minEntry
    MAX-ACCESS  not-accessible
    STATUS      current
    DESCRIPTION   ""
    INDEX       {
                  entityIndex
                }
    ::=  { currentType4PhysCodingLayer15minTable 1 }

CurrentType4PhysCodingLayer15minEntry ::=  SEQUENCE
  { currentType4PhysCodingLayer15minES Unsigned32,
    currentType4PhysCodingLayer15minCV Counter64String,
    currentType4PhysCodingLayer15minBBE Counter64String,
    currentType4PhysCodingLayer15minElapsedTime Integer32 }

currentType4PhysCodingLayer15minES OBJECT-TYPE
    SYNTAX      Unsigned32
    MAX-ACCESS  read-only
    STATUS      current
    DESCRIPTION
        "Physical Coding Layer Errored Seconds" 
    ::=  { currentType4PhysCodingLayer15minEntry 1 }

currentType4PhysCodingLayer15minCV OBJECT-TYPE
    SYNTAX      Counter64String
    MAX-ACCESS  read-only
    STATUS      current
    DESCRIPTION
        "Physical Coding Layer Coding Violations" 
    ::=  { currentType4PhysCodingLayer15minEntry 2 }

currentType4PhysCodingLayer15minBBE OBJECT-TYPE
    SYNTAX      Counter64String
    MAX-ACCESS  read-only
    STATUS      current
    DESCRIPTION
        "PCS Background Block Errors" 
    ::=  { currentType4PhysCodingLayer15minEntry 3 }

currentType4PhysCodingLayer15minElapsedTime OBJECT-TYPE
    SYNTAX      Integer32 (0..9000 | -2147483648)
    MAX-ACCESS  read-only
    STATUS      current
    DESCRIPTION
        "Elapsed 15Min" 
    ::=  { currentType4PhysCodingLayer15minEntry 4 }

currentType4PhysCodingLayer1dayTable OBJECT-TYPE
    SYNTAX      SEQUENCE OF CurrentType4PhysCodingLayer1dayEntry
    MAX-ACCESS  not-accessible
    STATUS      current
    DESCRIPTION   ""
    ::=  { performanceMonitoring 190 }

currentType4PhysCodingLayer1dayEntry OBJECT-TYPE
    SYNTAX      CurrentType4PhysCodingLayer1dayEntry
    MAX-ACCESS  not-accessible
    STATUS      current
    DESCRIPTION   ""
    INDEX       {
                  entityIndex
                }
    ::=  { currentType4PhysCodingLayer1dayTable 1 }

CurrentType4PhysCodingLayer1dayEntry ::=  SEQUENCE
  { currentType4PhysCodingLayer1dayES Unsigned32,
    currentType4PhysCodingLayer1dayCV Counter64String,
    currentType4PhysCodingLayer1dayBBE Counter64String,
    currentType4PhysCodingLayer1dayElapsedTime Integer32 }

currentType4PhysCodingLayer1dayES OBJECT-TYPE
    SYNTAX      Unsigned32
    MAX-ACCESS  read-only
    STATUS      current
    DESCRIPTION
        "Physical Coding Layer Errored Seconds" 
    ::=  { currentType4PhysCodingLayer1dayEntry 1 }

currentType4PhysCodingLayer1dayCV OBJECT-TYPE
    SYNTAX      Counter64String
    MAX-ACCESS  read-only
    STATUS      current
    DESCRIPTION
        "Physical Coding Layer Coding Violations" 
    ::=  { currentType4PhysCodingLayer1dayEntry 2 }

currentType4PhysCodingLayer1dayBBE OBJECT-TYPE
    SYNTAX      Counter64String
    MAX-ACCESS  read-only
    STATUS      current
    DESCRIPTION
        "PCS Background Block Errors" 
    ::=  { currentType4PhysCodingLayer1dayEntry 3 }

currentType4PhysCodingLayer1dayElapsedTime OBJECT-TYPE
    SYNTAX      Integer32 (0..86400 | -2147483648)
    MAX-ACCESS  read-only
    STATUS      current
    DESCRIPTION
        "Elapsed 1Day" 
    ::=  { currentType4PhysCodingLayer1dayEntry 4 }

intervalType4PhysCodingLayer15minTable OBJECT-TYPE
    SYNTAX      SEQUENCE OF IntervalType4PhysCodingLayer15minEntry
    MAX-ACCESS  not-accessible
    STATUS      current
    DESCRIPTION   ""
    ::=  { performanceMonitoring 191 }

intervalType4PhysCodingLayer15minEntry OBJECT-TYPE
    SYNTAX      IntervalType4PhysCodingLayer15minEntry
    MAX-ACCESS  not-accessible
    STATUS      current
    DESCRIPTION   ""
    INDEX       {
                  entityIndex,
                  intervalType4PhysCodingLayer15minNumber
                }
    ::=  { intervalType4PhysCodingLayer15minTable 1 }

IntervalType4PhysCodingLayer15minEntry ::=  SEQUENCE
  { intervalType4PhysCodingLayer15minNumber Integer32,
    intervalType4PhysCodingLayer15minES Unsigned32,
    intervalType4PhysCodingLayer15minCV Counter64String,
    intervalType4PhysCodingLayer15minBBE Counter64String,
    intervalType4PhysCodingLayer15minValidFlag TruthValue,
    intervalType4PhysCodingLayer15minTimeStamp DateAndTime }

intervalType4PhysCodingLayer15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalType4PhysCodingLayer15minEntry 1 }

intervalType4PhysCodingLayer15minES OBJECT-TYPE
    SYNTAX      Unsigned32
    MAX-ACCESS  read-only
    STATUS      current
    DESCRIPTION
        "Physical Coding Layer Errored Seconds" 
    ::=  { intervalType4PhysCodingLayer15minEntry 2 }

intervalType4PhysCodingLayer15minCV OBJECT-TYPE
    SYNTAX      Counter64String
    MAX-ACCESS  read-only
    STATUS      current
    DESCRIPTION
        "Physical Coding Layer Coding Violations" 
    ::=  { intervalType4PhysCodingLayer15minEntry 3 }

intervalType4PhysCodingLayer15minBBE OBJECT-TYPE
    SYNTAX      Counter64String
    MAX-ACCESS  read-only
    STATUS      current
    DESCRIPTION
        "PCS Background Block Errors" 
    ::=  { intervalType4PhysCodingLayer15minEntry 4 }

intervalType4PhysCodingLayer15minValidFlag OBJECT-TYPE
    SYNTAX      TruthValue
    MAX-ACCESS  read-only
    STATUS      current
    DESCRIPTION
        "Valid Flag" 
    ::=  { intervalType4PhysCodingLayer15minEntry 5 }

intervalType4PhysCodingLayer15minTimeStamp OBJECT-TYPE
    SYNTAX      DateAndTime
    MAX-ACCESS  read-only
    STATUS      current
    DESCRIPTION
        "Timestamp" 
    ::=  { intervalType4PhysCodingLayer15minEntry 6 }

intervalType4PhysCodingLayer1dayTable OBJECT-TYPE
    SYNTAX      SEQUENCE OF IntervalType4PhysCodingLayer1dayEntry
    MAX-ACCESS  not-accessible
    STATUS      current
    DESCRIPTION   ""
    ::=  { performanceMonitoring 192 }

intervalType4PhysCodingLayer1dayEntry OBJECT-TYPE
    SYNTAX      IntervalType4PhysCodingLayer1dayEntry
    MAX-ACCESS  not-accessible
    STATUS      current
    DESCRIPTION   ""
    INDEX       {
                  entityIndex,
                  intervalType4PhysCodingLayer1dayNumber
                }
    ::=  { intervalType4PhysCodingLayer1dayTable 1 }

IntervalType4PhysCodingLayer1dayEntry ::=  SEQUENCE
  { intervalType4PhysCodingLayer1dayNumber Integer32,
    intervalType4PhysCodingLayer1dayES Unsigned32,
    intervalType4PhysCodingLayer1dayCV Counter64String,
    intervalType4PhysCodingLayer1dayBBE Counter64String,
    intervalType4PhysCodingLayer1dayValidFlag TruthValue,
    intervalType4PhysCodingLayer1dayTimeStamp DateAndTime }

intervalType4PhysCodingLayer1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalType4PhysCodingLayer1dayEntry 1 }

intervalType4PhysCodingLayer1dayES OBJECT-TYPE
    SYNTAX      Unsigned32
    MAX-ACCESS  read-only
    STATUS      current
    DESCRIPTION
        "Physical Coding Layer Errored Seconds" 
    ::=  { intervalType4PhysCodingLayer1dayEntry 2 }

intervalType4PhysCodingLayer1dayCV OBJECT-TYPE
    SYNTAX      Counter64String
    MAX-ACCESS  read-only
    STATUS      current
    DESCRIPTION
        "Physical Coding Layer Coding Violations" 
    ::=  { intervalType4PhysCodingLayer1dayEntry 3 }

intervalType4PhysCodingLayer1dayBBE OBJECT-TYPE
    SYNTAX      Counter64String
    MAX-ACCESS  read-only
    STATUS      current
    DESCRIPTION
        "PCS Background Block Errors" 
    ::=  { intervalType4PhysCodingLayer1dayEntry 4 }

intervalType4PhysCodingLayer1dayValidFlag OBJECT-TYPE
    SYNTAX      TruthValue
    MAX-ACCESS  read-only
    STATUS      current
    DESCRIPTION
        "Valid Flag" 
    ::=  { intervalType4PhysCodingLayer1dayEntry 5 }

intervalType4PhysCodingLayer1dayTimeStamp OBJECT-TYPE
    SYNTAX      DateAndTime
    MAX-ACCESS  read-only
    STATUS      current
    DESCRIPTION
        "Timestamp" 
    ::=  { intervalType4PhysCodingLayer1dayEntry 6 }

currentDefectSeconds15minTable OBJECT-TYPE
    SYNTAX      SEQUENCE OF CurrentDefectSeconds15minEntry
    MAX-ACCESS  not-accessible
    STATUS      current
    DESCRIPTION   ""
    ::=  { performanceMIB 64 }

currentDefectSeconds15minEntry OBJECT-TYPE
    SYNTAX      CurrentDefectSeconds15minEntry
    MAX-ACCESS  not-accessible
    STATUS      current
    DESCRIPTION   ""
    INDEX       {
                  entityIndex
                }
    ::=  { currentDefectSeconds15minTable 1 }

CurrentDefectSeconds15minEntry ::=  SEQUENCE
  { currentDefectSeconds15minDS Unsigned32,
    currentDefectSeconds15minElapsedTime Integer32 }

currentDefectSeconds15minDS OBJECT-TYPE
    SYNTAX      Unsigned32
    MAX-ACCESS  read-only
    STATUS      current
    DESCRIPTION
        "Defect Seconds" 
    ::=  { currentDefectSeconds15minEntry 1 }

currentDefectSeconds15minElapsedTime OBJECT-TYPE
    SYNTAX      Integer32 (0..9000 | -2147483648)
    MAX-ACCESS  read-only
    STATUS      current
    DESCRIPTION
        "Elapsed 15Min" 
    ::=  { currentDefectSeconds15minEntry 2 }

currentDefectSeconds1dayTable OBJECT-TYPE
    SYNTAX      SEQUENCE OF CurrentDefectSeconds1dayEntry
    MAX-ACCESS  not-accessible
    STATUS      current
    DESCRIPTION   ""
    ::=  { performanceMIB 65 }

currentDefectSeconds1dayEntry OBJECT-TYPE
    SYNTAX      CurrentDefectSeconds1dayEntry
    MAX-ACCESS  not-accessible
    STATUS      current
    DESCRIPTION   ""
    INDEX       {
                  entityIndex
                }
    ::=  { currentDefectSeconds1dayTable 1 }

CurrentDefectSeconds1dayEntry ::=  SEQUENCE
  { currentDefectSeconds1dayDS Unsigned32,
    currentDefectSeconds1dayElapsedTime Integer32 }

currentDefectSeconds1dayDS OBJECT-TYPE
    SYNTAX      Unsigned32
    MAX-ACCESS  read-only
    STATUS      current
    DESCRIPTION
        "Defect Seconds" 
    ::=  { currentDefectSeconds1dayEntry 1 }

currentDefectSeconds1dayElapsedTime OBJECT-TYPE
    SYNTAX      Integer32 (0..86400 | -2147483648)
    MAX-ACCESS  read-only
    STATUS      current
    DESCRIPTION
        "Elapsed 1Day" 
    ::=  { currentDefectSeconds1dayEntry 2 }

intervalDefectSeconds15minTable OBJECT-TYPE
    SYNTAX      SEQUENCE OF IntervalDefectSeconds15minEntry
    MAX-ACCESS  not-accessible
    STATUS      current
    DESCRIPTION   ""
    ::=  { performanceMIB 66 }

intervalDefectSeconds15minEntry OBJECT-TYPE
    SYNTAX      IntervalDefectSeconds15minEntry
    MAX-ACCESS  not-accessible
    STATUS      current
    DESCRIPTION   ""
    INDEX       {
                  entityIndex,
                  intervalDefectSeconds15minNumber
                }
    ::=  { intervalDefectSeconds15minTable 1 }

IntervalDefectSeconds15minEntry ::=  SEQUENCE
  { intervalDefectSeconds15minNumber Integer32,
    intervalDefectSeconds15minDS Unsigned32,
    intervalDefectSeconds15minValidFlag TruthValue,
    intervalDefectSeconds15minTimeStamp DateAndTime }

intervalDefectSeconds15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalDefectSeconds15minEntry 1 }

intervalDefectSeconds15minDS OBJECT-TYPE
    SYNTAX      Unsigned32
    MAX-ACCESS  read-only
    STATUS      current
    DESCRIPTION
        "Defect Seconds" 
    ::=  { intervalDefectSeconds15minEntry 2 }

intervalDefectSeconds15minValidFlag OBJECT-TYPE
    SYNTAX      TruthValue
    MAX-ACCESS  read-only
    STATUS      current
    DESCRIPTION
        "Valid Flag" 
    ::=  { intervalDefectSeconds15minEntry 3 }

intervalDefectSeconds15minTimeStamp OBJECT-TYPE
    SYNTAX      DateAndTime
    MAX-ACCESS  read-only
    STATUS      current
    DESCRIPTION
        "Timestamp" 
    ::=  { intervalDefectSeconds15minEntry 4 }

intervalDefectSeconds1dayTable OBJECT-TYPE
    SYNTAX      SEQUENCE OF IntervalDefectSeconds1dayEntry
    MAX-ACCESS  not-accessible
    STATUS      current
    DESCRIPTION   ""
    ::=  { performanceMIB 67 }

intervalDefectSeconds1dayEntry OBJECT-TYPE
    SYNTAX      IntervalDefectSeconds1dayEntry
    MAX-ACCESS  not-accessible
    STATUS      current
    DESCRIPTION   ""
    INDEX       {
                  entityIndex,
                  intervalDefectSeconds1dayNumber
                }
    ::=  { intervalDefectSeconds1dayTable 1 }

IntervalDefectSeconds1dayEntry ::=  SEQUENCE
  { intervalDefectSeconds1dayNumber Integer32,
    intervalDefectSeconds1dayDS Unsigned32,
    intervalDefectSeconds1dayValidFlag TruthValue,
    intervalDefectSeconds1dayTimeStamp DateAndTime }

intervalDefectSeconds1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalDefectSeconds1dayEntry 1 }

intervalDefectSeconds1dayDS OBJECT-TYPE
    SYNTAX      Unsigned32
    MAX-ACCESS  read-only
    STATUS      current
    DESCRIPTION
        "Defect Seconds" 
    ::=  { intervalDefectSeconds1dayEntry 2 }

intervalDefectSeconds1dayValidFlag OBJECT-TYPE
    SYNTAX      TruthValue
    MAX-ACCESS  read-only
    STATUS      current
    DESCRIPTION
        "Valid Flag" 
    ::=  { intervalDefectSeconds1dayEntry 3 }

intervalDefectSeconds1dayTimeStamp OBJECT-TYPE
    SYNTAX      DateAndTime
    MAX-ACCESS  read-only
    STATUS      current
    DESCRIPTION
        "Timestamp" 
    ::=  { intervalDefectSeconds1dayEntry 4 }

f7Containers   OBJECT IDENTIFIER ::= { fspR7VendorTypes 1 }

f7ContainerFanSlot   OBJECT IDENTIFIER ::= { f7Containers 1 }

f7ContainerModuleSlot   OBJECT IDENTIFIER ::= { f7Containers 2 }

f7ContainerSfpSlot   OBJECT IDENTIFIER ::= { f7Containers 3 }

f7Shelfs   OBJECT IDENTIFIER ::= { fspR7VendorTypes 2 }

f7FanUnits   OBJECT IDENTIFIER ::= { fspR7VendorTypes 3 }

f7FanUnitsFan   OBJECT IDENTIFIER ::= { f7FanUnits 1 }

f7Modules   OBJECT IDENTIFIER ::= { fspR7VendorTypes 4 }

f7eqpSh1hu   OBJECT IDENTIFIER ::= { f7Modules 1 }

f7eqpSh1huDc   OBJECT IDENTIFIER ::= { f7Modules 2 }

f7eqpSh3hu   OBJECT IDENTIFIER ::= { f7Modules 3 }

f7eqpSh7hu   OBJECT IDENTIFIER ::= { f7Modules 4 }

f7eqpUnknown   OBJECT IDENTIFIER ::= { f7Modules 5 }

f7eqpNcu   OBJECT IDENTIFIER ::= { f7Modules 6 }

f7eqpNcutif   OBJECT IDENTIFIER ::= { f7Modules 7 }

f7eqpScu   OBJECT IDENTIFIER ::= { f7Modules 8 }

f7eqpScue   OBJECT IDENTIFIER ::= { f7Modules 9 }

f7eqpR6cu   OBJECT IDENTIFIER ::= { f7Modules 10 }

f7eqpPsu1huac   OBJECT IDENTIFIER ::= { f7Modules 11 }

f7eqpPsu7huac   OBJECT IDENTIFIER ::= { f7Modules 12 }

f7eqpPsu7hudc   OBJECT IDENTIFIER ::= { f7Modules 13 }

f7eqpFcu7hu   OBJECT IDENTIFIER ::= { f7Modules 14 }

f7eqp2clsmd   OBJECT IDENTIFIER ::= { f7Modules 15 }

f7eqp2absmc   OBJECT IDENTIFIER ::= { f7Modules 16 }

f7eqp2bsmd   OBJECT IDENTIFIER ::= { f7Modules 17 }

f7eqp1Gsmud   OBJECT IDENTIFIER ::= { f7Modules 18 }

f7eqp4gsmd   OBJECT IDENTIFIER ::= { f7Modules 19 }

f7eqp8gsmd   OBJECT IDENTIFIER ::= { f7Modules 20 }

f7eqp1csmuc   OBJECT IDENTIFIER ::= { f7Modules 21 }

f7eqp1csmuewc   OBJECT IDENTIFIER ::= { f7Modules 22 }

f7eqp4csmd   OBJECT IDENTIFIER ::= { f7Modules 23 }

f7eqp4csmud   OBJECT IDENTIFIER ::= { f7Modules 24 }

f7eqp4csmc   OBJECT IDENTIFIER ::= { f7Modules 25 }

f7eqpOsfm   OBJECT IDENTIFIER ::= { f7Modules 26 }

f7eqp1pm   OBJECT IDENTIFIER ::= { f7Modules 27 }

f7eqp2pm   OBJECT IDENTIFIER ::= { f7Modules 28 }

f7eqp40csmd   OBJECT IDENTIFIER ::= { f7Modules 29 }

f7eqpDcm   OBJECT IDENTIFIER ::= { f7Modules 30 }

f7eqpEdfas   OBJECT IDENTIFIER ::= { f7Modules 31 }

f7eqpEdfasgc   OBJECT IDENTIFIER ::= { f7Modules 32 }

f7eqpEdfadgc   OBJECT IDENTIFIER ::= { f7Modules 33 }

f7eqpRaman   OBJECT IDENTIFIER ::= { f7Modules 34 }

f7eqp4tcc2g5   OBJECT IDENTIFIER ::= { f7Modules 35 }

f7eqp4tcc2g5d   OBJECT IDENTIFIER ::= { f7Modules 36 }

f7eqp4tcc10gd   OBJECT IDENTIFIER ::= { f7Modules 37 }

f7eqp4tcc10gc   OBJECT IDENTIFIER ::= { f7Modules 38 }

f7eqpWcc10gd   OBJECT IDENTIFIER ::= { f7Modules 39 }

f7eqpWcc10gc   OBJECT IDENTIFIER ::= { f7Modules 40 }

f7eqpWcc2g7   OBJECT IDENTIFIER ::= { f7Modules 41 }

f7eqpWcc2g7d   OBJECT IDENTIFIER ::= { f7Modules 42 }

f7eqp2tcm2g5   OBJECT IDENTIFIER ::= { f7Modules 43 }

f7eqp2tca2g5   OBJECT IDENTIFIER ::= { f7Modules 44 }

f7eqp8tca10gd   OBJECT IDENTIFIER ::= { f7Modules 45 }

f7eqp8tca10gc   OBJECT IDENTIFIER ::= { f7Modules 46 }

f7eqpWca10gd   OBJECT IDENTIFIER ::= { f7Modules 47 }

f7eqpWca10gc   OBJECT IDENTIFIER ::= { f7Modules 48 }

f7eqp4tca4gd   OBJECT IDENTIFIER ::= { f7Modules 49 }

f7eqp4tca4gc   OBJECT IDENTIFIER ::= { f7Modules 50 }

f7eqpwca2g5   OBJECT IDENTIFIER ::= { f7Modules 51 }

f7eqp4tca1g3d   OBJECT IDENTIFIER ::= { f7Modules 52 }

f7eqp4tca1g3c   OBJECT IDENTIFIER ::= { f7Modules 53 }

f7eqp8tce2g5d   OBJECT IDENTIFIER ::= { f7Modules 54 }

f7eqp8tce2g5c   OBJECT IDENTIFIER ::= { f7Modules 55 }

f7eqpWcelsd   OBJECT IDENTIFIER ::= { f7Modules 56 }

f7eqpWcelsc   OBJECT IDENTIFIER ::= { f7Modules 57 }

f7eqpVsm   OBJECT IDENTIFIER ::= { f7Modules 58 }

f7eqpRsmolm   OBJECT IDENTIFIER ::= { f7Modules 59 }

f7eqpRsmsf   OBJECT IDENTIFIER ::= { f7Modules 60 }

f7eqpOscm   OBJECT IDENTIFIER ::= { f7Modules 61 }

f7eqp2oscm   OBJECT IDENTIFIER ::= { f7Modules 62 }

f7eqpDrm   OBJECT IDENTIFIER ::= { f7Modules 63 }

f7eqpXfpG   OBJECT IDENTIFIER ::= { f7Modules 64 }

f7eqpsfpd   OBJECT IDENTIFIER ::= { f7Modules 65 }

f7eqpSfpc   OBJECT IDENTIFIER ::= { f7Modules 66 }

f7eqpSfpg   OBJECT IDENTIFIER ::= { f7Modules 67 }

f7eqpSfpe   OBJECT IDENTIFIER ::= { f7Modules 68 }

f7eqpSh1hudcm   OBJECT IDENTIFIER ::= { f7Modules 69 }

f7eqpCustomc   OBJECT IDENTIFIER ::= { f7Modules 70 }

f7eqpCustomd   OBJECT IDENTIFIER ::= { f7Modules 71 }

f7eqpPsu1hudc   OBJECT IDENTIFIER ::= { f7Modules 72 }

f7eqpWcc2g7c   OBJECT IDENTIFIER ::= { f7Modules 73 }

f7eqp1csmuEwD   OBJECT IDENTIFIER ::= { f7Modules 74 }

f7eqp1csmuG   OBJECT IDENTIFIER ::= { f7Modules 75 }

f7eqp3BsmC   OBJECT IDENTIFIER ::= { f7Modules 76 }

f7eqpF2kSh5hu   OBJECT IDENTIFIER ::= { f7Modules 77 }

f7eqpF2kSh6hu   OBJECT IDENTIFIER ::= { f7Modules 78 }

f7eqp2Tca2g5s   OBJECT IDENTIFIER ::= { f7Modules 79 }

f7eqp8Csmuc   OBJECT IDENTIFIER ::= { f7Modules 80 }

f7eqpEdfaDgcb   OBJECT IDENTIFIER ::= { f7Modules 81 }

f7eqpOscm2n   OBJECT IDENTIFIER ::= { f7Modules 82 }

f7eqp4Tcc10gtd   OBJECT IDENTIFIER ::= { f7Modules 83 }

f7eqp4Tca4g   OBJECT IDENTIFIER ::= { f7Modules 84 }

f7eqpDcg   OBJECT IDENTIFIER ::= { f7Modules 85 }

f7eqp2Tcm2g5d   OBJECT IDENTIFIER ::= { f7Modules 86 }

f7eqp2Tcm2g5c   OBJECT IDENTIFIER ::= { f7Modules 87 }

f7eqpWcm2g5d   OBJECT IDENTIFIER ::= { f7Modules 88 }

f7eqpWcm2g5c   OBJECT IDENTIFIER ::= { f7Modules 89 }

f7eqpEdfmSgc   OBJECT IDENTIFIER ::= { f7Modules 90 }

f7eqpF2kDemiV2   OBJECT IDENTIFIER ::= { f7Modules 91 }

f7eqpPsm955   OBJECT IDENTIFIER ::= { f7Modules 92 }

f7eqpNcu2e   OBJECT IDENTIFIER ::= { f7Modules 93 }

f7eqp8TceGl2g5d   OBJECT IDENTIFIER ::= { f7Modules 94 }

f7eqp8TceGl2g5c   OBJECT IDENTIFIER ::= { f7Modules 95 }

f7Plugs   OBJECT IDENTIFIER ::= { fspR7VendorTypes 5 }

f7SFPCL   OBJECT IDENTIFIER ::= { f7Plugs 1 }

f7SFPHS   OBJECT IDENTIFIER ::= { f7Plugs 2 }

f7SFP2G1   OBJECT IDENTIFIER ::= { f7Plugs 3 }

f7SFP2G5   OBJECT IDENTIFIER ::= { f7Plugs 4 }

f7SFP4G   OBJECT IDENTIFIER ::= { f7Plugs 5 }

f7XFP10G   OBJECT IDENTIFIER ::= { f7Plugs 6 }

f7Ports   OBJECT IDENTIFIER ::= { fspR7VendorTypes 6 }

f7OTU1   OBJECT IDENTIFIER ::= { f7Ports 1 }

f7OTU2   OBJECT IDENTIFIER ::= { f7Ports 2 }

f710GBE   OBJECT IDENTIFIER ::= { f7Ports 3 }

f7OC192   OBJECT IDENTIFIER ::= { f7Ports 4 }

f7OC48   OBJECT IDENTIFIER ::= { f7Ports 5 }

f7STM16   OBJECT IDENTIFIER ::= { f7Ports 6 }

f7STM64   OBJECT IDENTIFIER ::= { f7Ports 7 }

f710GFC   OBJECT IDENTIFIER ::= { f7Ports 8 }

f710GFP   OBJECT IDENTIFIER ::= { f7Ports 9 }

f7Error   OBJECT IDENTIFIER ::= { fspR7VendorTypes 7 }


END
